package GambitRevisionMatrix {
  private import ScalarValues::*;
  attribute scope:String="AUDIT-MATRIX: one framework support REV, independent of the13-item runtime programme and SMP12 acceptance. Package the selected Git Python sources in the existing task cache and run the real selected tests/policy without publishing unrelated staging. No native runtime change or benchmark is implied.";
  attribute stage:String="Framework publication support before the next root-writer or borrower cut; not another runtime milestone.";
  attribute formalDuty:String="SysML owns row kinds/fields and the five obligations. Existing ASCENT checks reviewed evidence, source context and missing/stale refusal. Python validates raw provenance, arithmetic and real commit-body transport. QNT competing histories and Lean semantic laws are unchanged: this metadata contract introduces neither obligation.";
  part def Need { ref part gate:GambitCommitGates::Gate; attribute id:String; attribute method:String; attribute artifact:String; attribute scope:String; }
  part tests:Need { ref part :>> gate=GambitCommitGates::tests; attribute :>> id="MATRIX-TESTS"; attribute :>> method="framework-tests"; attribute :>> artifact="dev/modeling/revision-matrix.org"; attribute :>> scope="Actual selected Git Python package, existing unit tests, native SysML/ASCENT controls and real Git numeric commit-body readback; unchanged120s supervisor, no Gambit runtime acceptance."; }
  part learning:Need { ref part :>> gate=GambitCommitGates::learning; attribute :>> id="MATRIX-LEARNING"; attribute :>> method="source-analysis"; attribute :>> artifact="dev/modeling/revision-matrix.org"; attribute :>> scope="Retire prose-only metrics and value/provenance drift. Added metadata reads/hashes, arithmetic and audit/test maintenance; performance remains unmeasured."; }
  part process:Need { ref part :>> gate=GambitCommitGates::process; attribute :>> id="MATRIX-PROCESS"; attribute :>> method="source-analysis"; attribute :>> artifact="dev/modeling/revision-matrix.org"; attribute :>> scope="One selected framework support cut; preserve unrelated index and working bytes; publish matrix in the actual commit body. Main item3/13 and independent SMP1/12 do not advance."; }
  part models:Need { ref part :>> gate=GambitCommitGates::models; attribute :>> id="MATRIX-MODELS"; attribute :>> method="source-refinement"; attribute :>> artifact="dev/modeling/revision-matrix.org"; attribute :>> scope="Native SysML row contract drives existing Python and ASCENT admission. All five obligations and matrix/audit omissions must fail closed; no copied QNT/Lean proofs."; }
  part questions:Need { ref part :>> gate=GambitCommitGates::questions; attribute :>> id="MATRIX-QUESTIONS"; attribute :>> method="source-analysis"; attribute :>> artifact="dev/modeling/revision-matrix.org"; attribute :>> scope="Why source identity is not causal speedup; how zero baseline, raw bool/numeric confusion, missing evidence, controls and historical supplements are distinguished. No unmeasured performance, GC or continuation claim."; }
}
