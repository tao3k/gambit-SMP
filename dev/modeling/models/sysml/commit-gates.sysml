package GambitCommitGates {
  private import ScalarValues::*;
  part def Gate { attribute id : String; attribute purpose : String; }
  part tests : Gate { attribute :>> id = "tests"; attribute :>> purpose = "All tests required by this source cut must finish with exact source and profile receipts. Missing, timeout, unknown or newly introduced/related failures block. A retained baseline failure may be classified outside the cut only by an explicit SysML/ASCENT source-input equivalence and scope-disjointness proof, complete unchanged manifests and real scoped tests; it remains a failure and vetoes whole-family acceptance. No name-only allowlist, manifest reduction or retry-until-green qualifies"; }
  part learning : Gate { attribute :>> id = "learning"; attribute :>> purpose = "State each claimed benefit, mechanism, retired responsibility, added cost and corresponding test/source evidence. Separate measured results from theoretical conditions; no inferred speedup"; }
  part process : Gate { attribute :>> id = "process"; attribute :>> purpose = "Disclose the current refactoring stage, dependencies, remaining steps and acceptance boundary. Justify every official-source change by the selected responsibility replacement; retain official names and build entrypoints unless their replacement is necessary and evidenced"; }
  part models : Gate { attribute :>> id = "models"; attribute :>> purpose = "Native SysML drives ASCENT; select QNT schedules and Lean laws only for applicable semantic changes, with distinct duties and actual source-refinement boundaries"; }
  part questions : Gate { attribute :>> id = "questions"; attribute :>> purpose = "Answer the mandatory Gambit-paper, semantic, amplification and counterexample questions within the claimed cut; unresolved mandatory answers block"; }
  part def MetricEvidenceRef {
    attribute path : String;
    attribute pointer : String;
  }
  part def MetricObservation {
    attribute value : Real;
    attribute unit : String;
    attribute samples : Integer;
    part origin : MetricEvidenceRef;
  }
  part def BenefitCostRow {
    attribute id : String;
    attribute kind : String;
    attribute metric : String;
    attribute unit : String;
    attribute direction : String;
    attribute workload : String;
    attribute method : String;
    attribute limitation : String;
    part baseline : MetricEvidenceRef [0..1];
    part candidate : MetricEvidenceRef [0..1];
    part evidence : MetricEvidenceRef [1..*];
  }
  part revisionAudit {
    attribute commitUnitRequired : Boolean = true;
    attribute deliveryRegistry : String = "dev/refactoring/modern-c/models/sysml/delivery-outcomes.sysml";
    attribute supportSurfaces : String = "tests/;.github/;dev/;docs/;evidence/;src/gambit_smp/;tools/";
    attribute supportFiles : String = ".gitignore;configure;configure.ac;aclocal.m4;makefile.in;include/makefile.in;gsc/makefile.in;gsi/makefile.in;lib/makefile.in;bin/makefile.in;pyproject.toml;uv.lock";
    attribute derivedAuditFiles : String = "source.json;source-manifest.json;model-contract.json;comment.json;admission.json";
    attribute publicationPolicy : String = "dev/modeling/models/sysml/research-storage.sysml";
    attribute deliveryRule : String = "Every submission declares one integration result or an explicit support correction. Runtime integration requires every result obligation, transitive predecessor obligation and component source/native case on the exact tested tree/profile, with durable reviewed evidence; five audit gates alone never permit a fragment. Support corrections declare exact non-runtime paths, no integration target and zero progress. Header/runtime/generator semantic work cannot disguise itself as support. Missing classification, omitted case, stale receipt, unrelated runtime path or claimed support progress blocks. Historical admissions remain immutable; future models must adopt this contract. Raw Git remains a human/external boundary, not an authority enforced by this framework.";
    attribute allRevisions : Boolean = true;
    attribute matrixRequired : Boolean = true;
    attribute matrixFields : String = "id,kind,metric,unit,direction,baseline,candidate,workload,method,evidence,limitation";
    attribute matrixKinds : String = "measurement,control,accounted-cost,structural,unmeasured";
    attribute matrixRule : String = "Every future REV audit binds a nonempty structured benefit/cost matrix to the same base/tree/profile. Numeric values, units and sample counts come from durable source-bound evidence, with raw origin pointers checked against the recorded values, not literal narrative guesses. Record workload, method and limitation for each row. Compute signed delta/percent only with defined baselines; zero baseline has no percentage or ratio. Single observations remain observations; control timings, source accounting and structural benefits are not runtime speedup. Missing/stale matrix, row fields or evidence block ASCENT admission. Any source-bound measured regression blocks publication even when another row improves. Runtime integrations additionally require at least one measured positive benefit; unmeasured, control and structural rows do not establish it. Local DENY packets retain adverse observations; they cannot be submitted as qualified REV commits or PR comments. A noisy unfavorable cohort remains a refusal until positive net benefit is established, never resampled selectively or hidden. Historical published audit packets remain immutable; later supplements are labeled separately.";
    attribute fields : String = "responsibility,retired,validation,benefits,costs,process,checklist,models,open";
    attribute rule : String = "Every REV, including small corrections, must publish its reviewed audit in the Git commit body: exact responsibility/retirement, reproducible tests and results, evidenced benefits, added costs, current process, repository Org checklist, distinct model duties and remaining gaps. Bind the report before ASCENT admission and reject later changes. Every user-facing progress/final report must identify the problem solved or still under qualification, stable checklist item, closed and remaining obligations with their counting unit, position/dependencies in the programme, and why the retired authority/work is a fundamental responsibility replacement with a falsifier. A planned item, scoped leaf, whole-stage closure and full SMP acceptance are different units; never derive an SMP percentage from test or REV counts. DEV refactoring progress is independent of SMP patch-line milestones; no 8-12 credit transfers";
  }
  part def SubmissionUnit {
    attribute kind : String;
    attribute result : String;
    attribute progressDelta : Integer;
    attribute supportPaths : String;
    attribute testModules : String default = "";
  }
}
