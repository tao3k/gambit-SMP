package SigintDeliverySemantics {
 private import ScalarValues::*;
 part def Contract { attribute key : String; attribute anchor : String; attribute actionName : String; attribute lemmaName : String; attribute duty : String; attribute status : String; }
 part contract0 : Contract { attribute :>> key = "derived-credit"; attribute :>> anchor = "setup.c:206-228"; attribute :>> actionName = "claim"; attribute :>> lemmaName = "claimReopensPending"; attribute :>> duty = "The source claim clears pending before vector fetch; a later publication belongs to a new claim epoch"; attribute :>> status = "serial source cut; C race proof open"; }
 part contract1 : Contract { attribute :>> key = "native-target"; attribute :>> anchor = "os_setup.c:3044-3049; os_tty.c:8700-8714"; attribute :>> actionName = "publish"; attribute :>> lemmaName = "targetIdentity"; attribute :>> duty = "Select VM0 processor0 at native callback acceptance under lifecycle lease; no kernel-origin generation inference"; attribute :>> status = "selection-time refinement open"; }
 part contract2 : Contract { attribute :>> key = "vector-fetch"; attribute :>> anchor = "_kernel.scm:1448-1476"; attribute :>> actionName = "fetchVector"; attribute :>> lemmaName = "frozenSelectedHandler"; attribute :>> duty = "Fetch vector after claim; root selected procedure; later replacement does not rewrite that reference"; attribute :>> status = "cross-processor writer serialization open"; }
 part contract3 : Contract { attribute :>> key = "storage-commit"; attribute :>> anchor = "setup.c:4834-4878; _thread.scm:1320-1394"; attribute :>> actionName = "retireVm"; attribute :>> lemmaName = "boundWorkBlocksRetirement"; attribute :>> duty = "Pending and active target-bound work retain old VM; root lease and native retirement receipts required"; attribute :>> status = "prior retirement guards inherited"; }
 part contract4 : Contract { attribute :>> key = "mailbox"; attribute :>> anchor = "setup.c:86,226; signal-gate-mailbox design"; attribute :>> actionName = "takeWake"; attribute :>> lemmaName = "sameEpochMerge"; attribute :>> duty = "Mailbox is wake hint; authoritative target/claim-epoch pending state survives drain; never merge across claim"; attribute :>> status = "new typed transport"; }
 part contract5 : Contract { attribute :>> key = "thread-route"; attribute :>> anchor = "_thread.scm:3245-3251,1398-1429,2715-2745"; attribute :>> actionName = "chooseThread"; attribute :>> lemmaName = "currentOrPrimordial"; attribute :>> duty = "Current thread invokes directly; absent current thread queues primordial thunk; preserve terminated-target exceptions"; attribute :>> status = "scheduler refinement open"; }
 part contract6 : Contract { attribute :>> key = "dynamic-handler"; attribute :>> anchor = "_thread.scm:5303-5353"; attribute :>> actionName = "execute"; attribute :>> lemmaName = "lateParameterLookup"; attribute :>> duty = "Read dynamic user handler when thunk executes; custom vector procedures and exceptions require separate semantic refinement"; attribute :>> status = "abstract identity observation only"; }
 part contract7 : Contract { attribute :>> key = "deferred-user"; attribute :>> anchor = "_thread.scm:5305-5328"; attribute :>> actionName = "installHandler"; attribute :>> lemmaName = "deferredReplay"; attribute :>> duty = "Deferred-user pending bit and setter-filter replay are separate from native pending; clear before calling supplied procedure"; attribute :>> status = "filter store and nonlocal exit obligations open"; }
 part def Gain { attribute key : String; attribute avoided : String; attribute added : String; attribute condition : String; }
 part gain0 : Gain { attribute :>> key = "coalescing"; attribute :>> avoided = "For n raises inside one unchanged target/claim epoch: n-1 extra pending records relative to per-event queue"; attribute :>> added = "n target admissions/publications plus one claim; per-target pending and epoch metadata"; attribute :>> condition = "Compared with current flag path no callback-count saving is established; merging across claim is forbidden"; }
 part gain1 : Gain { attribute :>> key = "wake"; attribute :>> avoided = "For n wake publications and b exchanges: at most n-b redundant wake batches can merge when b<=n"; attribute :>> added = "n atomic OR operations and b exchanges; wake failure fallback and custodian"; attribute :>> condition = "Only wake hints merge; no SIGINT delivery or user callback may be inferred completed from exchange"; }
 part gain2 : Gain { attribute :>> key = "retirement"; attribute :>> avoided = "Avoid stale target access and automatic migration of accepted old-VM requests"; attribute :>> added = "One target lease per accepted pending/active unit; retirement checks and unknown-outcome custody"; attribute :>> condition = "Old VM must remain serviceable until accepted work and roots settle; no bounded shutdown guarantee"; }
 part gain3 : Gain { attribute :>> key = "language"; attribute :>> avoided = "One modern C generated contract can replace divergent native target/flag interfaces"; attribute :>> added = "Atomic protocol, root maps, vector writer discipline, scheduler and exception refinement"; attribute :>> condition = "Zig does not remove these semantic obligations; additional language benefit remains unproved"; }
 part def Gate { attribute key : String; attribute qualified : Boolean; attribute duty : String; }
 part gate0 : Gate { attribute :>> key = "c-atomic"; attribute :>> qualified = false; attribute :>> duty = "ISO C race-free pending claim/publication and lock-free signal-safe ABI; SC first; no volatile-only proof"; }
 part gate1 : Gate { attribute :>> key = "rooting"; attribute :>> qualified = false; attribute :>> duty = "Selected vector closure, queued thunk, dynamic environment and continuation roots through GC and exceptions"; }
 part gate2 : Gate { attribute :>> key = "vector-writers"; attribute :>> qualified = false; attribute :>> duty = "All vector and dynamic binding writers serialized or owner scoped; not-interrupts-enabled is not cross-processor exclusion"; }
 part gate3 : Gate { attribute :>> key = "target-cut"; attribute :>> qualified = false; attribute :>> duty = "Native callback acceptance must preserve source target-choice histories; ingress pin versus acceptance displacement requires proof"; }
 part gate4 : Gate { attribute :>> key = "gap-policy"; attribute :>> qualified = false; attribute :>> duty = "Signals without accepted target remain unresolved custody or explicitly rejected; new-VM reassignment is not compatibility"; }
 part gate5 : Gate { attribute :>> key = "source-simulation"; attribute :>> qualified = false; attribute :>> duty = "Simulation includes custom vector effects, thread termination, priority, exceptions, continuation and fairness"; }
 part gate6 : Gate { attribute :>> key = "retirement"; attribute :>> qualified = false; attribute :>> duty = "Root/native/roster/OS join and inherited host attestation remain unresolved; formal model checks are not native admission"; }
 part history : GambitAssuranceRouting::ModelNeed { ref part :>> owner = GambitBuildAssurance::planner.component; attribute :>> obligationId = "IDS-H"; attribute :>> kind = "interleaving"; attribute :>> subjectPath = "models/build/sigint_delivery_semantics.qnt"; attribute :>> subjectScope = "safe: serial pending bit versus target claim key; ordered vector and dynamic handler selection"; attribute :>> premise = "Serial source observations are not a proof of race-free C or full Scheme observational equivalence"; }
 part induction : GambitAssuranceRouting::ModelNeed { ref part :>> owner = GambitBuildAssurance::planner.component; attribute :>> obligationId = "IDS-I"; attribute :>> kind = "induction"; attribute :>> subjectPath = "models/build/SigintDeliverySemantics.lean"; attribute :>> subjectScope = "arbitrary raise claim history refinement plus selection and retirement lemmas"; attribute :>> premise = "Serial source observations are not a proof of race-free C or full Scheme observational equivalence"; }
 part source : GambitAssuranceRouting::ModelNeed { ref part :>> owner = GambitBuildAssurance::planner.component; attribute :>> obligationId = "IDS-S"; attribute :>> kind = "source-refinement"; attribute :>> subjectPath = "dev/architecture/toolchain/sigint-delivery-semantics-design.org"; attribute :>> subjectScope = "SMP SIGINT callback to VM0, flag clear, vector fetch, current or primordial thunk and dynamic lookup"; attribute :>> premise = "Serial source observations are not a proof of race-free C or full Scheme observational equivalence"; }
 part platform : GambitAssuranceRouting::ModelNeed { ref part :>> owner = GambitBuildAssurance::planner.component; attribute :>> obligationId = "IDS-E"; attribute :>> kind = "environment-refinement"; attribute :>> subjectPath = "dev/architecture/toolchain/sigint-delivery-semantics-design.org"; attribute :>> subjectScope = "Darwin signal ABI, atomic safety, roots and VM retirement acceptance cut"; attribute :>> premise = "Serial source observations are not a proof of race-free C or full Scheme observational equivalence"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SignalGateMailbox::source; }
 part def ContractDependency { ref part dependent : Contract; ref part prerequisite : Contract; attribute reason : String; }
 part edge0 : ContractDependency { ref part :>> dependent = contract0; ref part :>> prerequisite = contract1; attribute :>> reason = "Target binding precedes flag ownership"; }
 part edge1 : ContractDependency { ref part :>> dependent = contract4; ref part :>> prerequisite = contract0; attribute :>> reason = "Wake batch must not extend claim epoch"; }
 part edge2 : ContractDependency { ref part :>> dependent = contract2; ref part :>> prerequisite = contract0; attribute :>> reason = "Claim precedes vector fetch"; }
 part edge3 : ContractDependency { ref part :>> dependent = contract5; ref part :>> prerequisite = contract2; attribute :>> reason = "Selected vector determines bridge path"; }
 part edge4 : ContractDependency { ref part :>> dependent = contract6; ref part :>> prerequisite = contract5; attribute :>> reason = "Dynamic lookup occurs in actual executing thread"; }
 part edge5 : ContractDependency { ref part :>> dependent = contract7; ref part :>> prerequisite = contract6; attribute :>> reason = "Deferred behavior depends on execution-time handler"; }
 part edge6 : ContractDependency { ref part :>> dependent = contract3; ref part :>> prerequisite = contract1; attribute :>> reason = "Accepted target owns lifecycle lease"; }
 part edge7 : ContractDependency { ref part :>> dependent = contract3; ref part :>> prerequisite = contract4; attribute :>> reason = "Wake drain cannot discharge semantic work"; }
 part edge8 : ContractDependency { ref part :>> dependent = contract3; ref part :>> prerequisite = contract5; attribute :>> reason = "Queued target thunk remains live"; }
 part edge9 : ContractDependency { ref part :>> dependent = contract3; ref part :>> prerequisite = contract7; attribute :>> reason = "Pending replay cannot be silently discarded"; }
}
