package IterCompilerService {
 private import ScalarValues::*;
 enum def ContextPhase { Created; Active; Suspended; Sealing; Draining; Closed; Quarantined; }
 enum def ResultKind { GeneratedScheme; NormalizedScheme; GVM; ModernC; }
 part def CompileContext {
  attribute contextId : String; attribute ownerId : String; attribute generation : Integer;
  attribute inputEpoch : Integer; attribute attemptId : String; attribute phaseState : ContextPhase;
  attribute semanticProfile : String; attribute layoutProfile : String;
  attribute rootDebt : Integer; attribute callbackDebt : Integer; attribute borrowDebt : Integer;
  attribute varCounter : Integer; attribute nodeCounter : Integer; attribute operandCursor : Integer;
 }
 part def StageResult {
  attribute producerId : String; attribute inputEpoch : Integer; attribute kind : ResultKind;
  attribute graphDetached : Boolean; attribute traceComplete : Boolean;
  attribute outcomeKnown : Boolean; attribute success : Boolean; attribute published : Boolean;
 }
 requirement def PublicationLaw { subject r : StageResult;
  require constraint { not r.published or (r.graphDetached and r.traceComplete and r.outcomeKnown and r.success) }
 }
 requirement def ContextReleaseLaw { subject c : CompileContext;
  require constraint { c.phaseState != ContextPhase::Closed or (c.rootDebt == 0 and c.callbackDebt == 0 and c.borrowDebt == 0) }
 }
 part def ChainSpec { attribute key : String; attribute labelText : String; attribute anchor : String; }
 part chain0 : ChainSpec { attribute :>> key = "helpers"; attribute :>> labelText = "std/interface + list-builder + iter/interface + iter/iterators"; attribute :>> anchor = "std/iter/macros.ss:4-7"; }
 part chain1 : ChainSpec { attribute :>> key = "macros"; attribute :>> labelText = "iter/macros: begin-syntax + for / for1 / dispatch"; attribute :>> anchor = "std/iter/macros.ss:10-100"; }
 part chain2 : ChainSpec { attribute :>> key = "api"; attribute :>> labelText = "iter/api -> std/iter re-export"; attribute :>> anchor = "std/iter/api.ss:4-22; std/iter.ss:4-5"; }
 part chain3 : ChainSpec { attribute :>> key = "misc"; attribute :>> labelText = "string/misc: for + in-range"; attribute :>> anchor = "std/string/misc.ss:227-234"; }
 part chain4 : ChainSpec { attribute :>> key = "wg"; attribute :>> labelText = "sync/wg: for + thread-join!"; attribute :>> anchor = "std/sync/wg.ss:37-40"; }
 part def ChainEdge { attribute fromKey : String; attribute toKey : String; attribute contract : String; }
 part chainEdge0 : ChainEdge { attribute :>> fromKey = "helpers"; attribute :>> toKey = "macros"; attribute :>> contract = "Direct source imports; transitive phase/effect closure open"; }
 part chainEdge1 : ChainEdge { attribute :>> fromKey = "macros"; attribute :>> toKey = "api"; attribute :>> contract = "Imports and reexports for bindings"; }
 part chainEdge2 : ChainEdge { attribute :>> fromKey = "api"; attribute :>> toKey = "misc"; attribute :>> contract = "std/iter import and real for/in-range consumer"; }
 part chainEdge3 : ChainEdge { attribute :>> fromKey = "api"; attribute :>> toKey = "wg"; attribute :>> contract = "std/iter import and real for consumer"; }
 part def SeamSpec { attribute key : String; attribute owner : String; attribute anchor : String; attribute input : String; attribute completion : String; }
 part seam0 : SeamSpec { attribute :>> key = "gerbil-expand"; attribute :>> owner = "Gerbil"; attribute :>> anchor = "iter/macros.ss:10-100; iter/api.ss:4-22; iter.ss:4-5"; attribute :>> input = "Binding projection + executable support + fresh instance + capability trace"; attribute :>> completion = "Complete owned semantic expansion; binding equality never substitutes for transformer support"; }
 part seam1 : SeamSpec { attribute :>> key = "generated-scheme"; attribute :>> owner = "Gerbil to Gambit"; attribute :>> anchor = "compiler/driver.ss:647-747,787-804"; attribute :>> input = "Structured code + module-scoped declarations + origin map + phi + semantic identity"; attribute :>> completion = "Not GVM; includes runtime, loader and positive-phase sections; no publication from partial output files"; }
 part seam2 : SeamSpec { attribute :>> key = "normalize"; attribute :>> owner = "Gambit"; attribute :>> anchor = "gsc/_front.scm:194-250,317-350"; attribute :>> input = "Owned parse/environment/normalization context; source and demanded modules"; attribute :>> completion = "Result may retain context references until deep seal or ownership transfer; textual dump is not a typed API"; }
 part seam3 : SeamSpec { attribute :>> key = "lower-gvm"; attribute :>> owner = "Gambit"; attribute :>> anchor = "gsc/_front.scm:397-411; gsc/_gvm.scm:3022-3029"; attribute :>> input = "Normalized graph + environment + C interface + target semantic profile"; attribute :>> completion = "GVM result and ModuleSpec/FrameSpec/PointId share a cohort; optimizer facts tracked"; }
 part seam4 : SeamSpec { attribute :>> key = "emit-modern-c"; attribute :>> owner = "Gambit to Gerbil"; attribute :>> anchor = "gsc/_front.scm:435-449; gsc/_back.scm:388-475"; attribute :>> input = "Sealed GVM + layout/ABI + native requirements + diagnostics + outcome"; attribute :>> completion = "Native tool/profile change need not invalidate expansion; target semantic change may invalidate normalization"; }
 part def ContextSpec { attribute key : String; attribute anchor : String; attribute stateSet : String; attribute isolation : String; attribute retirement : String; }
 part context0 : ContextSpec { attribute :>> key = "environment"; attribute :>> anchor = "_env.scm:348-361"; attribute :>> stateSet = "next-var-stamp, ret-var, ret-var-set, closure-env-var, empty-var"; attribute :>> isolation = "Owned per invocation; immutable primitives may be shared only after write census"; attribute :>> retirement = "All references either sealed/relocated or remain rooted in retained context"; }
 part context1 : ContextSpec { attribute :>> key = "parse-tree"; attribute :>> anchor = "_ptree1.scm:2980-2995"; attribute :>> stateSet = "ptree port, next-node-stamp, temp-variable-stamp"; attribute :>> isolation = "Session-owned diagnostic sink and counters; identity reconstruction required"; attribute :>> retirement = "Do not close caller-owned info port; deactivate callback authority before freeing context"; }
 part context2 : ContextSpec { attribute :>> key = "gvm"; attribute :>> anchor = "_gvm.scm:3022-3029; _front.scm:979-1035"; attribute :>> stateSet = "operand interning plus basic-block/emission state"; attribute :>> isolation = "Own interning tables and emission cursors; begin/end globals cannot overlap"; attribute :>> retirement = "Live result cannot outlast its region without sealing or ownership transfer"; }
 part context3 : ContextSpec { attribute :>> key = "target"; attribute :>> anchor = "_back.scm:388-475; _t-c-1.scm"; attribute :>> stateSet = "target selection, primitive metadata and target dispatch functions"; attribute :>> isolation = "Separate immutable target description from per-emission mutable data; complete target writer census open"; attribute :>> retirement = "Do not reuse context after unknown cleanup; output files held attempt-private"; }
 part context4 : ContextSpec { attribute :>> key = "outcome"; attribute :>> anchor = "_front.scm:336-350,352-462"; attribute :>> stateSet = "input/diagnostic ports, roots, suspended state, errors and result thunk"; attribute :>> isolation = "Guarded one-shot service completion; no cross-owner continuation resume"; attribute :>> retirement = "Cancellation/failure enters draining; release only after root/borrow/callback custody closes"; }
 part def RetireSpec { attribute key : String; attribute anchor : String; attribute condition : String; attribute removed : String; attribute retained : String; }
 part retire0 : RetireSpec { attribute :>> key = "module-completion"; attribute :>> anchor = "std/make.ss:299-343"; attribute :>> condition = "All import consumers request exact interface/support/native projections"; attribute :>> removed = "Retire whole-module completion as sole readiness gate"; attribute :>> retained = "Keep true initializer and phase dependencies; no arbitrary cycle breaking"; }
 part retire1 : RetireSpec { attribute :>> key = "driver-mutex"; attribute :>> anchor = "compiler/driver.ss:119-136,632-633"; attribute :>> condition = "All expander/optimizer/loader writers isolated and binding identity preserved"; attribute :>> removed = "Retire global import/optimizer serialization only after writer migration"; attribute :>> retained = "Process isolation is an alternative execution mechanism, not proof of same-VM safety"; }
 part retire2 : RetireSpec { attribute :>> key = "global-begin-end"; attribute :>> anchor = "_front.scm:326-347; _env/_ptree1/_gvm/_back"; attribute :>> condition = "Every mutable compiler/target state owner and cleanup endpoint identified"; attribute :>> removed = "Retire process-global begin/end authority within the new service"; attribute :>> retained = "Preserve standalone gsc as service client; no claim that current internal procedures are reentrant"; }
 part retire3 : RetireSpec { attribute :>> key = "scm-file-invoke"; attribute :>> anchor = "compiler/driver.ss:787-804,881-886"; attribute :>> condition = "Structured GeneratedSchemeResult + origin/declaration fidelity + stage consumers admitted"; attribute :>> removed = "Retire intermediate file roundtrip as authoritative service handoff"; attribute :>> retained = "Optional human-readable export stays possible; textual equality not sufficient semantic evidence"; }
 part retire4 : RetireSpec { attribute :>> key = "job-and-files"; attribute :>> anchor = "compiler/base.ss:287-335; compiler/driver.ss:686-747"; attribute :>> condition = "Every producer/waiter uses one resource budget and atomic manifest"; attribute :>> removed = "Retire duplicate deferred compile-job authority and direct partial-file acceptance"; attribute :>> retained = "Native jobs remain; shared scheduler must preserve exit diagnostics, unknown custody and bootstrap"; }
 part def GainSpec { attribute key : String; attribute avoided : String; attribute added : String; attribute condition : String; }
 part gain0 : GainSpec { attribute :>> key = "no-change"; attribute :>> avoided = "Admitted matching query recomputation: target zero executions"; attribute :>> added = "V_trace + materialization"; attribute :>> condition = "R > H; hidden dynamic reads or clocks invalidate reuse"; }
 part gain1 : GainSpec { attribute :>> key = "iter-code-edit"; attribute :>> avoided = "Only unchanged consumed projections can stop propagation"; attribute :>> added = "Rebuild support and every affected macro consumer"; attribute :>> condition = "Unchanged exported for names alone yields no cutoff; output equality must include origins/effects"; }
 part gain2 : GainSpec { attribute :>> key = "two-consumers"; attribute :>> avoided = "Unnecessary waiting for unrelated runtime/native completion"; attribute :>> added = "Context memory + scheduling + IPC + per-instance initialization"; attribute :>> condition = "For a proven nonsemantic gate U and branch span B: old span p+U+B; new DAG span p+max(U,B); saved span min(U,B) must exceed added span. Resource limits and real support edges still apply"; }
 part gain3 : GainSpec { attribute :>> key = "backend-edit"; attribute :>> avoided = "Frontend re-expansion when only nonsemantic native inputs changed"; attribute :>> added = "GVM/C/native cohort validation and changed native work"; attribute :>> condition = "Target semantics/declarations can cross the boundary; native ABI-only edits require a narrower proven projection"; }
 part def GateSpec { attribute key : String; attribute qualified : Boolean; attribute condition : String; }
 part gate0 : GateSpec { attribute :>> key = "phase-closure"; attribute :>> qualified = false; attribute :>> condition = "All iter transformer/helper/initializer/native support and ordered effects captured"; }
 part gate1 : GateSpec { attribute :>> key = "generated-scheme-fidelity"; attribute :>> qualified = false; attribute :>> condition = "Code, declarations, phi, identity, source origin and diagnostics refine the current emitter"; }
 part gate2 : GateSpec { attribute :>> key = "context-ownership"; attribute :>> qualified = false; attribute :>> condition = "All Gambit and Gerbil mutable writer sets, roots and callback/continuation exits owned"; }
 part gate3 : GateSpec { attribute :>> key = "stage-sealing"; attribute :>> qualified = false; attribute :>> condition = "Each cross-stage pointer graph sealed or ownership-transferred without dead references"; }
 part gate4 : GateSpec { attribute :>> key = "trace-order"; attribute :>> qualified = false; attribute :>> condition = "Sequential and independent parallel dependency sections preserve macro effects and errors"; }
 part gate5 : GateSpec { attribute :>> key = "scheduler-outcome"; attribute :>> qualified = false; attribute :>> condition = "No duplicate producers or stale-epoch result publication; cancellation/unknown drains before release"; }
 part gate6 : GateSpec { attribute :>> key = "source-platform"; attribute :>> qualified = false; attribute :>> condition = "Bounded protocol refines real actions; memory, IPC, runtime and actual work/span remain unqualified"; }
 part def RefinementSpec { attribute key : String; attribute qntScope : String; attribute leanScope : String; attribute evidenceGap : String; }
 part refinement0 : RefinementSpec { attribute :>> key = "context-owner"; attribute :>> qntScope = "acquire;live;pause;resume;close"; attribute :>> leanScope = "freshGeneration;releaseNotifies"; attribute :>> evidenceGap = "All real roots, borrowers, callbacks and continuation generations refine the abstract owner map"; }
 part refinement1 : RefinementSpec { attribute :>> key = "stage-prefix"; attribute :>> qntScope = "scheme;advance;seal;publish"; attribute :>> leanScope = "orderedPrefix;failureNotSuccess"; attribute :>> evidenceGap = "Typed graph sealing and GeneratedScheme fidelity remain source obligations"; }
 part refinement2 : RefinementSpec { attribute :>> key = "ordered-trace"; attribute :>> qntScope = "sequenceFirst;sequenceSecond"; attribute :>> leanScope = "projectionNeedsSupport"; attribute :>> evidenceGap = "Toy ordered guard is a negative control, not full trace-interpreter semantics"; }
 part refinement3 : RefinementSpec { attribute :>> key = "unknown-custody"; attribute :>> qntScope = "unknownOutcome;acknowledge;settle;drain"; attribute :>> leanScope = "releaseNotifies;sourceSeparate"; attribute :>> evidenceGap = "Endpoint settlement truth and cleanup failure must be proven from actual execution host"; }
 attribute consumerCount : Integer = 2;
 attribute capacity : Integer = 2;
 attribute lastStage : Integer = 4;
 attribute actualAdmitted : Boolean = false;
 part history : GambitAssuranceRouting::ModelNeed { ref part :>> owner = GambitBuildAssurance::planner.component; attribute :>> obligationId = "IS-H"; attribute :>> kind = "interleaving"; attribute :>> subjectPath = "models/build/iter_compiler_service.qnt"; attribute :>> subjectScope = "iter_compiler_service:Test$"; attribute :>> premise = "Two-consumer owned-context protocol and real iter stage seams; conditional design only; source and platform refinement open"; }
 part induction : GambitAssuranceRouting::ModelNeed { ref part :>> owner = GambitBuildAssurance::planner.component; attribute :>> obligationId = "IS-I"; attribute :>> kind = "induction"; attribute :>> subjectPath = "models/build/IterCompilerService.lean"; attribute :>> subjectScope = "IterCompilerService:orderedPrefix;freshGeneration;releaseNotifies;projectionNeedsSupport;workPositive;spanImproves;failureNotSuccess;sourceSeparate"; attribute :>> premise = "Two-consumer owned-context protocol and real iter stage seams; conditional design only; source and platform refinement open"; }
 part source : GambitAssuranceRouting::ModelNeed { ref part :>> owner = GambitBuildAssurance::planner.component; attribute :>> obligationId = "IS-S"; attribute :>> kind = "source-refinement"; attribute :>> subjectPath = "dev/architecture/toolchain/iter-compiler-service-design.org"; attribute :>> subjectScope = "IS-S:source"; attribute :>> premise = "Two-consumer owned-context protocol and real iter stage seams; conditional design only; source and platform refinement open"; }
 part platform : GambitAssuranceRouting::ModelNeed { ref part :>> owner = GambitBuildAssurance::planner.component; attribute :>> obligationId = "IS-E"; attribute :>> kind = "environment-refinement"; attribute :>> subjectPath = "dev/architecture/toolchain/iter-compiler-service-design.org"; attribute :>> subjectScope = "IS-E:platform"; attribute :>> premise = "Two-consumer owned-context protocol and real iter stage seams; conditional design only; source and platform refinement open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = IncrementalCompilerArchitecture::source; }
}
