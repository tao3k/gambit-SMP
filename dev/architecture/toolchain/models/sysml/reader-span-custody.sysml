package ReaderSpanCustody {
 private import ScalarValues::*;
 part def Producer { attribute key : String; attribute anchor : String; attribute custodian : String; attribute interval : String; attribute interruption : String; }
 part producer0 : Producer { attribute :>> key = "port-delivery"; attribute :>> anchor = "stream.ss:49-57; _io.scm:5240-5323"; attribute :>> custodian = "port then in-flight character delivery"; attribute :>> interval = "Decoded character read and physical counter update precede char-stream location publication"; attribute :>> interruption = "Refill/error has native-port state; no assertion that every point permits Scheme continuation capture"; }
 part producer1 : Producer { attribute :>> key = "private-replay"; attribute :>> anchor = "stream.ss:40-48,59-65; lexer.ss:159-167"; attribute :>> custodian = "original char-stream and acceptance closure"; attribute :>> interval = "Unread characters keep order and logical position; physical port is not rewound"; attribute :>> interruption = "Partial unget and mutable location updates need explicit substep ownership; arbitrary preemption is a refinement obligation"; }
 part producer2 : Producer { attribute :>> key = "accepted-reduction"; attribute :>> anchor = "lexer.ss:139-146,158-176; deflexer.ss:50-62"; attribute :>> custodian = "acceptance record before invoking R"; attribute :>> interval = "Accepted lexeme excludes speculative suffix; raw source storage must not alias mutable @@ without qualification"; attribute :>> interruption = "R may throw, capture or mutate @@ before a token is returned; acceptance custody cannot depend on successful return"; }
 part producer3 : Producer { attribute :>> key = "ignored-lexeme"; attribute :>> anchor = "lexer.ss:23-26,62-66; deflexer.ss:40-44; lang-reader.ss:271-274,323-324"; attribute :>> custodian = "trivia ledger before ignored singleton disappears"; attribute :>> interval = "Every ignored occurrence needs its own span; singleton $ has neither occurrence identity nor location"; attribute :>> interruption = "Record span before looping; do not rerun an effectful reduction to reconstruct trivia"; }
 part producer4 : Producer { attribute :>> key = "failed-lexeme"; attribute :>> anchor = "lexer.ss:128-130,185-190; base.ss:28-30"; attribute :>> custodian = "failed attempt then rooted ERROR token/exception"; attribute :>> interval = "Unsuccessful consumed prefix belongs to failure horizon, not successful accepted token or unread residue"; attribute :>> interruption = "Token/string allocation and error translation can fail; original attempt retains custody until successor owns it"; }
 part producer5 : Producer { attribute :>> key = "header-io"; attribute :>> anchor = "lang-reader.ss:88-124"; attribute :>> custodian = "section header invocation"; attribute :>> interval = "Two peek sites, three read-char sites and one read-line site bypass the five datum entries"; attribute :>> interruption = "Peek may refill without consuming a logical character; header is outside body ParseError catch"; }
 part producer6 : Producer { attribute :>> key = "scheme-datum"; attribute :>> anchor = "runtime/syntax.ss:255-266; _io.scm:12694-12698"; attribute :>> custodian = "readenv and original input domain"; attribute :>> interval = "Reader consumes datum plus skipped text; callbacks may have effects not represented by the AST span"; attribute :>> interruption = "Readtable and dynamic parameter state must remain live; returned AST extent is not total consumed input"; }
 part producer7 : Producer { attribute :>> key = "post-action-delivery"; attribute :>> anchor = "lang-reader.ss:169-183,242-245; _thread.scm:8555-8584"; attribute :>> custodian = "action/result record plus live frame aliases"; attribute :>> interval = "Action read, reset, following token/location, rule creation and K/E delivery are distinct endpoints"; attribute :>> interruption = "Returning action does not mean downstream delivery completed; captures retain current objects, not restored snapshots"; }
 part def Reader { attribute key : String; attribute lineNumber : Integer; attribute bodyCatch : Boolean; attribute consumer : String; attribute failure : String; }
 part reader0 : Reader { attribute :>> key = "module-body"; attribute :>> lineNumber = 23; attribute :>> bodyCatch = false; attribute :>> consumer = "body cons or section dispatch at 25-33"; attribute :>> failure = "EOF raises no-definitions error via physical error-location helper"; }
 part reader1 : Reader { attribute :>> key = "section-id"; attribute :>> lineNumber = 99; attribute :>> bodyCatch = false; attribute :>> consumer = "identifier check then options"; attribute :>> failure = "Read/header exceptions escape without body ParseError conversion"; }
 part reader2 : Reader { attribute :>> key = "section-option"; attribute :>> lineNumber = 123; attribute :>> bodyCatch = false; attribute :>> consumer = "cons opt then recursive header read"; attribute :>> failure = "EOF/comment/newline and raw header probes keep their own observations"; }
 part reader3 : Reader { attribute :>> key = "parser-action"; attribute :>> lineNumber = 166; attribute :>> bodyCatch = true; attribute :>> consumer = "reset, next token, alternative or K/E at 169-183"; attribute :>> failure = "EOF becomes helper syntax error; body ParseError is translated; other exceptions rethrow"; }
 part reader4 : Reader { attribute :>> key = "lexer-action"; attribute :>> lineNumber = 238; attribute :>> bodyCatch = true; attribute :>> consumer = "reset, fresh location, rule construction, K at 242-245"; attribute :>> failure = "EOF helper error and body catch distinct; quote-preserving entry is explicit behavior repair"; }
 part def ResetPath { attribute key : String; attribute lineNumber : Integer; attribute nextStep : String; attribute condition : String; }
 part reset0 : ResetPath { attribute :>> key = "parser-reset"; attribute :>> lineNumber = 169; attribute :>> nextStep = "Immediately reads next token before branch/rule construction"; attribute :>> condition = "Pending token objects, EOF cache, parser-tail aliases and action completion remain represented; no repeated R/reader call on unknown result"; }
 part reset1 : ResetPath { attribute :>> key = "lexer-reset"; attribute :>> lineNumber = 242; attribute :>> nextStep = "Immediately observes fresh stream location without reading"; attribute :>> condition = "Qualify old zero location versus corrected domain endpoint as observable mode/repair decision before eliminating reset"; }
 part def Gate { attribute key : String; attribute qualified : Boolean; attribute condition : String; }
 part gate0 : Gate { attribute :>> key = "source-interval-refinement"; attribute :>> qualified = false; attribute :>> condition = "Every character occurrence has one current custodian; pending, accepted, trivia, unread and failure horizons conserve fetched input"; }
 part gate1 : Gate { attribute :>> key = "mutable-source-isolation"; attribute :>> qualified = false; attribute :>> condition = "No callback-visible mutable @@ alias can corrupt retained source; coordinates alone do not provide replay contents"; }
 part gate2 : Gate { attribute :>> key = "all-entry-coverage"; attribute :>> qualified = false; attribute :>> condition = "Five datum sites, six raw header sites, error-location helpers and native aliases all mediated or owned legacy"; }
 part gate3 : Gate { attribute :>> key = "capture-and-error-custody"; attribute :>> qualified = false; attribute :>> condition = "Live captures preserve original stream/domain and wind semantics; error translation transfers roots only after successor custody"; }
 part gate4 : Gate { attribute :>> key = "reset-retirement"; attribute :>> qualified = false; attribute :>> condition = "Both distinct post-action consumers preserve/repair observations; old aliases drain or retain legacy state; result unknown never implies read retry"; }
 part def Gain { attribute key : String; attribute avoided : String; attribute added : String; attribute threshold : String; }
 part gain0 : Gain { attribute :>> key = "reset-construction"; attribute :>> avoided = "Upper bound 2A stream constructor calls plus A initial-location calls; identical to prior bound, not additive"; attribute :>> added = "Acceptance/trivia/failure records, pins, grammar-view selection and location adapter"; attribute :>> threshold = "Avoided actual work exceeds added work; no allocation/time estimate inferred"; }
 part gain1 : Gain { attribute :>> key = "raw-storage"; attribute :>> avoided = "No reconstruct/relex retry merely to recover dropped source"; attribute :>> added = "Immutable retained chunks or proven isolated snapshot; mutable @@ cannot be reused freely"; attribute :>> threshold = "Unique retained decoded payload plus O(spans + live views); captures may retain unbounded history"; }
 part gain2 : Gain { attribute :>> key = "failure-continuation"; attribute :>> avoided = "Avoid accidental repeated callbacks, lost failure text and premature legacy retirement"; attribute :>> added = "Per-invocation settlement and root-transfer records; full Scheme continuation refinement remains necessary"; attribute :>> threshold = "Correctness prerequisite; no uniquely Zig saving established over modern C"; }
 attribute fixtureCharacters : Integer = 5;
 attribute actualAdmitted : Boolean = false;
 part history : GambitAssuranceRouting::ModelNeed { ref part :>> owner = GambitBuildAssurance::scheduler.component; attribute :>> obligationId = "RS-H"; attribute :>> kind = "interleaving"; attribute :>> subjectPath = "models/build/reader_span_custody.qnt"; attribute :>> subjectScope = "reader_span_custody:Test$"; attribute :>> premise = "Finite occurrence-set conservation, accepted versus failed prefix, callback mutation isolation, exception route and result-unknown controls; not arbitrary Scheme preemption"; }
 part induction : GambitAssuranceRouting::ModelNeed { ref part :>> owner = GambitBuildAssurance::scheduler.component; attribute :>> obligationId = "RS-I"; attribute :>> kind = "induction"; attribute :>> subjectPath = "models/build/ReaderSpanCustody.lean"; attribute :>> subjectScope = "ReaderSpanCustody:handoffConserves;partitionPrefix;stableSourceSurvivesCallback;bodyCatchOnly;liveResume;noRetirePending;netBenefit"; attribute :>> premise = "Conditional custody, source isolation, exception routing and net work kernels; source simulation, multi-shot winding and native delivery open"; }
 part source : GambitAssuranceRouting::ModelNeed { ref part :>> owner = GambitBuildAssurance::scheduler.component; attribute :>> obligationId = "RS-S"; attribute :>> kind = "source-refinement"; attribute :>> subjectPath = "dev/architecture/toolchain/reader-span-custody-design.org"; attribute :>> subjectScope = "RS-S:reader-span-source"; attribute :>> premise = "Actual producer/caller census derived; arbitrary callback alias reachability, control restoration and source-model step relation remain open"; }
 part platform : GambitAssuranceRouting::ModelNeed { ref part :>> owner = GambitBuildAssurance::scheduler.component; attribute :>> obligationId = "RS-E"; attribute :>> kind = "environment-refinement"; attribute :>> subjectPath = "dev/architecture/toolchain/reader-span-custody-design.org"; attribute :>> subjectScope = "RS-E:reader-span-native"; attribute :>> premise = "Physical delivery/refill synchronization, GC roots, immutable chunk publication, native alias exclusion and C memory order remain unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = LogicalCursor::source; }
}
