package SyncOpGuardCustody {
 private import ScalarValues::*;
 part def CallerSpec { attribute key : String; attribute anchor : String; attribute condition : String; }
 part caller0 : CallerSpec { attribute :>> key = "sync-request"; attribute :>> anchor = "setup.c:1117-1151,1182-1198"; attribute :>> condition = "on_all_processors raises sync interrupt and enters the same execute_sync_op_loop as servicing peers; stop root mutation without disabling processor-1 dispatcher participation"; }
 part caller1 : CallerSpec { attribute :>> key = "loop-completion"; attribute :>> anchor = "setup.c:1068-1113"; attribute :>> condition = "Selected callback return, request result acknowledgement, first-iteration flag reset and later NOOP exit are distinct; processor-zero deferred error may throw after loop exit"; }
 part caller2 : CallerSpec { attribute :>> key = "resize-nested-gc"; attribute :>> anchor = "setup.c:887-978"; attribute :>> condition = "Resize has higher priority than GC and may collect internally over old members; it must defer instead of waiting for its blocked guard, and must not consume a different pending GC request"; }
 part caller3 : CallerSpec { attribute :>> key = "guard-catcher"; attribute :>> anchor = "gambit.h.in:9981-9987,10001-10006; setup.c:3383-3389"; attribute :>> condition = "Stable guard records primary error and old catcher, closes marker and transfers outcome-root custody before exact rethrow; terminal callback does not imply all storage retired"; }
 part caller4 : CallerSpec { attribute :>> key = "cleanup-authority"; attribute :>> anchor = "setup.c:396-417,932-933,950,978,4665-4672,4843-4863; mem.c:4432-4450,4928-4934"; attribute :>> condition = "Global shutdown, shrink retirement and unactivated setup rollback need different permits; procedural queue cleanup, foreign still release and bulk RC free cannot be treated as a single safe leaf"; }
 part def ProtocolSpec { attribute key : String; attribute anchor : String; attribute condition : String; }
 part protocol0 : ProtocolSpec { attribute :>> key = "ready-but-participating"; attribute :>> anchor = "setup.c:781-801,1117-1151"; attribute :>> condition = "Ready frame and stopped mutator remain attached to old VM roster and service sync-op; Scheme return does not remove the processor"; }
 part protocol1 : ProtocolSpec { attribute :>> key = "loop-return"; attribute :>> anchor = "setup.c:1068-1113"; attribute :>> condition = "First reset, selected operation disposition and pending request result settle before final NOOP; resize-internal GC does not consume pending GC, and reload follows the latest epoch"; }
 part protocol2 : ProtocolSpec { attribute :>> key = "guard-outcome"; attribute :>> anchor = "setup.c:3383-3389; gambit.h.in:9981-9987"; attribute :>> condition = "Guard catches admitted unwind, preserves primary payload/destination, invalidates owned marker and hands rooted outcome to VM custodian; cleanup error cannot overwrite primary unwind"; }
 part protocol3 : ProtocolSpec { attribute :>> key = "exit-preflight"; attribute :>> anchor = "setup.c:932-978,4843-4863; mem.c:4933-4934"; attribute :>> condition = "Before roster commit or teardown admission closes, drain guard/readers/pins/foreign producers under old serviceable roster; only acknowledged storage move permits retirement"; }
 part protocol4 : ProtocolSpec { attribute :>> key = "topology-and-reuse"; attribute :>> anchor = "setup.c:517-524,649-699,962-978"; attribute :>> condition = "All participants use one effective topology result; publication acceptance is separate from sender tails/retained convergence; unknown OS join never permits PSTATE generation reuse"; }
 part def RouteSpec { attribute key : String; attribute anchor : String; attribute qntAction : String; attribute leanLemma : String; attribute condition : String; }
 part route0 : RouteSpec { attribute :>> key = "registration"; attribute :>> anchor = "setup.c:1117-1151"; attribute :>> qntAction = "requestSync"; attribute :>> leanLemma = "readinessNotReturn"; attribute :>> condition = "VM root handoff must keep old roster serviceable rather than substitute an OS-blocked waiter for processor one"; }
 part route1 : RouteSpec { attribute :>> key = "custody"; attribute :>> anchor = "setup.c:1068-1113"; attribute :>> qntAction = "returnSync"; attribute :>> leanLemma = "gcReturnAloneInsufficient"; attribute :>> condition = "GC callback completion does not authorize caller restore before loop reset/result/NOOP closure"; }
 part route2 : RouteSpec { attribute :>> key = "coverage"; attribute :>> anchor = "setup.c:3383-3389; gambit.h.in:9981-9987"; attribute :>> qntAction = "handoffOutcome"; attribute :>> leanLemma = "rethrowNeedsOutcomeRoot"; attribute :>> condition = "Stable primary error/result cells must have a custodian independent of the unwound C frame"; }
 part route3 : RouteSpec { attribute :>> key = "publication"; attribute :>> anchor = "setup.c:649-699,932-978"; attribute :>> qntAction = "publishRoster"; attribute :>> leanLemma = "nonzeroVoteRequired"; attribute :>> condition = "Root readiness and local veto cannot change processor_count independently; collective effective topology precedes old sender-tail release"; }
 part route4 : RouteSpec { attribute :>> key = "retirement"; attribute :>> anchor = "mem.c:684-699,4432-4450,4933-4934"; attribute :>> qntAction = "cleanupInertRc"; attribute :>> leanLemma = "unknownStorageBlocks"; attribute :>> condition = "Old bulk cleanup may run only on an inert, unowned remainder after storage and foreign producer handoff; unresolved transfer retains custody"; }
 part def GainSpec { attribute key : String; attribute avoided : String; attribute added : String; attribute condition : String; }
 part gain0 : GainSpec { attribute :>> key = "service-reuse"; attribute :>> avoided = "A separate FFI GC waiter/coordinator that cannot execute its processor role"; attribute :>> added = "Readiness token, stable owner binding and exact loop-return acknowledgement"; attribute :>> condition = "Reuse current service_sync_op/selected operation and existing NOOP exit only after source refinement; no assumption that root-ready means arbitrary native blocking is legal"; }
 part gain1 : GainSpec { attribute :>> key = "guard-reuse"; attribute :>> avoided = "Duplicate cleanup and replay after uncertain response; primary unwind corruption"; attribute :>> added = "Generated C completion state, rooted result/error handoff and per-resource terminal receipts"; attribute :>> condition = "Reuse runtime catcher mechanism with explicit guards; all supported nonlocal exits must reach the contract"; }
 part gain2 : GainSpec { attribute :>> key = "retirement"; attribute :>> avoided = "Premature thread retirement, unknown-join slot reuse and bulk freeing retained RC/still storage"; attribute :>> added = "Collective preflight, foreign-release accounting, storage transfer and sender-tail closure"; attribute :>> condition = "Added O(P) acknowledgement/domain bookkeeping may reuse existing rounds only if qualified; no measured speedup or zero-cost topology change is claimed"; }
 part def RefinementSpec { attribute key : String; attribute qntScope : String; attribute leanScope : String; attribute sourceDuty : String; }
 part refinement0 : RefinementSpec { attribute :>> key = "participant"; attribute :>> qntScope = "installGuard;publishReady;requestSync;join;selectGc;resetFlag;enterGc;scanOwnerRoot;returnGc;decideSelectedResize;reselectPendingGc;acknowledgeRequest;arriveNoop;chooseNoop;returnSync;recordDeferredError;catchLoopFailure;restoreOwner"; attribute :>> leanScope = "readinessNotReturn;sleepingDoesNotParticipate;gcReturnAloneInsufficient;internalGcCannotConsumeRequest;loopReturnRequiresReset"; attribute :>> sourceDuty = "Map real tree selection, first_iter, priority resize deferral, pending GC reselection and owner generation; both GCs use old roster; arbitrary request composition and fairness remain open"; }
 part refinement1 : RefinementSpec { attribute :>> key = "guard"; attribute :>> qntScope = "allocateMarker;normalReturn;catchThrow;restoreCatcher;closeMarker;recordSecondary;failNormalCleanup;settleGuard;handoffOutcome;withdrawRoot;propagate"; attribute :>> leanScope = "cleanupPreservesOriginal;rethrowNeedsOutcomeRoot;collectiveUnwindMustWait;pinBlocksWithdrawal"; attribute :>> sourceDuty = "Every allowed runtime rethrow requires rooted outcome custody and original catcher restoration; managed error identity and setjmp-safe frame storage remain source obligations"; }
 part refinement2 : RefinementSpec { attribute :>> key = "exit"; attribute :>> qntScope = "acquirePin;acquireReader;markUnknown;settleUnknown;releasePin;releaseReader;requestShrink;deferShrink;drainForeign;commitStorageMove;acknowledgeStorage;loseStorageReply;permitExit"; attribute :>> leanScope = "rootsAloneCannotExit;unknownStorageBlocks;exitNeedsGuard"; attribute :>> sourceDuty = "Prepare common effective topology before processor_count changes; foreign producer closure is a receipt assumption, not modeled arbitrary destructor execution"; }
 part refinement3 : RefinementSpec { attribute :>> key = "reclaim"; attribute :>> qntScope = "vote;publishRoster;finishTopologyTail;convergeRetained;disableInterrupts;cleanupInertRc;invokeExit;joinSucceeded;joinUnresolved;reuseSlot"; attribute :>> leanScope = "nonzeroVoteRequired;tailReceiptRequiresEverySender;joinUnknownCannotReuse;vmCannotCloseWhileOutcomeRoot;netBenefit"; attribute :>> sourceDuty = "Topology sender-tail/retained convergence, source cleanup paths and OS stop receipt refine separately; current procedural queue cleanup is not destruction of all sync facilities"; }
 part def PriorSpec { attribute key : String; attribute path : String; attribute invariant : String; attribute qntAction : String; attribute leanLemma : String; attribute condition : String; }
 part prior0 : PriorSpec { attribute :>> key = "strong-receipt"; attribute :>> path = "models/build/ffi_scan_ready_handoff.qnt"; attribute :>> invariant = "safe"; attribute :>> qntAction = "publishReady"; attribute :>> leanLemma = "readinessNotReturn"; attribute :>> condition = "Previous parked root handoff now needs actual sync-op participant and completion-guard integration; product simulation remains open"; }
 part prior1 : PriorSpec { attribute :>> key = "membership"; attribute :>> path = "models/gambit/gc_sync_membership.qnt"; attribute :>> invariant = "safe"; attribute :>> qntAction = "enterGc"; attribute :>> leanLemma = "loopReturnRequiresReset"; attribute :>> condition = "Existing model separates old GC population, final acknowledgement and resize; this study adds source loop and native guard obligations"; }
 part prior2 : PriorSpec { attribute :>> key = "cleanup-join"; attribute :>> path = "models/gambit/cleanup_resize_error_contract.qnt"; attribute :>> invariant = "safe"; attribute :>> qntAction = "reuseSlot"; attribute :>> leanLemma = "joinUnknownCannotReuse"; attribute :>> condition = "Reduced processor_count is not OS exit evidence; new generation reuse requires known join, independent of storage already freed by its owner"; }
 part prior3 : PriorSpec { attribute :>> key = "round-tail"; attribute :>> path = "models/gambit/sync_retirement_round_closure.qnt"; attribute :>> invariant = "safe"; attribute :>> qntAction = "convergeRetained"; attribute :>> leanLemma = "tailReceiptRequiresEverySender"; attribute :>> condition = "Old-tree sender tails and retained-tree convergence are not implied by worker exit alone; finite all-sender receipt here is stronger than a proved minimal source cut"; }
 part def GateSpec { attribute key : String; attribute qualified : Boolean; attribute condition : String; }
 part gate0 : GateSpec { attribute :>> key = "producer-closure"; attribute :>> qualified = false; attribute :>> condition = "Native root/error/result frames, foreign destructor producers and late FFI admission require complete source schemas and closure"; }
 part gate1 : GateSpec { attribute :>> key = "vm-ownership"; attribute :>> qualified = false; attribute :>> condition = "PSTATE storage and still/RC capacity move need acknowledged VM ownership; VM itself must retain heap and scan facilities until outcomes/foreign roots drain; unknown teardown may quarantine the whole VM"; }
 part gate2 : GateSpec { attribute :>> key = "gc-seal"; attribute :>> qualified = false; attribute :>> condition = "Root stop must retain a serviceable real sync-op participant; current selection/reset/NOOP/tree and direct resize GC need full source refinement"; }
 part gate3 : GateSpec { attribute :>> key = "scan-coverage"; attribute :>> qualified = false; attribute :>> condition = "Provisional frames, nonzero RC and rooted error channels are proposed adapters; generated root maps and actual relocation remain unqualified"; }
 part gate4 : GateSpec { attribute :>> key = "retirement"; attribute :>> qualified = false; attribute :>> condition = "Collective preflight, complete foreign release closure and sender-tail/retained convergence must precede resource retirement and slot reuse"; }
 part gate5 : GateSpec { attribute :>> key = "source-replacement"; attribute :>> qualified = false; attribute :>> condition = "Stable C guards, common effective topology, distinct cleanup permits and cleanup_rc interception remain unimplemented"; }
 part gate6 : GateSpec { attribute :>> key = "platform"; attribute :>> qualified = false; attribute :>> condition = "ISO C synchronization, setjmp/catcher ABI, OS exit/join receipts and inherited host registration remain unqualified"; }
 part def CensusSpec { attribute key : String; attribute anchor : String; attribute condition : String; attribute status : String; attribute qntAction : String; attribute leanLemma : String; }
 part census0 : CensusSpec { attribute :>> key = "requester-entry"; attribute :>> anchor = "setup.c:1132-1151,1182-1198"; attribute :>> condition = "Processor-1 allocating request raises VM sync interrupt and executes selected operation loop; locks needed by that loop are released before join"; attribute :>> status = "source-entry-closed"; attribute :>> qntAction = "requestSync"; attribute :>> leanLemma = "readinessNotReturn"; }
 part census1 : CensusSpec { attribute :>> key = "peer-service"; attribute :>> anchor = "setup.c:1117-1128,781-801"; attribute :>> condition = "Other processors enter service_sync_op; nonzero processor keeps servicing even after Scheme run returns"; attribute :>> status = "source-path-closed; fairness-open"; attribute :>> qntAction = "join"; attribute :>> leanLemma = "sleepingDoesNotParticipate"; }
 part census2 : CensusSpec { attribute :>> key = "old-roster"; attribute :>> anchor = "setup.c:557-568,900-915"; attribute :>> condition = "Tree captures current processor_count; resize nested GC happens before target membership commit; root-ready does not authorize excluding processor one"; attribute :>> status = "source-order-closed"; attribute :>> qntAction = "selectGc"; attribute :>> leanLemma = "rootsAloneCannotExit"; }
 part census3 : CensusSpec { attribute :>> key = "flag-reset"; attribute :>> anchor = "setup.c:1070-1089"; attribute :>> condition = "First selected round resets sync-op flag synchronously; later NOOP is needed before loop exit"; attribute :>> status = "source-order-closed"; attribute :>> qntAction = "resetFlag"; attribute :>> leanLemma = "loopReturnRequiresReset"; }
 part census4 : CensusSpec { attribute :>> key = "rc-payload"; attribute :>> anchor = "mem.c:3969-3986,6845-6850"; attribute :>> condition = "VM root adapter must scan processor-1 RC/provisional/error slots while owner executes selected GC; legacy processor-zero RC scan still needs replacement"; attribute :>> status = "source-adapter-open"; attribute :>> qntAction = "scanOwnerRoot"; attribute :>> leanLemma = "readinessNotReturn"; }
 part census5 : CensusSpec { attribute :>> key = "loop-result"; attribute :>> anchor = "setup.c:1101-1113"; attribute :>> condition = "Winning or combined request receives result and clears local request; callback return alone does not permit owner resume"; attribute :>> status = "source-order-closed"; attribute :>> qntAction = "acknowledgeRequest"; attribute :>> leanLemma = "gcReturnAloneInsufficient"; }
 part census6 : CensusSpec { attribute :>> key = "owner-restore"; attribute :>> anchor = "setup.c:819,1099-1113; c_intf.c:6535-6544"; attribute :>> condition = "After loop exit validate VM/PSTATE generation and reload moved roots; processor-zero deferred error may unwind instead of normal return"; attribute :>> status = "source-binding-open"; attribute :>> qntAction = "restoreOwner"; attribute :>> leanLemma = "loopReturnRequiresReset"; }
 part census7 : CensusSpec { attribute :>> key = "guard-error"; attribute :>> anchor = "setup.c:3383-3385; gambit.h.in:9981-9987"; attribute :>> condition = "Stable guard preserves original error and catcher destination through marker cleanup; exception data is handed to rooted VM outcome storage"; attribute :>> status = "source-catcher-open"; attribute :>> qntAction = "catchThrow"; attribute :>> leanLemma = "cleanupPreservesOriginal"; }
 part census8 : CensusSpec { attribute :>> key = "procedural-cleanup"; attribute :>> anchor = "setup.c:396-417,4665-4672"; attribute :>> condition = "cleanup_interrupts_pstate releases procedural interrupt queue; it does not itself demonstrate that all sync/GC facilities were disabled"; attribute :>> status = "source-scope-closed; new-admission-open"; attribute :>> qntAction = "disableInterrupts"; attribute :>> leanLemma = "exitNeedsGuard"; }
 part census9 : CensusSpec { attribute :>> key = "foreign-and-rc"; attribute :>> anchor = "mem.c:4432-4450,684-699,4933-4934"; attribute :>> condition = "free_still_objs may call release_foreign before bulk RC cleanup; arbitrary foreign effects must close or transfer while old owner still serviceable"; attribute :>> status = "source-producer-open"; attribute :>> qntAction = "drainForeign"; attribute :>> leanLemma = "unknownStorageBlocks"; }
 part census10 : CensusSpec { attribute :>> key = "topology-tail"; attribute :>> anchor = "setup.c:517-524,649-699,962-978"; attribute :>> condition = "Message publication unlocks before signal tail; common roster result and old sender lifetime are separate from worker receipt or join"; attribute :>> status = "source-tail-refinement-open"; attribute :>> qntAction = "finishTopologyTail"; attribute :>> leanLemma = "tailReceiptRequiresEverySender"; }
 part census11 : CensusSpec { attribute :>> key = "global-cleanup"; attribute :>> anchor = "setup.c:932-933,950,978,4843-4863"; attribute :>> condition = "Live shrink, unactivated rollback, global shutdown and cleanup_mem_vmstate wrapper need distinct permissions; VM wrapper destroys scan facilities before processor-zero memory cleanup, requiring whole-VM preflight"; attribute :>> status = "source-callers-closed; contracts-open"; attribute :>> qntAction = "reuseSlot"; attribute :>> leanLemma = "joinUnknownCannotReuse"; }
 part def SettleSpec { attribute key : String; attribute anchor : String; attribute condition : String; attribute status : String; attribute qntAction : String; attribute leanLemma : String; }
 part settle0 : SettleSpec { attribute :>> key = "ready-to-dispatch"; attribute :>> anchor = "setup.c:1117-1151"; attribute :>> condition = "Stopped mutator retains dispatcher service and old roster identity; OS sleep without service is rejected"; attribute :>> status = "conditional-model-closed"; attribute :>> qntAction = "join"; attribute :>> leanLemma = "sleepingDoesNotParticipate"; }
 part settle1 : SettleSpec { attribute :>> key = "gc-to-noop"; attribute :>> anchor = "setup.c:1068-1113"; attribute :>> condition = "Return of garbage_collect_pstate precedes request result/NOOP loop completion; owner root reload follows loop return"; attribute :>> status = "conditional-model-closed"; attribute :>> qntAction = "returnSync"; attribute :>> leanLemma = "gcReturnAloneInsufficient"; }
 part settle2 : SettleSpec { attribute :>> key = "catcher-and-marker"; attribute :>> anchor = "gambit.h.in:9981-9987; c_intf.c:6555-6561"; attribute :>> condition = "Restore old catcher and invalidate only initialized marker; completion guard records primary outcome before propagation"; attribute :>> status = "source-exit-coverage-open"; attribute :>> qntAction = "settleGuard"; attribute :>> leanLemma = "cleanupPreservesOriginal"; }
 part settle3 : SettleSpec { attribute :>> key = "outcome-and-root"; attribute :>> anchor = "setup.c:3383-3385; mem.c:4933-4934"; attribute :>> condition = "VM custodian accepts rooted error/result and remaining resources before guard frame withdrawal; pin/readers may delay storage free after rethrow"; attribute :>> status = "conditional-model-closed"; attribute :>> qntAction = "handoffOutcome"; attribute :>> leanLemma = "rethrowNeedsOutcomeRoot"; }
 part settle4 : SettleSpec { attribute :>> key = "storage-and-foreign"; attribute :>> anchor = "mem.c:4432-4450,684-699"; attribute :>> condition = "Acknowledge native storage ownership and foreign producer closure before topological removal; lost reply does not grant cleanup permission"; attribute :>> status = "source-transfer-open"; attribute :>> qntAction = "permitExit"; attribute :>> leanLemma = "unknownStorageBlocks"; }
 part settle5 : SettleSpec { attribute :>> key = "tree-and-admission"; attribute :>> anchor = "setup.c:517-524,649-699"; attribute :>> condition = "All participants observe effective roster; sender tails and retained convergence precede teardown; no local target-count veto after commit"; attribute :>> status = "source-round-refinement-open"; attribute :>> qntAction = "convergeRetained"; attribute :>> leanLemma = "tailReceiptRequiresEverySender"; }
 part settle6 : SettleSpec { attribute :>> key = "exit-and-generation"; attribute :>> anchor = "setup.c:932-978"; attribute :>> condition = "Owner may free only inert remainder; observed known join permits OS/PSTATE generation reuse, ignored/unknown join does not"; attribute :>> status = "platform-open"; attribute :>> qntAction = "reuseSlot"; attribute :>> leanLemma = "joinUnknownCannotReuse"; }
 attribute workspaceCount : Integer = 2;
 attribute participantCount : Integer = 2;
 attribute actualAdmitted : Boolean = false;
 part history : GambitAssuranceRouting::ModelNeed { ref part :>> owner = GambitBuildAssurance::planner.component; attribute :>> obligationId = "SGC-H"; attribute :>> kind = "interleaving"; attribute :>> subjectPath = "models/build/syncop_guard_custody.qnt"; attribute :>> subjectScope = "syncop_guard_custody:Test$"; attribute :>> premise = "Conditional participant/guard/cleanup research; actual tree, root adapters, catcher and teardown require source/platform refinement"; }
 part induction : GambitAssuranceRouting::ModelNeed { ref part :>> owner = GambitBuildAssurance::planner.component; attribute :>> obligationId = "SGC-I"; attribute :>> kind = "induction"; attribute :>> subjectPath = "models/build/SyncOpGuardCustody.lean"; attribute :>> subjectScope = "SyncOpGuardCustody:readinessNotReturn;sleepingDoesNotParticipate;gcReturnAloneInsufficient;internalGcCannotConsumeRequest;loopReturnRequiresReset;cleanupPreservesOriginal;rethrowNeedsOutcomeRoot;collectiveUnwindMustWait;rootsAloneCannotExit;unknownStorageBlocks;exitNeedsGuard;pinBlocksWithdrawal;vmCannotCloseWhileOutcomeRoot;nonzeroVoteRequired;tailReceiptRequiresEverySender;joinUnknownCannotReuse;vmCannotCloseWhileOutcomeRoot;netBenefit"; attribute :>> premise = "Conditional participant/guard/cleanup research; actual tree, root adapters, catcher and teardown require source/platform refinement"; }
 part source : GambitAssuranceRouting::ModelNeed { ref part :>> owner = GambitBuildAssurance::planner.component; attribute :>> obligationId = "SGC-S"; attribute :>> kind = "source-refinement"; attribute :>> subjectPath = "dev/architecture/toolchain/syncop-guard-custody-design.org"; attribute :>> subjectScope = "SGC-S:source"; attribute :>> premise = "Conditional participant/guard/cleanup research; actual tree, root adapters, catcher and teardown require source/platform refinement"; }
 part platform : GambitAssuranceRouting::ModelNeed { ref part :>> owner = GambitBuildAssurance::planner.component; attribute :>> obligationId = "SGC-E"; attribute :>> kind = "environment-refinement"; attribute :>> subjectPath = "dev/architecture/toolchain/syncop-guard-custody-design.org"; attribute :>> subjectScope = "SGC-E:platform"; attribute :>> premise = "Conditional participant/guard/cleanup research; actual tree, root adapters, catcher and teardown require source/platform refinement"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = FfiScanReadyHandoff::source; }
}
