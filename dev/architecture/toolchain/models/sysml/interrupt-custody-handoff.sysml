package InterruptCustodyHandoff {
 private import ScalarValues::*;
 part def Contract { attribute key : String; attribute anchor : String; attribute actionName : String; attribute lemmaName : String; attribute guardName : String; attribute duty : String; attribute status : String; }
 part contract0 : Contract { attribute :>> key = "derived-credit"; attribute :>> anchor = "setup.c:206-242"; attribute :>> actionName = "claim"; attribute :>> lemmaName = "claimPreserves"; attribute :>> guardName = "s.c[i]==1"; attribute :>> duty = "Reserve consumer custody before exchanging pending into active batch; clear is not callback completion"; attribute :>> status = "split native refinement open"; }
 part contract1 : Contract { attribute :>> key = "target-accept"; attribute :>> anchor = "os_setup.c:3044-3049; setup.c:66-92"; attribute :>> actionName = "accept"; attribute :>> lemmaName = "acceptCovered"; attribute :>> guardName = "s.open"; attribute :>> duty = "Successful producer admission pins the immutable target domain before descriptor access; Close denies only new entrants"; attribute :>> status = "gate ABI and target-cut open"; }
 part contract2 : Contract { attribute :>> key = "pending-publish"; attribute :>> anchor = "setup.c:86-90"; attribute :>> actionName = "publish"; attribute :>> lemmaName = "publishPreserves"; attribute :>> guardName = "s.p[i]==1"; attribute :>> duty = "Accepted producer may publish after Close; stable domain owns pending until claim or exclusive coordinator drain"; attribute :>> status = "no per-publication lease allocation"; }
 part contract3 : Contract { attribute :>> key = "storage-commit"; attribute :>> anchor = "setup.c:4834-4878; mem.c:6852-6862"; attribute :>> actionName = "retireVm"; attribute :>> lemmaName = "retirementRequiresClosure"; attribute :>> guardName = "drained"; attribute :>> duty = "Retire after producer gate closed and drained, consumer gate sealed and drained, pending empty, writer and root custody settled"; attribute :>> status = "native/root receipts inherited open"; }
 part contract4 : Contract { attribute :>> key = "claim-seal"; attribute :>> anchor = "setup.c:1049-1113"; attribute :>> actionName = "sealClaims"; attribute :>> lemmaName = "sealNeedsProducerDrain"; attribute :>> guardName = "producers==Set()"; attribute :>> duty = "Seal normal claim admission only after producers drain; existing reservations finish; coordinator owns residual pending"; attribute :>> status = "new shutdown protocol"; }
 part contract5 : Contract { attribute :>> key = "activation-root"; attribute :>> anchor = "_kernel.c:12430-12449; mem.c:6511-6537"; attribute :>> actionName = "rootCapture"; attribute :>> lemmaName = "captureRoots"; attribute :>> guardName = "s.c[i]==3"; attribute :>> duty = "Vector load to registered activation root is a no-safepoint interval; collection scans and rewrites that slot"; attribute :>> status = "generated PointId and root map open"; }
 part contract6 : Contract { attribute :>> key = "vector-writer"; attribute :>> anchor = "_kernel.scm:1473-1476; gambit.h.in:4231,5482"; attribute :>> actionName = "commitVector"; attribute :>> lemmaName = "rootedReplacementStable"; attribute :>> guardName = "s.frozen"; attribute :>> duty = "Root setter argument before queueing; close external admission; derived request holds parent claim until rendezvous commit; preserve selected roots"; attribute :>> status = "all writer and alias closure open"; }
 part contract7 : Contract { attribute :>> key = "gc-move"; attribute :>> anchor = "mem.c:3490-3508,6511-6645,6852-6862"; attribute :>> actionName = "moveGc"; attribute :>> lemmaName = "relocationPreserves"; attribute :>> guardName = "noTemp"; attribute :>> duty = "All participating contexts parked with no unrooted load; rewrite global vector, selected activations and queued setter argument"; attribute :>> status = "STW abstraction only"; }
 part def Gain { attribute key : String; attribute avoided : String; attribute added : String; attribute condition : String; }
 part gain0 : Gain { attribute :>> key = "native-operations"; attribute :>> avoided = "No lease object or counted signal queue allocation per raise; one domain-owned pending bit per target reason"; attribute :>> added = "Per accepted callback: one gate snapshot load, admission CAS, pending RMW, wake OR and exit decrement"; attribute :>> condition = "Four RMW plus one load is a proposed uncontended protocol count, not a native instruction or latency bound"; }
 part gain1 : Gain { attribute :>> key = "claim-operations"; attribute :>> avoided = "Coalescing remains one claim per pending epoch; no extra callback reduction versus current flag"; attribute :>> added = "Per normal claim attempt: one gate snapshot load, reserve CAS, pending exchange and reservation release; rooted-slot stores"; attribute :>> condition = "Three RMW plus one load; empty claims still pay; unknown outcomes retain rather than replay"; }
 part gain2 : Gain { attribute :>> key = "vector-gc"; attribute :>> avoided = "Reuse VM globals, register/saved/frame scanning and sync-op participation rather than inventing unmanaged Scheme pointers"; attribute :>> added = "One rooted request slot per outstanding setter; rendezvous per committed write; scan k extra activation slots and q queued argument slots"; attribute :>> condition = "k excludes existing scanned registers and frames; rendezvous cost grows with roster; setter frequency and GC cost must be included"; }
 part gain3 : Gain { attribute :>> key = "net-benefit"; attribute :>> avoided = "Unifies target lifecycle, pending claim and root handoff contracts in modern generated C"; attribute :>> added = "Two admission domains, coordinator takeover, exceptional settlement, source and platform proof obligations"; attribute :>> condition = "No speed gain established; benefit requires avoided real lifetime failures or eliminated work to exceed additional atomics, rendezvous and scans; Zig does not remove these obligations"; }
 part def Gate { attribute key : String; attribute qualified : Boolean; attribute duty : String; }
 part gate0 : Gate { attribute :>> key = "gate-encoding"; attribute :>> qualified = false; attribute :>> duty = "Coherent lock-free signal-safe admission representation; target acceptance cut and no-wrap proof"; }
 part gate1 : Gate { attribute :>> key = "split-publication"; attribute :>> qualified = false; attribute :>> duty = "Publish-before-exit and reserve-before-claim instruction-level simulation; SC alone does not transact several objects"; }
 part gate2 : Gate { attribute :>> key = "root-materialization"; attribute :>> qualified = false; attribute :>> duty = "Exact generated PointId, register spill, frame map, saved and continuation proof for current configuration"; }
 part gate3 : Gate { attribute :>> key = "vector-writer-closure"; attribute :>> qualified = false; attribute :>> duty = "All private/global vector aliases, direct FFI writes and synchronous setter exception/continuation semantics"; }
 part gate4 : Gate { attribute :>> key = "gc-rendezvous"; attribute :>> qualified = false; attribute :>> duty = "Actual roster and sync-op precedence; collector exclusion and no allocation/checkpoint in unrooted interval"; }
 part gate5 : Gate { attribute :>> key = "completion-custody"; attribute :>> qualified = false; attribute :>> duty = "Unknown enqueue/callback result and continuation-retained roots; no post-effect blind retry or cyclic shutdown wait"; }
 part gate6 : Gate { attribute :>> key = "platform-retirement"; attribute :>> qualified = false; attribute :>> duty = "Darwin atomic lowering, signal safety, native/OS joins, inherited host attestation; no native admission"; }
 part history : GambitAssuranceRouting::ModelNeed { ref part :>> owner = GambitBuildAssurance::planner.component; attribute :>> obligationId = "ICH-H"; attribute :>> kind = "interleaving"; attribute :>> subjectPath = "models/build/interrupt_custody_handoff.qnt"; attribute :>> subjectScope = "safe: two publishers, two normal claimers and exclusive drainer; moving selected and writer roots"; attribute :>> premise = "Model preservation is conditional; source, relaxed-memory and platform simulation remain open"; }
 part induction : GambitAssuranceRouting::ModelNeed { ref part :>> owner = GambitBuildAssurance::planner.component; attribute :>> obligationId = "ICH-I"; attribute :>> kind = "induction"; attribute :>> subjectPath = "models/build/InterruptCustodyHandoff.lean"; attribute :>> subjectScope = "custody step and history preservation plus root relocation and closure premises"; attribute :>> premise = "Model preservation is conditional; source, relaxed-memory and platform simulation remain open"; }
 part source : GambitAssuranceRouting::ModelNeed { ref part :>> owner = GambitBuildAssurance::planner.component; attribute :>> obligationId = "ICH-S"; attribute :>> kind = "source-refinement"; attribute :>> subjectPath = "dev/architecture/toolchain/interrupt-custody-handoff-design.org"; attribute :>> subjectScope = "native acceptance and flag consumer; ordinary vector writes; generated R1 and GC root consumers"; attribute :>> premise = "Model preservation is conditional; source, relaxed-memory and platform simulation remain open"; }
 part platform : GambitAssuranceRouting::ModelNeed { ref part :>> owner = GambitBuildAssurance::planner.component; attribute :>> obligationId = "ICH-E"; attribute :>> kind = "environment-refinement"; attribute :>> subjectPath = "dev/architecture/toolchain/interrupt-custody-handoff-design.org"; attribute :>> subjectScope = "SC atomics, lock-free signal gate, source memory locations, roster participation and native retirement"; attribute :>> premise = "Model preservation is conditional; source, relaxed-memory and platform simulation remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SigintDeliverySemantics::source; }
 part def ContractDependency { ref part dependent : Contract; ref part prerequisite : Contract; attribute reason : String; }
 part edge0 : ContractDependency { ref part :>> dependent = contract2; ref part :>> prerequisite = contract1; attribute :>> reason = "Accepted producer remains pinned through final publication"; }
 part edge1 : ContractDependency { ref part :>> dependent = contract0; ref part :>> prerequisite = contract2; attribute :>> reason = "Claim transfers published domain custody"; }
 part edge2 : ContractDependency { ref part :>> dependent = contract4; ref part :>> prerequisite = contract2; attribute :>> reason = "No pending producer may outlive claim seal"; }
 part edge3 : ContractDependency { ref part :>> dependent = contract3; ref part :>> prerequisite = contract4; attribute :>> reason = "Retirement requires sealed and drained claimers"; }
 part edge4 : ContractDependency { ref part :>> dependent = contract3; ref part :>> prerequisite = contract0; attribute :>> reason = "Active batch is not completed by pending clear"; }
 part edge5 : ContractDependency { ref part :>> dependent = contract5; ref part :>> prerequisite = contract0; attribute :>> reason = "Claimed work retains target while materializing handler root"; }
 part edge6 : ContractDependency { ref part :>> dependent = contract6; ref part :>> prerequisite = contract5; attribute :>> reason = "Replacement cannot erase selected activation root"; }
 part edge7 : ContractDependency { ref part :>> dependent = contract7; ref part :>> prerequisite = contract5; attribute :>> reason = "Moving collection rewrites selected root"; }
 part edge8 : ContractDependency { ref part :>> dependent = contract7; ref part :>> prerequisite = contract6; attribute :>> reason = "Queued setter argument is also scanned"; }
 part edge9 : ContractDependency { ref part :>> dependent = contract3; ref part :>> prerequisite = contract7; attribute :>> reason = "Root and collector ownership settle before target retirement"; }
}
