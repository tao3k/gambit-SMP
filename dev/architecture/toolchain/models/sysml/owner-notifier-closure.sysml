package OwnerNotifierClosure {
 private import ScalarValues::*;
 part def Holder { attribute key : String; attribute anchor : String; attribute actualEdge : String; attribute requiredChange : String; }
 part holder0 : Holder { attribute :>> key = "stream-and-lexer"; attribute :>> anchor = "stream.ss:19,40-65; lexer.ss:20,42-44,54-105"; attribute :>> actualEdge = "token-stream owns char-stream/buffer/grammar/EOF; char-stream owns port/location/history; no owner token currently exists"; attribute :>> requiredChange = "Every governed resource-capable view must carry the proposed managed owner anchor; detached token/chunk views retain only their own necessary owners"; }
 part holder1 : Holder { attribute :>> key = "parser-control"; attribute :>> anchor = "lang-reader.ss:131-216,218-260; defparser.ss:17-40"; attribute :>> actualEdge = "Active parser paths and ordinary K/E closures reference stream, rules, tokens and port; captured continuation retains actual surviving frames"; attribute :>> requiredChange = "Trace exact live control/capture paths without cloning token/list-tail identity or assuming every lexical variable survives tail-call elimination"; }
 part holder2 : Holder { attribute :>> key = "readenv-and-handler"; attribute :>> anchor = "runtime/syntax.ss:255-266; _io.scm:12694-12698"; attribute :>> actualEdge = "readenv owns input port/current readtable and invokes dynamically selected handler with readenv"; attribute :>> requiredChange = "Reader/handler aliases that can use old input must protect its owner; opaque mutable/native handlers retain legacy ownership"; }
 part holder3 : Holder { attribute :>> key = "exception-stacktrace"; attribute :>> anchor = "runtime/error.ss:16-20,37-43,67-72; runtime/syntax.ss:71,169-171"; attribute :>> actualEdge = "StackTrace holds continuation; raise can capture before catch graft and replacement raise can capture again"; attribute :>> requiredChange = "Include original/replacement/secondary errors and captures in owner coverage; notification code must not invoke error/logging paths that capture testator"; }
 part holder4 : Holder { attribute :>> key = "native-rc"; attribute :>> anchor = "mem.c:703-826,3969-3986; os_dyn.c:748-769,1047-1053"; attribute :>> actualEdge = "Registered RC data strongly marks a Scheme procedure, whose environment may retain reader/control objects"; attribute :>> requiredChange = "Real borrow/pending work retains roots; notifier/control payload is rootless and cannot wait for a GC notice while itself rooting the owner"; }
 part holder5 : Holder { attribute :>> key = "will-action-and-frame"; attribute :>> anchor = "mem.c:4039-4064; _kernel.scm:2082-2116; _nonstd.scm:1874-1895"; attribute :>> actualEdge = "Will action is strong; execution clears will fields but passes testator through active action and dispatcher locals; public execution does not require GC selection"; attribute :>> requiredChange = "Private will/action handles, GC dispatch provenance, noncapturing/nonpublishing leaf, normal return and frame/root retirement proof before sealing"; }
 part holder6 : Holder { attribute :>> key = "jobs-and-controller"; attribute :>> anchor = "_kernel.scm:1925-1939,2071-2077,2153-2156; std/db/sqlite.ss:42-45,64-67"; attribute :>> actualEdge = "GC job FIFO retains registered thunks; execute-jobs does not clear registry; SQLite shows module-level finalizer actions but not restricted notifier qualification"; attribute :>> requiredChange = "Prefer one owner-independent drain job and per-owner rootless slots; no job/controller closure may capture owner or testator"; }
 part def Gate { attribute key : String; attribute qualified : Boolean; attribute condition : String; }
 part gate0 : Gate { attribute :>> key = "holder-coverage"; attribute :>> qualified = false; attribute :>> condition = "Source-bound alias/control graph covers every resource-capable view, including raw aliases and all processor native roots"; }
 part gate1 : Gate { attribute :>> key = "action-closure"; attribute :>> qualified = false; attribute :>> condition = "Action, weak handle, job and controller do not escape or strongly capture owner; top-level naming alone is insufficient"; }
 part gate2 : Gate { attribute :>> key = "dispatch-provenance"; attribute :>> qualified = false; attribute :>> condition = "Private GC dequeue ticket binds owner generation/close epoch; public will-execute or direct action call cannot forge selection evidence"; }
 part gate3 : Gate { attribute :>> key = "nonresurrection"; attribute :>> qualified = false; attribute :>> condition = "No public will-testator access, owner publication, user call, capture, or error-stacktrace route through notifier; generic user will semantics preserved elsewhere"; }
 part gate4 : Gate { attribute :>> key = "callback-frame-exit"; attribute :>> qualified = false; attribute :>> condition = "Distinguish action return, dispatcher frame/root retirement and winding/escape; GVM/GC root-map or equivalent source/native proof required"; }
 part gate5 : Gate { attribute :>> key = "rootless-mailbox"; attribute :>> qualified = false; attribute :>> condition = "Slot reserved before registration, no allocation/user callback on notice path, stable rootless payload and control-storage lifetime through unknown replies"; }
 part gate6 : Gate { attribute :>> key = "notice-to-release-refinement"; attribute :>> qualified = false; attribute :>> condition = "Sealed notice is only one contribution to RA admission/drain/settlement join; native ordering, thread affinity and grace remain open"; }
 part def Gain { attribute key : String; attribute avoided : String; attribute added : String; attribute condition : String; }
 part gain0 : Gain { attribute :>> key = "persistent-jobs"; attribute :>> avoided = "If otherwise one job per owner: W persistent owner-capturing GC-job registrations can become one owner-independent drain registration"; attribute :>> added = "O(W) rootless preallocated per-owner slots plus dispatcher scan/queue work"; attribute :>> condition = "Proposed organization, not a claimed existing gxi implementation or speed measurement; no owner backedges in drain closure"; }
 part gain1 : Gain { attribute :>> key = "finalization-allocation"; attribute :>> avoided = "No mandatory event allocation/error formatting while notifier holds testator"; attribute :>> added = "Registration-time slot reservation, failure rollback, normal-return/frame-exit and publication protocol"; attribute :>> condition = "No allocation on notification path is an admission premise to prove, not a property provided by Zig or a function name"; }
 part gain2 : Gain { attribute :>> key = "retention-and-latency"; attribute :>> avoided = "Prevent self-retention and invalid release from manual execution, resurrection or early notification"; attribute :>> added = "Separate selected/prepared/returned/retired/sealed states and identities; captured errors may retain resources indefinitely"; attribute :>> condition = "No bounded GC latency, callback-return deadline or throughput gain inferred"; }
 part gain3 : Gain { attribute :>> key = "native-baseline"; attribute :>> avoided = "Prior reset/ignored-string/rootless-ack gains remain distinct, not counted again"; attribute :>> added = "Same semantic root/publication support in modern C or Zig"; attribute :>> condition = "Modern C remains mandatory; no uniquely Zig net gain established here"; }
 attribute ownerGeneration : Integer = 17;
 attribute actualAdmitted : Boolean = false;
 part def NoticeEvidence { attribute requested : Boolean; attribute holderCoverage : Boolean; attribute privateClosure : Boolean; attribute gcTicket : Boolean; attribute normalReturn : Boolean; attribute frameRetired : Boolean; attribute noCaptureOrPublication : Boolean; attribute rootlessPayload : Boolean; attribute identityMatches : Boolean; }
 requirement def NoticeLaw { subject evidence : NoticeEvidence; require constraint { not evidence.requested or (evidence.holderCoverage and evidence.privateClosure and evidence.gcTicket and evidence.normalReturn and evidence.frameRetired and evidence.noCaptureOrPublication and evidence.rootlessPayload and evidence.identityMatches) } }
 part history : GambitAssuranceRouting::ModelNeed { ref part :>> owner = GambitBuildAssurance::scheduler.component; attribute :>> obligationId = "NC-H"; attribute :>> kind = "interleaving"; attribute :>> subjectPath = "models/build/owner_notifier_closure.qnt"; attribute :>> subjectScope = "owner_notifier_closure:Test$"; attribute :>> premise = "Finite holder/provenance/action/dispatcher/notice protocol and adversarial manual execution, capture, resurrection and exception paths; GC/source root-map predicates assumed"; }
 part induction : GambitAssuranceRouting::ModelNeed { ref part :>> owner = GambitBuildAssurance::scheduler.component; attribute :>> obligationId = "NC-I"; attribute :>> kind = "induction"; attribute :>> subjectPath = "models/build/OwnerNotifierClosure.lean"; attribute :>> subjectScope = "OwnerNotifierClosure:clearSlotsKeepsLocal;manualHasNoTicket;preparedNotSealed;afterIsNotReturn;jobBackedge;validNeedsExit;captureRejects;stablePayload"; attribute :>> premise = "Conditional root/frame, provenance, winding and rootless-notice kernels; no actual GC root-map, alias closure or nonallocating leaf proof"; }
 part source : GambitAssuranceRouting::ModelNeed { ref part :>> owner = GambitBuildAssurance::scheduler.component; attribute :>> obligationId = "NC-S"; attribute :>> kind = "source-refinement"; attribute :>> subjectPath = "dev/architecture/toolchain/owner-notifier-closure-design.org"; attribute :>> subjectScope = "NC-S:notifier-closure-source"; attribute :>> premise = "Actual holder shapes, public manual execution, resurrection test and persistent job sources derived; proposed owner anchor/private leaf/control-root retirement refinement open"; }
 part platform : GambitAssuranceRouting::ModelNeed { ref part :>> owner = GambitBuildAssurance::scheduler.component; attribute :>> obligationId = "NC-E"; attribute :>> kind = "environment-refinement"; attribute :>> subjectPath = "dev/architecture/toolchain/owner-notifier-closure-design.org"; attribute :>> subjectScope = "NC-E:notifier-frame-native"; attribute :>> premise = "GC dispatch ticket, GVM/root-map exit cut, preallocated mailbox publication, native callback ABI, owner executor and storage grace unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = StreamReleaseAuthority::source; }
}
