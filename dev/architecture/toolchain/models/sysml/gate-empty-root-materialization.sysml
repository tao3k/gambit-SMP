package GateEmptyRootMaterialization {
 private import ScalarValues::*;
 part def Contract { attribute key : String; attribute anchor : String; attribute actionName : String; attribute lemmaName : String; attribute guardName : String; attribute duty : String; attribute status : String; }
 part contract0 : Contract { attribute :>> key = "derived-credit"; attribute :>> anchor = "setup.c:206-242; prior interrupt custody contract"; attribute :>> actionName = "exchangePending"; attribute :>> lemmaName = "reservationBeforeExchange"; attribute :>> guardName = "s.cs[i]==1"; attribute :>> duty = "Consumer CAS reservation precedes pending exchange; reservation survives seal and covers empty-result completion"; attribute :>> status = "C replacement pending"; }
 part contract1 : Contract { attribute :>> key = "producer-release"; attribute :>> anchor = "setup.c:66-92; gambit.h.in:11014-11026"; attribute :>> actionName = "decrementP"; attribute :>> lemmaName = "lastDecrement"; attribute :>> guardName = "s.ps[i]==3"; attribute :>> duty = "Pending and wake publication plus last target access precede release decrement; all gate modifications remain RMW within incarnation"; attribute :>> status = "SC profile candidate"; }
 part contract2 : Contract { attribute :>> key = "producer-zero"; attribute :>> anchor = "setup.c:4834-4878; proposed native gate"; attribute :>> actionName = "observePZero"; attribute :>> lemmaName = "closedZeroQualified"; attribute :>> guardName = "not(s.po)"; attribute :>> duty = "Observe closed zero through acquire and valid RMW frontier; open zero and last contributor alone are insufficient"; attribute :>> status = "C memory refinement conditional"; }
 part contract3 : Contract { attribute :>> key = "storage-commit"; attribute :>> anchor = "setup.c:4834-4878; mem.c:6852-6862"; attribute :>> actionName = "issueEmpty"; attribute :>> lemmaName = "finalNeedsBothGates"; attribute :>> guardName = "emptyEligible"; attribute :>> duty = "Both gates closed and drained; exclusive pending inspection after all claims/root handoffs; native empty receipt is not whole VM retirement"; attribute :>> status = "parent root/native obligations retained"; }
 part contract4 : Contract { attribute :>> key = "consumer-reserve"; attribute :>> anchor = "setup.c:206-242; proposed native gate"; attribute :>> actionName = "reserveC"; attribute :>> lemmaName = "closedGateDenies"; attribute :>> guardName = "s.seenCo[i]"; attribute :>> duty = "One coherent open/count snapshot and CAS; close invalidates stale snapshot; reservation count not inferred from pending bit"; attribute :>> status = "bounded count; no incarnation reuse"; }
 part contract5 : Contract { attribute :>> key = "root-spill"; attribute :>> anchor = "gambit.h.in:6802-6818,7082-7098; _kernel.c:12400-12449"; attribute :>> actionName = "spill"; attribute :>> lemmaName = "spillMaterializes"; attribute :>> guardName = "s.cs[i]==3"; attribute :>> duty = "R1 may be a C local and SELF may become live carrier; spill selected carrier before GC and publish correct root location"; attribute :>> status = "actual configuration and restore graph open"; }
 part contract6 : Contract { attribute :>> key = "root-reload"; attribute :>> anchor = "_kernel.scm:55-72,274-283,1971-1977; mem.c:6511-6537"; attribute :>> actionName = "reload"; attribute :>> lemmaName = "reloadFresh"; attribute :>> guardName = "s.cs[i]==4 or s.cs[i]==5"; attribute :>> duty = "Collector rewrites scanned slot; reload live carrier before use; local R1 is not automatically a collector root"; attribute :>> status = "source witness not native admission"; }
 part contract7 : Contract { attribute :>> key = "consumer-zero"; attribute :>> anchor = "setup.c:1049-1113; prior interrupt custody contract"; attribute :>> actionName = "observeCZero"; attribute :>> lemmaName = "activeClaimBlocksFinal"; attribute :>> guardName = "s.cc==0"; attribute :>> duty = "Seal consumer gate only after producer closed-zero receipt; observe drained reservations and preserve deferred/unknown/root custody"; attribute :>> status = "whole roster and root closure open"; }
 part def Gain { attribute key : String; attribute avoided : String; attribute added : String; attribute condition : String; }
 part gain0 : Gain { attribute :>> key = "gate-cost"; attribute :>> avoided = "No per-signal heap or lease object; pending remains one coalescible domain slot"; attribute :>> added = "Per accepted callback: one snapshot load and four RMWs including wake; normal claim: one snapshot and three RMWs"; attribute :>> condition = "Protocol counts only; SC is initial profile and weaker order is not admitted; existing flags already coalesce"; }
 part gain1 : Gain { attribute :>> key = "final-check"; attribute :>> avoided = "Ordered gate drains establish a stable native pending inspection instead of repeated speculative emptiness"; attribute :>> added = "Two close RMWs, at least two qualifying acquire observations, drain polling and exclusive pending inspection"; attribute :>> condition = "No single zero or last decrement licenses VM cleanup; root/native/roster receipts remain necessary"; }
 part gain2 : Gain { attribute :>> key = "root-cost"; attribute :>> avoided = "Reuse generated register/saved/frame scanning and existing spill-reload mechanisms"; attribute :>> added = "For k live local carriers: k slot stores and k reloads per materialization round, plus actual frame/host overhead"; attribute :>> condition = "Direct PSTATE registers need no extra local spill; k comes from effective masks/configuration, not an assumed constant"; }
 part gain3 : Gain { attribute :>> key = "net-condition"; attribute :>> avoided = "Eliminate unsafe acceptance/retirement gaps and redundant competing final drain decisions"; attribute :>> added = "Atomic admission, root completion and preserved unknown-result custody; source and memory-model proof work"; attribute :>> condition = "No runtime speed or build-time benefit established; modern C is sufficient to express the contract; Zig removes none of these obligations"; }
 part def Gate { attribute key : String; attribute qualified : Boolean; attribute duty : String; }
 part gate0 : Gate { attribute :>> key = "coherent-gates"; attribute :>> qualified = false; attribute :>> duty = "Exact unsigned fields, non-wrap, lock-free signal ABI and no ordinary stores/reset within a live incarnation"; }
 part gate1 : Gate { attribute :>> key = "c-memory"; attribute :>> qualified = false; attribute :>> duty = "C execution graph, modification-order/read-from and release/acquire proof; SC QNT is not a full C memory model"; }
 part gate2 : Gate { attribute :>> key = "closure-census"; attribute :>> qualified = false; attribute :>> duty = "All producers, normal/derived writers, roots and cleanup requests covered by frozen parent domains"; }
 part gate3 : Gate { attribute :>> key = "r1-configuration"; attribute :>> qualified = false; attribute :>> duty = "Actual generated artifact and effective host/local-register/argument-register settings bound to profile"; }
 part gate4 : Gate { attribute :>> key = "restore-closure"; attribute :>> qualified = false; attribute :>> duty = "R1 to SELF, same-host edges, frames, saved values, exceptions and continuation captures all mapped"; }
 part gate5 : Gate { attribute :>> key = "final-authority"; attribute :>> qualified = false; attribute :>> duty = "No old target access after decrement; native empty receipt separated from root/VM/OS retirement authority"; }
 part gate6 : Gate { attribute :>> key = "platform"; attribute :>> qualified = false; attribute :>> duty = "Darwin signal safety and atomic lowering plus inherited host attestation remain unresolved; no native testing"; }
 part history : GambitAssuranceRouting::ModelNeed { ref part :>> owner = GambitBuildAssurance::planner.component; attribute :>> obligationId = "GER-H"; attribute :>> kind = "interleaving"; attribute :>> subjectPath = "models/build/gate_empty_root_materialization.qnt"; attribute :>> subjectScope = "safe: SC atomic event order, coherent CAS snapshots, two gate drains, exclusive final pending and local spill move reload"; attribute :>> premise = "Conditional formal reasoning; no implemented gate, C axiomatic simulation or native profile acceptance"; }
 part induction : GambitAssuranceRouting::ModelNeed { ref part :>> owner = GambitBuildAssurance::planner.component; attribute :>> obligationId = "GER-I"; attribute :>> kind = "induction"; attribute :>> subjectPath = "models/build/GateEmptyRootMaterialization.lean"; attribute :>> subjectScope = "conditional release-frontier history preservation, closed zero and root materialization lemmas"; attribute :>> premise = "Conditional formal reasoning; no implemented gate, C axiomatic simulation or native profile acceptance"; }
 part source : GambitAssuranceRouting::ModelNeed { ref part :>> owner = GambitBuildAssurance::planner.component; attribute :>> obligationId = "GER-S"; attribute :>> kind = "source-refinement"; attribute :>> subjectPath = "dev/architecture/toolchain/gate-empty-root-materialization-design.org"; attribute :>> subjectScope = "actual R1 and SELF host/save/GC/reload seams; proposed gate instruction cuts versus old flag path"; attribute :>> premise = "Conditional formal reasoning; no implemented gate, C axiomatic simulation or native profile acceptance"; }
 part platform : GambitAssuranceRouting::ModelNeed { ref part :>> owner = GambitBuildAssurance::planner.component; attribute :>> obligationId = "GER-E"; attribute :>> kind = "environment-refinement"; attribute :>> subjectPath = "dev/architecture/toolchain/gate-empty-root-materialization-design.org"; attribute :>> subjectScope = "C atomic order and signal ABI, effective generated configuration, final authority and root restoration closure"; attribute :>> premise = "Conditional formal reasoning; no implemented gate, C axiomatic simulation or native profile acceptance"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = InterruptCustodyHandoff::source; }
 part def ContractDependency { ref part dependent : Contract; ref part prerequisite : Contract; attribute reason : String; }
 part edge0 : ContractDependency { ref part :>> dependent = contract2; ref part :>> prerequisite = contract1; attribute :>> reason = "Last release observation must carry all prior contributions"; }
 part edge1 : ContractDependency { ref part :>> dependent = contract7; ref part :>> prerequisite = contract2; attribute :>> reason = "Producer drain precedes consumer seal"; }
 part edge2 : ContractDependency { ref part :>> dependent = contract0; ref part :>> prerequisite = contract4; attribute :>> reason = "Reservation exists before exchange"; }
 part edge3 : ContractDependency { ref part :>> dependent = contract5; ref part :>> prerequisite = contract0; attribute :>> reason = "Claim ownership spans root materialization"; }
 part edge4 : ContractDependency { ref part :>> dependent = contract6; ref part :>> prerequisite = contract5; attribute :>> reason = "Reload must read relocated scanned slot"; }
 part edge5 : ContractDependency { ref part :>> dependent = contract7; ref part :>> prerequisite = contract6; attribute :>> reason = "Last consumer exit follows root and restoration settlement"; }
 part edge6 : ContractDependency { ref part :>> dependent = contract3; ref part :>> prerequisite = contract2; attribute :>> reason = "Final inspection excludes future publication"; }
 part edge7 : ContractDependency { ref part :>> dependent = contract3; ref part :>> prerequisite = contract7; attribute :>> reason = "Final inspection excludes normal claimers"; }
 part edge8 : ContractDependency { ref part :>> dependent = contract3; ref part :>> prerequisite = contract0; attribute :>> reason = "Pending empty cannot hide claimed active batch"; }
 part edge9 : ContractDependency { ref part :>> dependent = contract5; ref part :>> prerequisite = contract4; attribute :>> reason = "Reserved target remains alive while carrier is local"; }
}
