package BundleRootPublication {
 private import ScalarValues::*;
 part def RootSpec { attribute key : String; attribute anchor : String; attribute condition : String; }
 part root0 : RootSpec { attribute :>> key = "scheme-roots"; attribute :>> anchor = "mem.c:6511-6537,6591-6645,6852-6858"; attribute :>> condition = "Scheme global/continuation/register/saved roots are actual scan paths; service-owned root graph must remain in their qualified closure"; }
 part root1 : RootSpec { attribute :>> key = "rc-scope"; attribute :>> anchor = "mem.c:277,306,723-739,3969-3986,6845-6849"; attribute :>> condition = "RC list is per processor but inspected strong phase invokes mark_rc only at processor 0; arbitrary worker RC coverage remains unqualified"; }
 part root2 : RootSpec { attribute :>> key = "rc-mutation"; attribute :>> anchor = "mem.c:760-825"; attribute :>> condition = "RC retain/release and data assignment are plain operations; do not treat them as thread-safe handle leases or immutable publication"; }
 part root3 : RootSpec { attribute :>> key = "allocator"; attribute :>> anchor = "mem.c:1487-1497,1647-1648,1742-1813"; attribute :>> condition = "Native still allocation may GC/fail; initialize body before next allocation; native pair/vector input constraints forbid arbitrary movable arguments"; }
 part root4 : RootSpec { attribute :>> key = "ffi-gap"; attribute :>> anchor = "c_intf.c:6511-6546"; attribute :>> condition = "Real stack-marker creator allocates before assigning proc_or_false and carries a GC-protection TODO; copying this order does not prove candidate input safety"; }
 part def PublicationSpec { attribute key : String; attribute anchor : String; attribute condition : String; }
 part publication0 : PublicationSpec { attribute :>> key = "root-store"; attribute :>> anchor = "proposed service; mem.c:6591-6645"; attribute :>> condition = "Service Scheme root graph and future VM-scoped root registry must cover bundle graph/receipts; native descriptor carries identity not raw movable address"; }
 part publication1 : PublicationSpec { attribute :>> key = "reserve-initialize"; attribute :>> anchor = "mem.c:703-719,1487-1497"; attribute :>> condition = "Reserve empty scanned slot, protect allocation inputs, initialize each new object before next GC-capable step, then attach through qualified slot store"; }
 part publication2 : PublicationSpec { attribute :>> key = "release-acquire"; attribute :>> anchor = "gambit.h.in:11014-11026; proposed contract"; attribute :>> condition = "Release publication/acquire observation orders native metadata; separate scanner/lifetime proof still required"; }
 part publication3 : PublicationSpec { attribute :>> key = "pin-retire"; attribute :>> anchor = "proposed contract; mem.c:760-791"; attribute :>> condition = "Read descriptor and acquire its lifetime lease under same retirement gate; load then addref is a reclaim gap"; }
 part publication4 : PublicationSpec { attribute :>> key = "fallback"; attribute :>> anchor = "os_thread.c:715-735,788-794; gambit.h.in:11054-11082"; attribute :>> condition = "Emulated CAS uses mutex but barrier fallback is empty; sequential branch is not concurrent publication qualification"; }
 part def RouteSpec { attribute key : String; attribute anchor : String; attribute qntAction : String; attribute leanLemma : String; attribute condition : String; }
 part route0 : RouteSpec { attribute :>> key = "candidate"; attribute :>> anchor = "mem.c:1487-1497,1742-1813"; attribute :>> qntAction = "initialize"; attribute :>> leanLemma = "initializedBeforePublish"; attribute :>> condition = "Input roots precede allocation and complete initialization precedes next collection; failure keeps old authority"; }
 part route1 : RouteSpec { attribute :>> key = "scan"; attribute :>> anchor = "mem.c:3969-3986,6591-6645,6845-6858"; attribute :>> qntAction = "collect"; attribute :>> leanLemma = "gcKeepsRoot"; attribute :>> condition = "Selected root slots scanned and updated for exactly the owner VM; no unsupported worker RC shortcut"; }
 part route2 : RouteSpec { attribute :>> key = "publish"; attribute :>> anchor = "gambit.h.in:11014-11026; proposed seam"; attribute :>> qntAction = "publishBundle"; attribute :>> leanLemma = "receiptCommit"; attribute :>> condition = "Root transfer and bundle/index/receipt publication form one protocol cut before acknowledgement"; }
 part route3 : RouteSpec { attribute :>> key = "borrow"; attribute :>> anchor = "mem.c:760-791; proposed seam"; attribute :>> qntAction = "borrow"; attribute :>> leanLemma = "gateBlocksRetire"; attribute :>> condition = "Acquire native handle plus root lifetime under gate; GC-aware dereference resolves relocated slot"; }
 part route4 : RouteSpec { attribute :>> key = "unwind"; attribute :>> anchor = "c_intf.c:6511-6546; _thread.scm:4623-4639"; attribute :>> qntAction = "abortCandidate"; attribute :>> leanLemma = "abortKeepsAuthority"; attribute :>> condition = "Failed/unknown/captured attempts preserve root holders; restoration cannot undo committed receipt"; }
 part def GainSpec { attribute key : String; attribute avoided : String; attribute added : String; attribute condition : String; }
 part gain0 : GainSpec { attribute :>> key = "shared-root-graph"; attribute :>> avoided = "Per-consumer duplication of identical immutable compiler input graphs"; attribute :>> added = "Scanned root store, handles, retired snapshots and leases"; attribute :>> condition = "Actual avoided copying must exceed root/index/retention overhead; roots alone are correctness, not speedup"; }
 part gain1 : GainSpec { attribute :>> key = "independent-contexts"; attribute :>> avoided = "Global cross-context serialization after ownership migration"; attribute :>> added = "VM/root domain identity, reader gates and qualified participant mapping"; attribute :>> condition = "Independent ready work must exceed coordination; current nonzero RC coverage not assumed"; }
 part gain2 : GainSpec { attribute :>> key = "failure-recovery"; attribute :>> avoided = "Reexecuting qualified macro work to recover a committed result"; attribute :>> added = "Exact receipt retention, root custody and authoritative resolution"; attribute :>> condition = "No effect rollback/retry on unknown commit; retention and unresolved tasks can negate gains"; }
 part def RefinementSpec { attribute key : String; attribute qntScope : String; attribute leanScope : String; attribute sourceDuty : String; }
 part refinement0 : RefinementSpec { attribute :>> key = "allocation"; attribute :>> qntScope = "reserveRoot;allocateCandidate;initialize"; attribute :>> leanScope = "initializedBeforePublish;abortKeepsAuthority"; attribute :>> sourceDuty = "Actual allocation/root/map/error refinement including uninitialized-object interval"; }
 part refinement1 : RefinementSpec { attribute :>> key = "collection"; attribute :>> qntScope = "collect;dereference"; attribute :>> leanScope = "gcKeepsRoot;handleResolution"; attribute :>> sourceDuty = "GC relocation and selected scanner domain; no raw address retention across safepoints"; }
 part refinement2 : RefinementSpec { attribute :>> key = "publication"; attribute :>> qntScope = "publishBundle;borrow;retireOld"; attribute :>> leanScope = "receiptCommit;gateBlocksRetire;releaseAcquirePremise"; attribute :>> sourceDuty = "Real C happens-before plus retirement/root scanning participation"; }
 part refinement3 : RefinementSpec { attribute :>> key = "control"; attribute :>> qntScope = "loseAck;saveCandidate;resumeAfter"; attribute :>> leanScope = "retainedCustody;noRollback;costPositive"; attribute :>> sourceDuty = "Native/continuation roots, unknown owner and measured work/span/memory"; }
 part def GateSpec { attribute key : String; attribute qualified : Boolean; attribute condition : String; }
 part gate0 : GateSpec { attribute :>> key = "root-domain"; attribute :>> qualified = false; attribute :>> condition = "Every service/FFI/worker holder assigned to a live scanned VM root domain"; }
 part gate1 : GateSpec { attribute :>> key = "init-source"; attribute :>> qualified = false; attribute :>> condition = "Allocation input protection, object initialization and failure cleanup source refinement"; }
 part gate2 : GateSpec { attribute :>> key = "c-memory"; attribute :>> qualified = false; attribute :>> condition = "Release/acquire/gate protocol proven for actual configured sync branch"; }
 part gate3 : GateSpec { attribute :>> key = "relocation"; attribute :>> qualified = false; attribute :>> condition = "GC-aware slot resolution and root registration/retirement synchronization"; }
 part gate4 : GateSpec { attribute :>> key = "continuation"; attribute :>> qualified = false; attribute :>> condition = "Saved PCs, native borrowers, unknown result and root retirement closure"; }
 part gate5 : GateSpec { attribute :>> key = "retirement"; attribute :>> qualified = false; attribute :>> condition = "Old RC/global/mutable bundle authorities retired only after all consumers migrate"; }
 part gate6 : GateSpec { attribute :>> key = "platform"; attribute :>> qualified = false; attribute :>> condition = "Host attestation, native qualification and measured benefit remain independent"; }
 attribute workspaceCount : Integer = 2;
 attribute actualAdmitted : Boolean = false;
 part history : GambitAssuranceRouting::ModelNeed { ref part :>> owner = GambitBuildAssurance::planner.component; attribute :>> obligationId = "BR-H"; attribute :>> kind = "interleaving"; attribute :>> subjectPath = "models/build/bundle_root_publication.qnt"; attribute :>> subjectScope = "bundle_root_publication:Test$"; attribute :>> premise = "Conditional root/visibility/lifetime protocol; source GC/C memory refinement remains open"; }
 part induction : GambitAssuranceRouting::ModelNeed { ref part :>> owner = GambitBuildAssurance::planner.component; attribute :>> obligationId = "BR-I"; attribute :>> kind = "induction"; attribute :>> subjectPath = "models/build/BundleRootPublication.lean"; attribute :>> subjectScope = "BundleRootPublication:gcKeepsRoot;initializedBeforePublish;receiptCommit;gateBlocksRetire;abortKeepsAuthority;handleResolution;releaseAcquirePremise;retainedCustody;noRollback;costPositive"; attribute :>> premise = "Conditional root/visibility/lifetime protocol; source GC/C memory refinement remains open"; }
 part source : GambitAssuranceRouting::ModelNeed { ref part :>> owner = GambitBuildAssurance::planner.component; attribute :>> obligationId = "BR-S"; attribute :>> kind = "source-refinement"; attribute :>> subjectPath = "dev/architecture/toolchain/bundle-root-publication-design.org"; attribute :>> subjectScope = "BR-S:source"; attribute :>> premise = "Conditional root/visibility/lifetime protocol; source GC/C memory refinement remains open"; }
 part platform : GambitAssuranceRouting::ModelNeed { ref part :>> owner = GambitBuildAssurance::planner.component; attribute :>> obligationId = "BR-E"; attribute :>> kind = "environment-refinement"; attribute :>> subjectPath = "dev/architecture/toolchain/bundle-root-publication-design.org"; attribute :>> subjectScope = "BR-E:platform"; attribute :>> premise = "Conditional root/visibility/lifetime protocol; source GC/C memory refinement remains open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = RegistryAtomicCommit::source; }
}
