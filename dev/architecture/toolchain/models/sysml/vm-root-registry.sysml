package VMRootRegistry {
 private import ScalarValues::*;
 part def CallerSpec { attribute key : String; attribute anchor : String; attribute condition : String; }
 part caller0 : CallerSpec { attribute :>> key = "rc-register"; attribute :>> anchor = "mem.c:277,306,723-754,3969-3986,6845-6849"; attribute :>> condition = "Current PSTATE registration versus processor-0 RC scan is not a VM-wide root contract"; }
 part caller1 : CallerSpec { attribute :>> key = "c-closure"; attribute :>> anchor = "os_dyn.c:744-769,1047-1058; c_intf.c:6511-6546"; attribute :>> condition = "Real C closure stores Scheme proc in RC data; callback self and marker protection remain separate qualified boundaries"; }
 part caller2 : CallerSpec { attribute :>> key = "tcl-client"; attribute :>> anchor = "examples/tcltk/tcltk.scm:188-194,298-326"; attribute :>> condition = "Tcl retains RC client data plus still vector; deletion releases both; scan observations alone do not prove current object death"; }
 part caller3 : CallerSpec { attribute :>> key = "resize-exit"; attribute :>> anchor = "setup.c:918-978,4665-4706; mem.c:4432-4449,4659,4928-4934"; attribute :>> condition = "Processor setup/cleanup initializes/frees RC chains; committed VM roots and their still-object storage must survive creator processor; root registration alone is insufficient"; }
 part caller4 : CallerSpec { attribute :>> key = "gc-phase"; attribute :>> anchor = "mem.c:6591-6645,6845-6858,7002-7038"; attribute :>> condition = "Existing GC phase barriers and root partitions are source seams; registry membership is not processor_count"; }
 part def ProtocolSpec { attribute key : String; attribute anchor : String; attribute condition : String; }
 part protocol0 : ProtocolSpec { attribute :>> key = "register"; attribute :>> anchor = "proposed VM contract; mem.c:723-754"; attribute :>> condition = "Reserve initialized slot; producer root protects payload until atomic VM-root/index receipt handoff; wrong VM rejects"; }
 part protocol1 : ProtocolSpec { attribute :>> key = "seal"; attribute :>> anchor = "proposed contract; mem.c:7002-7016"; attribute :>> condition = "Close new permits, drain/cancel preaccepted updates and dereferences, then freeze slot membership and scanner tickets"; }
 part protocol2 : ProtocolSpec { attribute :>> key = "scan"; attribute :>> anchor = "mem.c:3984,6626,6642-6644; proposed adapter"; attribute :>> condition = "Exactly covered slots scanned via mutable root locations; relocation updates values; registered readers hold lifetime not raw addresses"; }
 part protocol3 : ProtocolSpec { attribute :>> key = "retire"; attribute :>> anchor = "proposed contract; mem.c:760-791,4928-4934"; attribute :>> condition = "Close slot admission; retain until scanner tickets, update permits, read leases and unresolved receipt holders all retire"; }
 part protocol4 : ProtocolSpec { attribute :>> key = "processor-lifetime"; attribute :>> anchor = "setup.c:930-978; proposed VM contract"; attribute :>> condition = "Committed slot ownership belongs to VM, not creator PSTATE; local-only pending roots and still storage need separate handoff before processor cleanup"; }
 part def RouteSpec { attribute key : String; attribute anchor : String; attribute qntAction : String; attribute leanLemma : String; attribute condition : String; }
 part route0 : RouteSpec { attribute :>> key = "registration"; attribute :>> anchor = "mem.c:723-754; os_dyn.c:764-769"; attribute :>> qntAction = "commitRegister"; attribute :>> leanLemma = "vmMatch"; attribute :>> condition = "All publishers retain producer root until slot and registration receipt are authoritative"; }
 part route1 : RouteSpec { attribute :>> key = "quiescence"; attribute :>> anchor = "mem.c:7002-7016; proposed GC entry seam"; attribute :>> qntAction = "startScan"; attribute :>> leanLemma = "acceptedUpdateMayDrain"; attribute :>> condition = "Closing prevents new writers but permits accepted writers to finish before snapshot freeze"; }
 part route2 : RouteSpec { attribute :>> key = "coverage"; attribute :>> anchor = "mem.c:3969-3986,6845-6858"; attribute :>> qntAction = "endScan"; attribute :>> leanLemma = "coverageUnion"; attribute :>> condition = "Nonzero processor roots included by VM membership; scanner assignment exactly covers snapshot"; }
 part route3 : RouteSpec { attribute :>> key = "retirement"; attribute :>> anchor = "mem.c:760-791,4928-4934; proposed epoch gate"; attribute :>> qntAction = "reclaim"; attribute :>> leanLemma = "scanBlocksReclaim"; attribute :>> condition = "Reader retirement alone cannot unlink a slot still held by current GC snapshot or unknown acknowledgement"; }
 part route4 : RouteSpec { attribute :>> key = "resize"; attribute :>> anchor = "setup.c:918-978; mem.c:4432-4449"; attribute :>> qntAction = "departOne"; attribute :>> leanLemma = "creatorExitPreservesSlot"; attribute :>> condition = "PSTATE departure does not revoke VM slot identity; backing storage needs separate handoff"; }
 part def GainSpec { attribute key : String; attribute avoided : String; attribute added : String; attribute condition : String; }
 part gain0 : GainSpec { attribute :>> key = "vm-root-ownership"; attribute :>> avoided = "Per-processor root transfer tied to compiler task migration after VM handoff"; attribute :>> added = "VM registry, payload admission, epoch/scanner tickets and GC slot adapters"; attribute :>> condition = "Only committed VM-owned slots decouple from processor exit; no elimination of root scanning"; }
 part gain1 : GainSpec { attribute :>> key = "stable-scan"; attribute :>> avoided = "Repeated uncertain RC-chain discovery and unqualified worker coverage"; attribute :>> added = "Closed snapshot, partition/coverage evidence and update/deref draining"; attribute :>> condition = "Exact membership can bound scan work; quiescence delays and slot bookkeeping count"; }
 part gain2 : GainSpec { attribute :>> key = "independent-service"; attribute :>> avoided = "Global processor-zero affinity for newly managed compiler holders"; attribute :>> added = "Per-VM handle/lease identity and callback/native migration"; attribute :>> condition = "Parallel benefit requires actual independent work and all native writers admitted; no automatic multicore gain"; }
 part def RefinementSpec { attribute key : String; attribute qntScope : String; attribute leanScope : String; attribute sourceDuty : String; }
 part refinement0 : RefinementSpec { attribute :>> key = "root"; attribute :>> qntScope = "prepareRegister;commitRegister;departOne"; attribute :>> leanScope = "vmMatch;creatorExitPreservesSlot;storageBlocksExit"; attribute :>> sourceDuty = "Actual C closure/Tcl/native producer/root transfer and teardown simulation"; }
 part refinement1 : RefinementSpec { attribute :>> key = "phase"; attribute :>> qntScope = "beginUpdate;closeGC;commitUpdate;startScan"; attribute :>> leanScope = "acceptedUpdateMayDrain;noNewWriter;coverageUnion"; attribute :>> sourceDuty = "Actual barrier/participant/slot freeze relation and independent worker coverage"; }
 part refinement2 : RefinementSpec { attribute :>> key = "reclaim"; attribute :>> qntScope = "requestRetire;reclaim;ackRegister"; attribute :>> leanScope = "scanBlocksReclaim;leaseBlocksReclaim;unknownBlocksReclaim"; attribute :>> sourceDuty = "All leases/GC tickets/unknown outcomes and root registration lifetime closed"; }
 part refinement3 : RefinementSpec { attribute :>> key = "value"; attribute :>> qntScope = "readSlot;endScan"; attribute :>> leanScope = "slotAfterScan;costPositive"; attribute :>> sourceDuty = "Moving reference restoration, C memory order and work/span/retention measurement"; }
 part def GateSpec { attribute key : String; attribute qualified : Boolean; attribute condition : String; }
 part gate0 : GateSpec { attribute :>> key = "producer-closure"; attribute :>> qualified = false; attribute :>> condition = "Resolved C closure/Tcl/FFI/compiler publishers and borrowers completely admitted"; }
 part gate1 : GateSpec { attribute :>> key = "vm-ownership"; attribute :>> qualified = false; attribute :>> condition = "Actual per-VM slots and registration receipts survive PSTATE exit with source protection"; }
 part gate2 : GateSpec { attribute :>> key = "gc-seal"; attribute :>> qualified = false; attribute :>> condition = "New permit closure and preaccepted update/deref draining cannot deadlock with actual GC"; }
 part gate3 : GateSpec { attribute :>> key = "scan-coverage"; attribute :>> qualified = false; attribute :>> condition = "Registry snapshot and scanner partitions cover every admitted nonzero root and update correct slot"; }
 part gate4 : GateSpec { attribute :>> key = "retirement"; attribute :>> qualified = false; attribute :>> condition = "Epoch tickets/read leases/unresolved outcomes/continuations/native holds fully drained"; }
 part gate5 : GateSpec { attribute :>> key = "source-replacement"; attribute :>> qualified = false; attribute :>> condition = "Old RC/global root authorities retired only after all required users migrate"; }
 part gate6 : GateSpec { attribute :>> key = "platform"; attribute :>> qualified = false; attribute :>> condition = "C weak memory/root maps/host attestation/native qualification and measured benefit remain open"; }
 attribute workspaceCount : Integer = 2;
 attribute actualAdmitted : Boolean = false;
 part history : GambitAssuranceRouting::ModelNeed { ref part :>> owner = GambitBuildAssurance::planner.component; attribute :>> obligationId = "VR-H"; attribute :>> kind = "interleaving"; attribute :>> subjectPath = "models/build/vm_root_registry.qnt"; attribute :>> subjectScope = "vm_root_registry:Test$"; attribute :>> premise = "Conditional VM root registry/epoch proof; actual source and native coverage remain open"; }
 part induction : GambitAssuranceRouting::ModelNeed { ref part :>> owner = GambitBuildAssurance::planner.component; attribute :>> obligationId = "VR-I"; attribute :>> kind = "induction"; attribute :>> subjectPath = "models/build/VMRootRegistry.lean"; attribute :>> subjectScope = "VMRootRegistry:vmMatch;acceptedUpdateMayDrain;noNewWriter;coverageUnion;scanBlocksReclaim;leaseBlocksReclaim;unknownBlocksReclaim;creatorExitPreservesSlot;storageBlocksExit;slotAfterScan;costPositive"; attribute :>> premise = "Conditional VM root registry/epoch proof; actual source and native coverage remain open"; }
 part source : GambitAssuranceRouting::ModelNeed { ref part :>> owner = GambitBuildAssurance::planner.component; attribute :>> obligationId = "VR-S"; attribute :>> kind = "source-refinement"; attribute :>> subjectPath = "dev/architecture/toolchain/vm-root-registry-design.org"; attribute :>> subjectScope = "VR-S:source"; attribute :>> premise = "Conditional VM root registry/epoch proof; actual source and native coverage remain open"; }
 part platform : GambitAssuranceRouting::ModelNeed { ref part :>> owner = GambitBuildAssurance::planner.component; attribute :>> obligationId = "VR-E"; attribute :>> kind = "environment-refinement"; attribute :>> subjectPath = "dev/architecture/toolchain/vm-root-registry-design.org"; attribute :>> subjectScope = "VR-E:platform"; attribute :>> premise = "Conditional VM root registry/epoch proof; actual source and native coverage remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = BundleRootPublication::source; }
}
