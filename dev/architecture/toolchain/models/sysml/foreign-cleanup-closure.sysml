package ForeignCleanupClosure {
 private import ScalarValues::*;
 part def Contract { attribute key : String; attribute anchor : String; attribute actionName : String; attribute lemmaName : String; attribute duty : String; attribute status : String; }
 part contract0 : Contract { attribute :>> key = "capture"; attribute :>> anchor = "c_intf.c:1696-1707; mem.c:4403-4406"; attribute :>> actionName = "captureRoot"; attribute :>> lemmaName = "captureConserves"; attribute :>> duty = "Reserve native task and trace schema before wrapper invalidation/free; per-wrapper release right, not pointer identity"; attribute :>> status = "open capture adapter"; }
 part contract1 : Contract { attribute :>> key = "derived-credit"; attribute :>> anchor = "os_io.c:1886-1933,2011-2037"; attribute :>> actionName = "reserveChild"; attribute :>> lemmaName = "reserveConserves"; attribute :>> duty = "Accepted parent owns reserved child credit before publication; unknown publication cannot be replayed"; attribute :>> status = "conditional platform branches"; }
 part contract2 : Contract { attribute :>> key = "device-cursor"; attribute :>> anchor = "os_io.c:1625-1666"; attribute :>> actionName = "parkWait"; attribute :>> lemmaName = "waitRetainsCredit"; attribute :>> duty = "Detach, RD, WR and final release are distinct resumable phases; partial failure retains exact cursor"; attribute :>> status = "new managed adapter"; }
 part contract3 : Contract { attribute :>> key = "owner"; attribute :>> anchor = "os_io.c:973-978; setup.c:887-978"; attribute :>> actionName = "exitOwner"; attribute :>> lemmaName = "affinityBlocksExit"; attribute :>> duty = "PSTATE FDSET use is not arbitrary worker execution; old roster and wake-to-sync-op service remain available"; attribute :>> status = "open wait integration"; }
 part contract4 : Contract { attribute :>> key = "release-outcome"; attribute :>> anchor = "os_io.c:1603-1622; c_intf.c:1702-1707"; attribute :>> actionName = "terminalError"; attribute :>> lemmaName = "errorCanConsume"; attribute :>> duty = "Final release may free native self despite error; no raw-pointer retry based on status alone"; attribute :>> status = "source witnessed"; }
 part contract5 : Contract { attribute :>> key = "storage-commit"; attribute :>> anchor = "mem.c:684-699,4432-4450,4928-4966"; attribute :>> actionName = "commitLost"; attribute :>> lemmaName = "commitPreservesScanner"; attribute :>> duty = "At a safe epoch publish canonical RC/still owner, root adapter and capacity ledger together; lost reply leaves target owning"; attribute :>> status = "open source refinement"; }
 part contract6 : Contract { attribute :>> key = "accounting"; attribute :>> anchor = "mem.c:1570,1684,4410-4420,6804-6805"; attribute :>> actionName = "foldQuota"; attribute :>> lemmaName = "foldConserves"; attribute :>> duty = "RC bytes and still physical words/deferred quota are separate; no double census at transfer"; attribute :>> status = "open capacity integration"; }
 part contract7 : Contract { attribute :>> key = "vm-permit"; attribute :>> anchor = "mem.c:4938-4966; os_io.c:183-192"; attribute :>> actionName = "cleanupVm"; attribute :>> lemmaName = "vmRequiresGlobalClosure"; attribute :>> duty = "External ingress closed, child credit zero, outcomes/roots/readers drained, affinity and services settled before any facility teardown"; attribute :>> status = "conditional permit"; }
 part def Gain { attribute key : String; attribute avoided : String; attribute added : String; attribute condition : String; }
 part gain0 : Gain { attribute :>> key = "collector"; attribute :>> avoided = "B foreign callback invocations removed from collective sweep for admitted non-leaf hooks"; attribute :>> added = "B captures plus queue/owner dispatch and retained roots"; attribute :>> condition = "B callback waiting time may leave collective critical path; no bounded latency unless admitted profiles terminate"; }
 part gain1 : Gain { attribute :>> key = "storage"; attribute :>> avoided = "One canonical RC/still owner instead of source/target duplicate scan or census"; attribute :>> added = "One gated transfer, generation journal and leases"; attribute :>> condition = "For H moved domains, 0 uncovered domains and exactly H canonical scan/census entries; not a speed measurement"; }
 part gain2 : Gain { attribute :>> key = "closure"; attribute :>> avoided = "Zero ambiguous task replays after known consumed-error or unknown delivery"; attribute :>> added = "O(T+E+P) task/edge/owner records; O(1) credit operations per transition"; attribute :>> condition = "Saved duplicate work exceeds capture, dispatch, barriers and retention cost; arbitrary hooks may remain inline or rejected"; }
 part gain3 : Gain { attribute :>> key = "language"; attribute :>> avoided = "One modern C runtime contract serves Scheme generator and optional backends"; attribute :>> added = "C atomics, explicit tagged outcomes, generated profiles and state machines"; attribute :>> condition = "Zig does not remove root, effect, affinity, reclamation or termination proofs; no demonstrated incremental language benefit"; }
 part def Gate { attribute key : String; attribute qualified : Boolean; attribute duty : String; }
 part gate0 : Gate { attribute :>> key = "effect-profiles"; attribute :>> qualified = false; attribute :>> duty = "All hook origins, aliases and configuration-specific effects classified"; }
 part gate1 : Gate { attribute :>> key = "root-scanning"; attribute :>> qualified = false; attribute :>> duty = "Nonzero RC and target arena roots scanned/updated at every admitted GC epoch"; }
 part gate2 : Gate { attribute :>> key = "wait-roster"; attribute :>> qualified = false; attribute :>> duty = "Serviceable old roster, thread-affine completion and abort-to-dispatch integration"; }
 part gate3 : Gate { attribute :>> key = "atomic-handoff"; attribute :>> qualified = false; attribute :>> duty = "C synchronization plus scan/census linearization and lost-reply journal"; }
 part gate4 : Gate { attribute :>> key = "exit-coverage"; attribute :>> qualified = false; attribute :>> duty = "All supported exception, cancellation and continuation exits retain custody"; }
 part gate5 : Gate { attribute :>> key = "global-teardown"; attribute :>> qualified = false; attribute :>> duty = "I/O service lifetime, derived-work closure and retained-VM backpressure"; }
 part gate6 : Gate { attribute :>> key = "platform"; attribute :>> qualified = false; attribute :>> duty = "Actual Darwin/POSIX/OpenSSL selection, ABI and inherited host attestation"; }
 part history : GambitAssuranceRouting::ModelNeed { ref part :>> owner = GambitBuildAssurance::planner.component; attribute :>> obligationId = "FCC-H"; attribute :>> kind = "interleaving"; attribute :>> subjectPath = "models/build/foreign_cleanup_closure.qnt"; attribute :>> subjectScope = "safe: three rights, parent/child credit, old owner, unknown handoff"; attribute :>> premise = "Conditional formal model; no runtime admission or source simulation claimed"; }
 part induction : GambitAssuranceRouting::ModelNeed { ref part :>> owner = GambitBuildAssurance::planner.component; attribute :>> obligationId = "FCC-I"; attribute :>> kind = "induction"; attribute :>> subjectPath = "models/build/ForeignCleanupClosure.lean"; attribute :>> subjectScope = "credit conservation, scanner uniqueness, affinity, VM permit"; attribute :>> premise = "Conditional formal model; no runtime admission or source simulation claimed"; }
 part source : GambitAssuranceRouting::ModelNeed { ref part :>> owner = GambitBuildAssurance::planner.component; attribute :>> obligationId = "FCC-S"; attribute :>> kind = "source-refinement"; attribute :>> subjectPath = "dev/architecture/toolchain/foreign-cleanup-closure-design.org"; attribute :>> subjectScope = "actual release origins, phases and root/census adapters"; attribute :>> premise = "Conditional formal model; no runtime admission or source simulation claimed"; }
 part platform : GambitAssuranceRouting::ModelNeed { ref part :>> owner = GambitBuildAssurance::planner.component; attribute :>> obligationId = "FCC-E"; attribute :>> kind = "environment-refinement"; attribute :>> subjectPath = "dev/architecture/toolchain/foreign-cleanup-closure-design.org"; attribute :>> subjectScope = "C memory order, native profile and host attestation"; attribute :>> premise = "Conditional formal model; no runtime admission or source simulation claimed"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SyncOpGuardCustody::source; }

 part def ContractDependency { ref part dependent : Contract; ref part prerequisite : Contract; attribute reason : String; }
 part edge0 : ContractDependency { ref part :>> dependent = contract1; ref part :>> prerequisite = contract0; attribute :>> reason = "Child custody requires captured parent right"; }
 part edge1 : ContractDependency { ref part :>> dependent = contract2; ref part :>> prerequisite = contract0; attribute :>> reason = "Cursor must own native lifetime"; }
 part edge2 : ContractDependency { ref part :>> dependent = contract2; ref part :>> prerequisite = contract3; attribute :>> reason = "Wait resume requires attached execution owner"; }
 part edge3 : ContractDependency { ref part :>> dependent = contract2; ref part :>> prerequisite = contract4; attribute :>> reason = "Cursor result must distinguish native consumption"; }
 part edge4 : ContractDependency { ref part :>> dependent = contract5; ref part :>> prerequisite = contract0; attribute :>> reason = "Transfer requires rooted captured payload"; }
 part edge5 : ContractDependency { ref part :>> dependent = contract5; ref part :>> prerequisite = contract6; attribute :>> reason = "Scan and census authority commit together"; }
 part edge6 : ContractDependency { ref part :>> dependent = contract7; ref part :>> prerequisite = contract1; attribute :>> reason = "No accepted or reserved descendant debt"; }
 part edge7 : ContractDependency { ref part :>> dependent = contract7; ref part :>> prerequisite = contract3; attribute :>> reason = "Old roster and thread affinity settled"; }
 part edge8 : ContractDependency { ref part :>> dependent = contract7; ref part :>> prerequisite = contract4; attribute :>> reason = "No unresolved external residue"; }
 part edge9 : ContractDependency { ref part :>> dependent = contract7; ref part :>> prerequisite = contract5; attribute :>> reason = "Canonical storage acknowledged before teardown"; }
}
