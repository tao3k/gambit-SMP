package StrongClosureReceipt {
 private import ScalarValues::*;
 part def CallerSpec { attribute key : String; attribute anchor : String; attribute condition : String; }
 part caller0 : CallerSpec { attribute :>> key = "root-producers"; attribute :>> anchor = "mem.c:3454-3459,6511-6664,6843-6864"; attribute :>> condition = "Initial active credits cover each root walker before its first idle; p0-only VM/symbol/RC paths and all-processor frame/register/global paths have different coverage"; }
 part caller1 : CallerSpec { attribute :>> key = "private-copy"; attribute :>> anchor = "mem.c:3504-3505,3578-3663,3667-3813"; attribute :>> condition = "Forwarding can precede full payload copy; winner retains active credit through private alloc cursor, inline tail and captured-frame copying"; }
 part caller2 : CallerSpec { attribute :>> key = "chunk-publication"; attribute :>> anchor = "mem.c:3238-3306"; attribute :>> condition = "Private incomplete chunk need not enter FIFO; complete chunk publishes marker/link before visible tail; producer stays active through synchronous call"; }
 part caller3 : CallerSpec { attribute :>> key = "dequeue-and-scan"; attribute :>> anchor = "mem.c:4196-4204,4235-4383,6698-6727"; attribute :>> condition = "Dequeued chunk and still node remain scanner-frame custody until body/children/cursor advance complete; new private work requires local rescan"; }
 part caller4 : CallerSpec { attribute :>> key = "zero-and-return"; attribute :>> anchor = "mem.c:6738-6767,6864-6869,7014-7023"; attribute :>> condition = "Count zero observed under termination mutex closes covered work; waiters check zero before reacquiring credit; payload closure differs from all callback returns"; }
 part def ProtocolSpec { attribute key : String; attribute anchor : String; attribute condition : String; }
 part protocol0 : ProtocolSpec { attribute :>> key = "counted-root-closure"; attribute :>> anchor = "mem.c:3458-3459,6845-6864; proposed root census"; attribute :>> condition = "Freeze root/participant membership; close each root producer only after all admitted root slots seed accounted work; complete census remains separate from queue closure"; }
 part protocol1 : ProtocolSpec { attribute :>> key = "active-custody"; attribute :>> anchor = "mem.c:3578-3663,3794-3808,4324-4334"; attribute :>> condition = "A counted synchronous owner covers forwarding-visible copies, private initialized chunks and pending cursor writes; cannot go idle or exit with any such debt"; }
 part protocol2 : ProtocolSpec { attribute :>> key = "publication-handoff"; attribute :>> anchor = "mem.c:3280-3305,4348-4368,6717-6727"; attribute :>> condition = "Body/marker/link precede tail publication; source covers until queue acceptance or local scan, active thief owns after dequeue; parent completion never drops derived work"; }
 part protocol3 : ProtocolSpec { attribute :>> key = "strong-receipt"; attribute :>> anchor = "mem.c:6738-6767,6864; proposed epoch receipt"; attribute :>> condition = "Zero count plus complete ownership/root coverage and same-epoch synchronization permits strong-closure receipt; no new root/publication after terminal zero"; }
 part protocol4 : ProtocolSpec { attribute :>> key = "barrier-reuse"; attribute :>> anchor = "mem.c:6864-6869,7016; proposed classification insertion"; attribute :>> condition = "Returned worker may classify from certified closure before peers return; existing barrier waits for every classification; receipt does not authorize PSTATE/queue retirement"; }
 part def RouteSpec { attribute key : String; attribute anchor : String; attribute qntAction : String; attribute leanLemma : String; attribute condition : String; }
 part route0 : RouteSpec { attribute :>> key = "registration"; attribute :>> anchor = "mem.c:3454-3459,6845-6864"; attribute :>> qntAction = "closeRoots"; attribute :>> leanLemma = "openRootRequiresActive"; attribute :>> condition = "Root producer is part of initial credit population until admitted root traversal is complete"; }
 part route1 : RouteSpec { attribute :>> key = "custody"; attribute :>> anchor = "mem.c:3504-3663,4235-4383"; attribute :>> qntAction = "idle"; attribute :>> leanLemma = "idleCannotOwnDebt"; attribute :>> condition = "Idle guard requires no private copy, cursor, unpublished/queued work or dequeued frame responsibility"; }
 part route2 : RouteSpec { attribute :>> key = "coverage"; attribute :>> anchor = "mem.c:6738-6767"; attribute :>> qntAction = "issueReceipt"; attribute :>> leanLemma = "zeroActiveCloses"; attribute :>> condition = "Exact active count and coverage of every strong work source imply generated-work closure; full root census separately required"; }
 part route3 : RouteSpec { attribute :>> key = "publication"; attribute :>> anchor = "mem.c:3280-3305,6717-6727"; attribute :>> qntAction = "dequeue"; attribute :>> leanLemma = "custodyAtDequeue"; attribute :>> condition = "Transfer to an active scanner preserves custody; no independent publisher credit needed only under synchronous lifetime coverage"; }
 part route4 : RouteSpec { attribute :>> key = "retirement"; attribute :>> anchor = "mem.c:6864-6869,7016; setup.c:1068-1105"; attribute :>> qntAction = "reuseBarrier"; attribute :>> leanLemma = "oneReturnNotAll"; attribute :>> condition = "Payload closure permits classification but resource/callback retirement needs full return and barrier obligations"; }
 part def GainSpec { attribute key : String; attribute avoided : String; attribute added : String; attribute condition : String; }
 part gain0 : GainSpec { attribute :>> key = "reuse-rendezvous"; attribute :>> avoided = "An extra all-classifier rendezvous if existing strong/weak barrier can carry decisions"; attribute :>> added = "Root/work coverage proof, epoch receipt and classification acknowledgement; existing barrier still mandatory"; attribute :>> condition = "Zero extra barrier only after strong-return closure is qualified; local emptiness is insufficient"; }
 part gain1 : GainSpec { attribute :>> key = "reuse-worker-credit"; attribute :>> avoided = "Per-copy or per-chunk independent publication atomics for synchronous covered work"; attribute :>> added = "Explicit ownership and idle discipline; private cursor/tail/copy obligations remain even if represented only in proof"; attribute :>> condition = "No extra runtime counter is implied by proof state; detached producers require credit handoff or separate tracking"; }
 part gain2 : GainSpec { attribute :>> key = "preserve-boundaries"; attribute :>> avoided = "Treating count zero as root census or all-callback retirement"; attribute :>> added = "Typed root/closure/return/phase credentials and unsupported-profile refusal"; attribute :>> condition = "Correctness foundation rather than proven GC speedup; root omissions and native memory-order gaps still prevent full qualification"; }
 part def RefinementSpec { attribute key : String; attribute qntScope : String; attribute leanScope : String; attribute sourceDuty : String; }
 part refinement0 : RefinementSpec { attribute :>> key = "roots"; attribute :>> qntScope = "seedRoot;closeRoots;issueReceipt"; attribute :>> leanScope = "openRootRequiresActive;incompleteCensusBlocks"; attribute :>> sourceDuty = "Root maps, actual global partitions, nonzero native holders and stable VM domain admission; producer traversal completion is not coverage completeness"; }
 part refinement1 : RefinementSpec { attribute :>> key = "work"; attribute :>> qntScope = "claim;copyWord;finishCopy;commitCursor;beginPublish;commitPublish;scanPrivate"; attribute :>> leanScope = "forwardNotCompletion;idleCannotOwnDebt;noExtraCreditForCoveredDebt"; attribute :>> sourceDuty = "Map actual private alloc variables, inline PAIR tail and captured-frame copy into owned obligations; prove publication and local cursor drain without object-layout simplification"; }
 part refinement2 : RefinementSpec { attribute :>> key = "termination"; attribute :>> qntScope = "dequeue;scanBody;finishScan;idle;wake;issueReceipt"; attribute :>> leanScope = "custodyAtDequeue;zeroActiveCloses;staleBlocks"; attribute :>> sourceDuty = "Source FIFO/active-count/mutex/condvar and root producers refine to stable epoch credit conservation; no late independent writer after zero"; }
 part refinement3 : RefinementSpec { attribute :>> key = "reuse"; attribute :>> qntScope = "classify;reuseBarrier;retireMetadata"; attribute :>> leanScope = "oneReturnNotAll;retirementNeedsPeer;classifyBeforeWeak;weakBlocksLateClassification;netBenefit"; attribute :>> sourceDuty = "No marking after strong return; decision stores precede existing barrier release; root/queue/PSTATE lifetime and chosen will semantics stay separate"; }
 part def PriorSpec { attribute key : String; attribute path : String; attribute invariant : String; attribute qntAction : String; attribute leanLemma : String; attribute condition : String; }
 part prior0 : PriorSpec { attribute :>> key = "scan-count"; attribute :>> path = "models/gambit/gc_scan_termination.qnt"; attribute :>> invariant = "safe"; attribute :>> qntAction = "idle"; attribute :>> leanLemma = "idleCannotOwnDebt"; attribute :>> condition = "Existing counted-producer model distinguishes a detached-publisher fault control; new idle obligations refine private copy/cursor/frame coverage"; }
 part prior1 : PriorSpec { attribute :>> key = "work-closure"; attribute :>> path = "models/gambit/gc_work_closure.qnt"; attribute :>> invariant = "terminationSafe"; attribute :>> qntAction = "finishScan"; attribute :>> leanLemma = "zeroActiveCloses"; attribute :>> condition = "Existing canonical work/copy/publication composition is linked to active-owner coverage; one symbolic object does not prove actual chunk layout"; }
 part prior2 : PriorSpec { attribute :>> key = "callback-boundary"; attribute :>> path = "models/gambit/scan_barrier_quiescence.qnt"; attribute :>> invariant = "callbackClosure"; attribute :>> qntAction = "reuseBarrier"; attribute :>> leanLemma = "oneReturnNotAll"; attribute :>> condition = "Existing model assumes callback return and separately aggregates users; payload closure must not be substituted for its return premise"; }
 part def GateSpec { attribute key : String; attribute qualified : Boolean; attribute condition : String; }
 part gate0 : GateSpec { attribute :>> key = "producer-closure"; attribute :>> qualified = false; attribute :>> condition = "Exact root census, native writer admission and all private/movable/still/chunk producer call sites covered"; }
 part gate1 : GateSpec { attribute :>> key = "vm-ownership"; attribute :>> qualified = false; attribute :>> condition = "Participant/arena/root membership stable with exact worker ownership and safe exit; root registry nonzero coverage qualified"; }
 part gate2 : GateSpec { attribute :>> key = "gc-seal"; attribute :>> qualified = false; attribute :>> condition = "Real local drain and active lifetime imply no pending copy/cursor/tail/publication/frame at idle; no terminal-zero reopen"; }
 part gate3 : GateSpec { attribute :>> key = "scan-coverage"; attribute :>> qualified = false; attribute :>> condition = "Actual FIFO/fast-path/continuation/root maps refine to canonical graph obligations and matching epoch closure"; }
 part gate4 : GateSpec { attribute :>> key = "retirement"; attribute :>> qualified = false; attribute :>> condition = "Payload closure, per-worker callback return, global barrier and resource retirement remain distinct with all users included"; }
 part gate5 : GateSpec { attribute :>> key = "source-replacement"; attribute :>> qualified = false; attribute :>> condition = "Existing barrier reused and duplicate counters avoided only after complete writer/lifetime proof; asynchronous extensions not silently admitted"; }
 part gate6 : GateSpec { attribute :>> key = "platform"; attribute :>> qualified = false; attribute :>> condition = "C happens-before/lock/condvar/header access, ABI/configured GC, host registration and native correctness remain open"; }
 attribute workspaceCount : Integer = 2;
 attribute actualAdmitted : Boolean = false;
 part history : GambitAssuranceRouting::ModelNeed { ref part :>> owner = GambitBuildAssurance::planner.component; attribute :>> obligationId = "SR-H"; attribute :>> kind = "interleaving"; attribute :>> subjectPath = "models/build/strong_closure_receipt.qnt"; attribute :>> subjectScope = "strong_closure_receipt:Test$"; attribute :>> premise = "Conditional strong-closure receipt and source producer coverage; full root census and native qualification remain open"; }
 part induction : GambitAssuranceRouting::ModelNeed { ref part :>> owner = GambitBuildAssurance::planner.component; attribute :>> obligationId = "SR-I"; attribute :>> kind = "induction"; attribute :>> subjectPath = "models/build/StrongClosureReceipt.lean"; attribute :>> subjectScope = "StrongClosureReceipt:zeroActiveCloses;openRootRequiresActive;idleCannotOwnDebt;custodyAtDequeue;forwardNotCompletion;incompleteCensusBlocks;staleBlocks;oneReturnNotAll;retirementNeedsPeer;classifyBeforeWeak;weakBlocksLateClassification;noExtraCreditForCoveredDebt;netBenefit"; attribute :>> premise = "Conditional strong-closure receipt and source producer coverage; full root census and native qualification remain open"; }
 part source : GambitAssuranceRouting::ModelNeed { ref part :>> owner = GambitBuildAssurance::planner.component; attribute :>> obligationId = "SR-S"; attribute :>> kind = "source-refinement"; attribute :>> subjectPath = "dev/architecture/toolchain/strong-closure-receipt-design.org"; attribute :>> subjectScope = "SR-S:source"; attribute :>> premise = "Conditional strong-closure receipt and source producer coverage; full root census and native qualification remain open"; }
 part platform : GambitAssuranceRouting::ModelNeed { ref part :>> owner = GambitBuildAssurance::planner.component; attribute :>> obligationId = "SR-E"; attribute :>> kind = "environment-refinement"; attribute :>> subjectPath = "dev/architecture/toolchain/strong-closure-receipt-design.org"; attribute :>> subjectScope = "SR-E:platform"; attribute :>> premise = "Conditional strong-closure receipt and source producer coverage; full root census and native qualification remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = WillStrongCut::source; }
}
