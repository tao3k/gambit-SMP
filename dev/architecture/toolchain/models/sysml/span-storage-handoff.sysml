package SpanStorageHandoff {
 private import ScalarValues::*;
 part def Contract { attribute key : String; attribute anchor : String; attribute rule : String; attribute openDuty : String; }
 part contract0 : Contract { attribute :>> key = "isolated-content"; attribute :>> anchor = "lexer.ss:120-122,146,175; deflexer.ss:53-58"; attribute :>> rule = "Private retained decoded chunks never alias mutable callback-visible @@; resuming after its allocation preserves the same exposed object"; attribute :>> openDuty = "Native/reflective alias exclusion and actual chunk publication; a copied Scheme record alone does not prove separate backing storage"; }
 part contract1 : Contract { attribute :>> key = "resume-occurrence"; attribute :>> anchor = "_thread.scm:8422-8529,8555-8584; lexer.ss:146,175"; attribute :>> rule = "Separate capture identity, resumption occurrence, source program point and transport operation; resuming after read does not reread, while executing a reader entry again may legitimately read current input"; attribute :>> openDuty = "Exact source/control simulation including captures in winding thunks; finite two-resumption model is not full Scheme semantics"; }
 part contract2 : Contract { attribute :>> key = "exception-reachability"; attribute :>> anchor = "std/error.ss:43-69; runtime/error.ss:16-20,37-43,67-72; runtime/syntax.ss:71,169-171"; attribute :>> rule = "ParseError and SyntaxError carry StackTrace continuation slots; delivery or successful wrapping does not prove old stream unreachable"; attribute :>> openDuty = "Actual reachable frames depend on tail-call elimination and capture point; do not assume every exception retains every stream"; }
 part contract3 : Contract { attribute :>> key = "translation-transfer"; attribute :>> anchor = "lang-reader.ss:60-71; runtime/error.ss:67-72; runtime/syntax.ss:169-171"; attribute :>> rule = "Prepare replacement roots before releasing original attempt custody; allocation, mapping or raise failure keeps responsibility until handler/trace/control reachability settles"; attribute :>> openDuty = "Ordinary nested-error propagation preserved; failure fallback must not silently replace the actual thrown exception with the original"; }
 part contract4 : Contract { attribute :>> key = "separate-release-domains"; attribute :>> anchor = "base.ss:7-8; lexer.ss:20,50-52; stream.ss:19,37-38; _io.scm:10003-10014"; attribute :>> rule = "Old stream, raw chunks, origin-port object and physical resource have distinct lifetimes; detached token/span views need not retain the old stream"; attribute :>> openDuty = "Prove no reverse side-table edge; GC-managed control capsules cannot be strongly rooted by their own native pin counts"; }
 part contract5 : Contract { attribute :>> key = "known-ignore-reduction"; attribute :>> anchor = "deflexer.ss:40-44; lexer.ss:146,175; lang-reader.ss:271-274,323-324"; attribute :>> rule = "A generated constant-$ reduction does not observe @@; a qualified descriptor may omit its otherwise unused chars->string materialization"; attribute :>> openDuty = "Restrict to proven generated descriptor; arbitrary Rs retain API, mutation and effects; allocation-failure observations require an explicit optimization profile"; }
 part def Gate { attribute key : String; attribute qualified : Boolean; attribute condition : String; }
 part gate0 : Gate { attribute :>> key = "storage-alias-proof"; attribute :>> qualified = false; attribute :>> condition = "Private chunks, exposed strings and native writable aliases have a complete source-bound separation argument"; }
 part gate1 : Gate { attribute :>> key = "multi-shot-refinement"; attribute :>> qualified = false; attribute :>> condition = "Capture/resumption/program-point/operation identities reflect real execution and winding; no global memoization of user effects"; }
 part gate2 : Gate { attribute :>> key = "exception-root-closure"; attribute :>> qualified = false; attribute :>> condition = "Original, replacement, secondary error, stacktrace and control references included before reclamation"; }
 part gate3 : Gate { attribute :>> key = "reclamation-adapter"; attribute :>> qualified = false; attribute :>> condition = "Managed reachability and native borrows/pending operations form a sound release witness without self-rooting cycles; native ordering unqualified"; }
 part gate4 : Gate { attribute :>> key = "ignore-specialization"; attribute :>> qualified = false; attribute :>> condition = "Generated constant-$ classification and allocation-observation policy prove omitted materialization admissible"; }
 part def Gain { attribute key : String; attribute avoided : String; attribute added : String; attribute condition : String; }
 part gain0 : Gain { attribute :>> key = "reset-calls"; attribute :>> avoided = "Same prior upper bound: 2A stream constructor calls plus A initial-location calls"; attribute :>> added = "Isolated content, views, root/operation records and adapters"; attribute :>> condition = "Not additive to prior study and not a time/allocation benchmark"; }
 part gain1 : Gain { attribute :>> key = "ignored-strings"; attribute :>> avoided = "For I qualified ignored occurrences: at most I chars->string source calls, with input lengths summing to L_ignore"; attribute :>> added = "Generated reduction classification, retained raw text and observation-policy proof"; attribute :>> condition = "Only constant-$ descriptors; preexisting compiler elimination may reduce realized saving to zero"; }
 part gain2 : Gain { attribute :>> key = "shared-raw-chunks"; attribute :>> avoided = "No mandatory full raw copy for each continuation resumption; old stream may drain before detached token/span views"; attribute :>> added = "Unique retained decoded contents plus O(views + active resumptions + pending operations); mutable @@ remains separate"; attribute :>> condition = "No side-table back edge; live errors/captures can retain history indefinitely"; }
 part gain3 : Gain { attribute :>> key = "modern-c-baseline"; attribute :>> avoided = "Remove split lifetime authority and accidental duplicate reads/effects"; attribute :>> added = "Tracing/root integration, failure custody and native publication support in either modern C or Zig"; attribute :>> condition = "Net work positive only when avoided work exceeds these supports; no uniquely Zig advantage established"; }
 attribute maximumResumptions : Integer = 2;
 attribute actualAdmitted : Boolean = false;
 part history : GambitAssuranceRouting::ModelNeed { ref part :>> owner = GambitBuildAssurance::scheduler.component; attribute :>> obligationId = "SH-H"; attribute :>> kind = "interleaving"; attribute :>> subjectPath = "models/build/span_storage_handoff.qnt"; attribute :>> subjectScope = "span_storage_handoff:Test$"; attribute :>> premise = "Bounded two-resumption storage/identity, partial translation, pending-delivery and separate stream/chunk reclamation histories; environment reachability witness assumed"; }
 part induction : GambitAssuranceRouting::ModelNeed { ref part :>> owner = GambitBuildAssurance::scheduler.component; attribute :>> obligationId = "SH-I"; attribute :>> kind = "induction"; attribute :>> subjectPath = "models/build/SpanStorageHandoff.lean"; attribute :>> subjectScope = "SpanStorageHandoff:mutationIsolation;exposedIdentity;resumeEffects;readAfterCut;rootTransfer;failureKeepsCustody;streamDrain;netWork"; attribute :>> premise = "Conditional immutable-storage, resumption arithmetic, root handoff and release kernels; no full reachability/GC/native-order proof"; }
 part source : GambitAssuranceRouting::ModelNeed { ref part :>> owner = GambitBuildAssurance::scheduler.component; attribute :>> obligationId = "SH-S"; attribute :>> kind = "source-refinement"; attribute :>> subjectPath = "dev/architecture/toolchain/span-storage-handoff-design.org"; attribute :>> subjectScope = "SH-S:storage-control-source"; attribute :>> premise = "Actual @@ exposure, exception stacktrace and catch-graft sources derived; exact frame/alias closure and multi-shot event simulation open"; }
 part platform : GambitAssuranceRouting::ModelNeed { ref part :>> owner = GambitBuildAssurance::scheduler.component; attribute :>> obligationId = "SH-E"; attribute :>> kind = "environment-refinement"; attribute :>> subjectPath = "dev/architecture/toolchain/span-storage-handoff-design.org"; attribute :>> subjectScope = "SH-E:storage-native-reclamation"; attribute :>> premise = "Private backing storage, native borrow root publication, tracing reachability certificates, release memory ordering and cleanup threading remain unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = ReaderSpanCustody::source; }
}
