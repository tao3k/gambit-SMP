package MarkerAuditQuiescence {
 private import ScalarValues::*;
 part def Contract { attribute key : String; attribute anchor : String; attribute actionName : String; attribute lemmaName : String; attribute guardName : String; attribute duty : String; attribute status : String; }
 part contract0 : Contract { attribute :>> key = "derived-credit"; attribute :>> anchor = "mem.c:4210-4248,4432-4451,4928-4935"; attribute :>> actionName = "retireRoots"; attribute :>> lemmaName = "retirementNeedsCallerDone"; attribute :>> guardName = "s.callerDone"; attribute :>> duty = "Accounting completion is not physical caller completion; close roots only after caller and reader/GC grace evidence; audit pin never silently increments marker count"; attribute :>> status = "VM guardian retains failed/unknown audit custody"; }
 part contract1 : Contract { attribute :>> key = "execution-owner"; attribute :>> anchor = "setup.c:931-979; mem.c:4432-4451"; attribute :>> actionName = "closeWriters"; attribute :>> lemmaName = "closingDoesNotDrain"; attribute :>> guardName = "s.session"; attribute :>> duty = "Close generation-aware write admission before drain; pre-admitted original and alias writers retain obligations until stopped or acknowledged"; attribute :>> status = "current direct writers lack this gate"; }
 part contract2 : Contract { attribute :>> key = "writer-closure"; attribute :>> anchor = "mem.c:1447-1480,1730-1737; _kernel.scm:2411-2417; gambit.h.in:13294-13300"; attribute :>> actionName = "admitClosedProfile"; attribute :>> lemmaName = "extraCreditDefeatsInference"; attribute :>> guardName = "not(s.foreignWrite)"; attribute :>> duty = "Exact count=1-ownedDrop requires zero unaccounted native credits; strict private-marker profile rejects generic/reference aliases and raw metadata writes"; attribute :>> status = "syntactic census is not alias-complete proof"; }
 part contract3 : Contract { attribute :>> key = "storage-commit"; attribute :>> anchor = "setup.c:931-979,4666-4673; mem.c:4928-4935"; attribute :>> actionName = "reclaim"; attribute :>> lemmaName = "joinDoesNotTransferArena"; attribute :>> guardName = "s.rootGrace"; attribute :>> duty = "Transfer still arena, scanner ownership and accounting before old PSTATE cleanup; successful join alone cannot preserve already-freed marker storage"; attribute :>> status = "existing cleanup order must change for retained markers"; }
 part contract4 : Contract { attribute :>> key = "audit-receipt"; attribute :>> anchor = "mem.c:1475-1480; os_thread.c:546-556"; attribute :>> actionName = "certifyAudit"; attribute :>> lemmaName = "qualificationNeedsAll"; attribute :>> guardName = "qualified"; attribute :>> duty = "Receipt binds generation, closed writer set, confirmed exit/visibility, root/arena handoff and GC cut; count alone and timeout do not certify"; attribute :>> status = "new source-closed proof-carrying admission"; }
 part contract5 : Contract { attribute :>> key = "auditor-transfer"; attribute :>> anchor = "os_thread.c:546-556; setup.c:979"; attribute :>> actionName = "confirmAuditExit"; attribute :>> lemmaName = "unknownKeepsCustody"; attribute :>> guardName = "not(s.auditLive)"; attribute :>> duty = "Lost response retains audit write lease; replacement only after exact auditor cessation and visibility plus fresh GC cut and reread"; attribute :>> status = "no takeover based on unknown or failed join"; }
 part contract6 : Contract { attribute :>> key = "single-drop"; attribute :>> anchor = "c_intf.c:6555-6562; mem.c:1461-1480"; attribute :>> actionName = "auditDrop"; attribute :>> lemmaName = "dropPreserves"; attribute :>> guardName = "s.drops==0"; attribute :>> duty = "At exclusive cut, count 1 permits only missing decrement and count 0 permits recording; invalidation and decrement have separate progress"; attribute :>> status = "no full-kill replay after zero count"; }
 part contract7 : Contract { attribute :>> key = "gc-cut"; attribute :>> anchor = "mem.c:4210-4248,4387-4451; setup.c:931-979"; attribute :>> actionName = "beginGcCut"; attribute :>> lemmaName = "exclusiveAuditExcludesScan"; attribute :>> guardName = "writersDrained"; attribute :>> duty = "Serialize plain refcount/body audit with collector; preserve independent scanned root at count zero and keep old storage owned"; attribute :>> status = "no global lock held across GC participation wait"; }
 part def Gain { attribute key : String; attribute avoided : String; attribute added : String; attribute condition : String; }
 part gain0 : Gain { attribute :>> key = "private-marker-audit"; attribute :>> avoided = "Recover unlogged owned decrement with existing count representation under verified exclusive baseline"; attribute :>> added = "Writer-profile closure, same-generation directory, join/visibility and root/arena/GC handoff"; attribute :>> condition = "Current code does not establish a universal single-reference marker invariant; unsafe/open alias paths reject audit"; }
 part gain1 : Gain { attribute :>> key = "repeatable-audit"; attribute :>> avoided = "A replacement can reread zero after prior auditor decremented but did not record"; attribute :>> added = "Keep guardian root/session; confirm auditor stopped, refresh cut and discard old observation"; attribute :>> condition = "Failed join or response loss cannot release prior lease or authorize another writer"; }
 part gain2 : Gain { attribute :>> key = "storage-preservation"; attribute :>> avoided = "Allow processor exit while retained marker remains valid in VM-owned storage"; attribute :>> added = "Scanner ownership and still capacity/accounting handoff before cleanup; independent root registration"; attribute :>> condition = "Join-only or ordinary root pin does not override free_still_objs; cleanup path must be refactored"; }
 part gain3 : Gain { attribute :>> key = "modern-c-net-benefit"; attribute :>> avoided = "Reuse allocator count and shared root/admission machinery instead of forcing token representation for every eligible marker"; attribute :>> added = "Stop/drain/GC latency, verification and unknown retention remain; token path still alternative"; attribute :>> condition = "Net gain depends on a genuinely closed private-marker domain and shared support; no runtime speed or Zig-specific saving established"; }
 part def Gate { attribute key : String; attribute qualified : Boolean; attribute duty : String; }
 part gate0 : Gate { attribute :>> key = "reference-writer-closure"; attribute :>> qualified = false; attribute :>> duty = "Generic C, Scheme primitive, exported function-table and raw native alias writers are closed or marker profile is rejected; census cannot certify this universally"; }
 part gate1 : Gate { attribute :>> key = "stop-and-visibility"; attribute :>> qualified = false; attribute :>> duty = "Exact old writer and every auditor cessation, admitted join result, happens-before, no late leased writer; current shrink ignores join error"; }
 part gate2 : Gate { attribute :>> key = "arena-handoff"; attribute :>> qualified = false; attribute :>> duty = "Still list, scanner/sweep and capacity census transfer before cleanup_pstate/free_still_objs; root registration alone is insufficient"; }
 part gate3 : Gate { attribute :>> key = "audit-qualification"; attribute :>> qualified = false; attribute :>> duty = "Known one-credit baseline, independent root pin without still increment, stable generation, excluded raw aliases, no corrupt/torn state"; }
 part gate4 : Gate { attribute :>> key = "auditor-retirement"; attribute :>> qualified = false; attribute :>> duty = "No overlap or stale observation after audit helper exit; read leases and root/session guardian outlive unknown outcomes"; }
 part gate5 : Gate { attribute :>> key = "c11-source-refinement"; attribute :>> qualified = false; attribute :>> duty = "Gate close/drain, ordinary-field quiescence, collector exclusion and native join semantics are mapped to concrete instructions"; }
 part gate6 : Gate { attribute :>> key = "darwin-native"; attribute :>> qualified = false; attribute :>> duty = "Static SDK macro parity only; installed pthread/GC/SMP object and full source/native registration remain open"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Nine literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "MAQ-H"; attribute :>> kind = "interleaving"; attribute :>> subjectPath = "models/build/marker_audit_quiescence.qnt"; attribute :>> subjectScope = "safe: closed marker writer admission, old join and arena/GC handoff, exact credit audit, late writers, auditor exit and fresh-cut replacement"; attribute :>> premise = "No-abandonment cleanup, VM root-domain coverage and directory lifetime are premises, not implemented facilities; current native profile remains unqualified"; }
 part induction : GambitAssuranceRouting::ModelNeed { ref part :>> owner = GambitBuildAssurance::planner.component; attribute :>> obligationId = "MAQ-I"; attribute :>> kind = "induction"; attribute :>> subjectPath = "models/build/MarkerAuditQuiescence.lean"; attribute :>> subjectScope = "count-plus-owned-credit induction, extra-credit counterexample, qualification prerequisites and persistent keeper custody"; attribute :>> premise = "No-abandonment cleanup, VM root-domain coverage and directory lifetime are premises, not implemented facilities; current native profile remains unqualified"; }
 part source : GambitAssuranceRouting::ModelNeed { ref part :>> owner = GambitBuildAssurance::planner.component; attribute :>> obligationId = "MAQ-S"; attribute :>> kind = "source-refinement"; attribute :>> subjectPath = "dev/architecture/toolchain/marker-audit-quiescence-design.org"; attribute :>> subjectScope = "all named refcount writes and API/primitive/alias routes, marker caller identity, processor cleanup order and quiescent audit integration"; attribute :>> premise = "No-abandonment cleanup, VM root-domain coverage and directory lifetime are premises, not implemented facilities; current native profile remains unqualified"; }
 part platform : GambitAssuranceRouting::ModelNeed { ref part :>> owner = GambitBuildAssurance::planner.component; attribute :>> obligationId = "MAQ-E"; attribute :>> kind = "environment-refinement"; attribute :>> subjectPath = "dev/architecture/toolchain/marker-audit-quiescence-design.org"; attribute :>> subjectScope = "C11 closed gate/drain, ordinary field read/write quiescence, exact join status, GC/arena handoff and Darwin/SMP qualification"; attribute :>> premise = "No-abandonment cleanup, VM root-domain coverage and directory lifetime are premises, not implemented facilities; current native profile remains unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = ReleaseCommitCustody::source; }
 part def ContractDependency { ref part dependent : Contract; ref part prerequisite : Contract; attribute reason : String; }
 part edge0 : ContractDependency { ref part :>> dependent = contract2; ref part :>> prerequisite = contract1; attribute :>> reason = "Close admission before writer-profile closure receipt"; }
 part edge1 : ContractDependency { ref part :>> dependent = contract7; ref part :>> prerequisite = contract1; attribute :>> reason = "Drain pre-admitted writers before collector cut"; }
 part edge2 : ContractDependency { ref part :>> dependent = contract4; ref part :>> prerequisite = contract2; attribute :>> reason = "Count inference needs complete writer/credit provenance"; }
 part edge3 : ContractDependency { ref part :>> dependent = contract4; ref part :>> prerequisite = contract7; attribute :>> reason = "Audit receipt includes collector and root storage cut"; }
 part edge4 : ContractDependency { ref part :>> dependent = contract5; ref part :>> prerequisite = contract4; attribute :>> reason = "Replacement needs identity-specific audit authority"; }
 part edge5 : ContractDependency { ref part :>> dependent = contract6; ref part :>> prerequisite = contract4; attribute :>> reason = "Only qualified exact-credit observation permits missing decrement"; }
 part edge6 : ContractDependency { ref part :>> dependent = contract0; ref part :>> prerequisite = contract6; attribute :>> reason = "Accounting settlement precedes physical root retirement"; }
 part edge7 : ContractDependency { ref part :>> dependent = contract0; ref part :>> prerequisite = contract5; attribute :>> reason = "No unresolved auditor lease at retirement"; }
 part edge8 : ContractDependency { ref part :>> dependent = contract3; ref part :>> prerequisite = contract0; attribute :>> reason = "Storage reclaim follows caller and root retirement"; }
 part edge9 : ContractDependency { ref part :>> dependent = contract4; ref part :>> prerequisite = contract1; attribute :>> reason = "Closed gate and successful cessation precede qualification"; }
 part def MemoryEdge { attribute key : String; attribute writer : String; attribute publication : String; attribute reader : String; attribute observation : String; attribute lifetime : String; }
 part memory0 : MemoryEdge { attribute :>> key = "close-admission"; attribute :>> writer = "stable VM directory closes native writer generation"; attribute :>> publication = "SC gate transition; candidate acq_rel CAS"; attribute :>> reader = "old and late requesting writers"; attribute :>> observation = "acquire same closed generation; no unchecked increment after separate open test"; attribute :>> lifetime = "raw bypass aliases must be excluded by admitted profile"; }
 part memory1 : MemoryEdge { attribute :>> key = "writer-drain"; attribute :>> writer = "last admitted writer completes ordinary count/body accesses"; attribute :>> publication = "release write-lease decrement"; attribute :>> reader = "collector/audit coordinator"; attribute :>> observation = "acquire drained same gate after close; preserve reads-from chain"; attribute :>> lifetime = "counter zero is meaningful only with closed admission and complete writer set"; }
 part memory2 : MemoryEdge { attribute :>> key = "join-result"; attribute :>> writer = "OS thread termination and exact join result"; attribute :>> publication = "platform termination synchronization; capture native return code"; attribute :>> reader = "guardian"; attribute :>> observation = "successful matching join; errors/unknown retain lease and custody"; attribute :>> lifetime = "native thread death alone does not transfer arena or roots"; }
 part memory3 : MemoryEdge { attribute :>> key = "arena-transfer"; attribute :>> writer = "old storage owner publishes retained still-list/accounting handoff"; attribute :>> publication = "release immutable StorageHandoffReceipt"; attribute :>> reader = "target VM storage/scanner owner"; attribute :>> observation = "acquire same generation before old cleanup"; attribute :>> lifetime = "old free_still_objs cannot run on transferred retained chain"; }
 part memory4 : MemoryEdge { attribute :>> key = "gc-cut"; attribute :>> writer = "coordinator parks producers and scanner/auditor in disjoint phases"; attribute :>> publication = "release epoch/root snapshot and matching acknowledgement"; attribute :>> reader = "collector then exclusive auditor"; attribute :>> observation = "acquire complete cut; no global root lock across GC wait"; attribute :>> lifetime = "count-zero marker remains ordinary root-reachable"; }
 part memory5 : MemoryEdge { attribute :>> key = "audit-read"; attribute :>> writer = "exclusive auditor with proven native credit baseline"; attribute :>> publication = "plain count and marker reads after HB/quiescence"; attribute :>> reader = "same auditor"; attribute :>> observation = "fresh observation under active lease only"; attribute :>> lifetime = "no atomic cast on mixed plain fields; no extra native still reference for audit pin"; }
 part memory6 : MemoryEdge { attribute :>> key = "audit-write"; attribute :>> writer = "exclusive auditor performs missing invalidation/drop"; attribute :>> publication = "plain writes then release accounting receipt"; attribute :>> reader = "query/custodian"; attribute :>> observation = "acquire same audit/marker generation"; attribute :>> lifetime = "if auditor exits before receipt, keep roots and establish a fresh cut before reread"; }
 part memory7 : MemoryEdge { attribute :>> key = "replacement"; attribute :>> writer = "prior auditor exits, then guardian confirms cessation and visibility"; attribute :>> publication = "release/drain prior audit lease and invalidate old observation"; attribute :>> reader = "next auditor"; attribute :>> observation = "acquire fresh epoch-qualified receipt before touching count"; attribute :>> lifetime = "lost response is not cessation; no helper overlap"; }
 part memory8 : MemoryEdge { attribute :>> key = "retirement"; attribute :>> writer = "physical caller and reader/root grace obligations settle"; attribute :>> publication = "release Done/root-domain retirement"; attribute :>> reader = "VM guardian"; attribute :>> observation = "acquire complete retirement receipt"; attribute :>> lifetime = "no free based on count zero, invalid marker, join or audit accounting alone"; }
 part def WriterRoute { attribute key : String; attribute kind : String; attribute anchor : String; attribute target : String; attribute admission : String; attribute status : String; }
 part writer0 : WriterRoute { attribute :>> key = "initial-count"; attribute :>> kind = "direct field write"; attribute :>> anchor = "mem.c:1683"; attribute :>> target = "fresh still allocation"; attribute :>> admission = "count set to 1 before publication"; attribute :>> status = "not a retained old marker rewrite"; }
 part writer1 : WriterRoute { attribute :>> key = "native-inc"; attribute :>> kind = "direct arithmetic writer"; attribute :>> anchor = "mem.c:1447-1453"; attribute :>> target = "arbitrary still object argument"; attribute :>> admission = "guarded managed writer or reject alias"; attribute :>> status = "no intrinsic marker/private-token check"; }
 part writer2 : WriterRoute { attribute :>> key = "native-dec"; attribute :>> kind = "direct arithmetic writer"; attribute :>> anchor = "mem.c:1461-1467"; attribute :>> target = "arbitrary still object argument"; attribute :>> admission = "owned credit and admitted write role"; attribute :>> status = "plain non-idempotent decrement"; }
 part writer3 : WriterRoute { attribute :>> key = "marker-kill"; attribute :>> kind = "specialized caller"; attribute :>> anchor = "c_intf.c:6555-6562; setup.c:3415; gambit.h.in:10047,10053,10059"; attribute :>> target = "actual marker from make_sfun_stack_marker"; attribute :>> admission = "old tail and auditor cannot overlap"; attribute :>> status = "known in-tree marker decrement route"; }
 part writer4 : WriterRoute { attribute :>> key = "generic-release"; attribute :>> kind = "indirect decrement caller"; attribute :>> anchor = "mem.c:1730-1737; gambit.h.in:10194-10645"; attribute :>> target = "allocated still SCMOBJ argument"; attribute :>> admission = "prove temporary distinct from marker or refuse alias"; attribute :>> status = "conversion macros and Tcl use generic API; marker alias not excluded by function"; }
 part writer5 : WriterRoute { attribute :>> key = "scheme-primitives"; attribute :>> kind = "indirect inc/dec callers"; attribute :>> anchor = "_kernel.scm:2411-2417; _kernel.c:18157,18187; pthread/mylib.scm:26-31"; attribute :>> target = "Scheme object argument"; attribute :>> admission = "restrict marker access to unsafe native-count operations"; attribute :>> status = "real caller example uses counter, not observed marker"; }
 part writer6 : WriterRoute { attribute :>> key = "native-exports"; attribute :>> kind = "function-pointer exposure"; attribute :>> anchor = "setup.c:5931-5944; gambit.h.in:13281-13300,14624-14643"; attribute :>> target = "external native code can pass encoded object"; attribute :>> admission = "admitted embedding/profile closure"; attribute :>> status = "export declaration is capability, not observed marker invocation"; }
 part writer7 : WriterRoute { attribute :>> key = "raw-layout"; attribute :>> kind = "unbounded potential bypass"; attribute :>> anchor = "mem.c:525,1452,1466; gambit.h.in body/object macros"; attribute :>> target = "native pointer or encoded object alias"; attribute :>> admission = "reject unmanaged body/header writes"; attribute :>> status = "symbol census cannot enumerate arbitrary C pointer arithmetic"; }
 part writer8 : WriterRoute { attribute :>> key = "gc-and-cleanup"; attribute :>> kind = "read/lifecycle consumers"; attribute :>> anchor = "mem.c:4221,4387-4451,4928-4935"; attribute :>> target = "still chain storage and metadata"; attribute :>> admission = "transfer scan/sweep/storage responsibility before exit"; attribute :>> status = "GC reads count; cleanup frees without count check, not another arithmetic writer"; }
 part writer9 : WriterRoute { attribute :>> key = "fresh-body-copy"; attribute :>> kind = "distinct allocation consumer"; attribute :>> anchor = "_kernel.scm:2390-2398"; attribute :>> target = "new result object from still-copy"; attribute :>> admission = "track object identity, do not count as marker rewrite"; attribute :>> status = "payload copy and new-result drop are not evidence of old marker count mutation"; }
 part writer10 : WriterRoute { attribute :>> key = "continuation-access"; attribute :>> kind = "possible alias exposure"; attribute :>> anchor = "setup.c:3340; _kernel.scm:3145-3152,3415-3501; _io.scm:11690-11726"; attribute :>> target = "captured frames and generic slot access"; attribute :>> admission = "private-marker proof must cover introspection/serialization/native forwarding"; attribute :>> status = "source exposes mechanisms; exact executable marker extraction remains unproved"; }
 part def AuditPolicy { attribute key : String; attribute identity : String; attribute roots : String; attribute executor : String; }
 part policy0 : AuditPolicy { attribute :>> key = "marker-audit"; attribute :>> identity = "activation-generation"; attribute :>> roots = "scanned-slots"; attribute :>> executor = "closed-writers-fresh-audit-epoch"; }
}
