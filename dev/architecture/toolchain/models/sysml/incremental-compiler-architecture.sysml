package IncrementalCompilerArchitecture {
 private import ScalarValues::*;
 part def ComponentSpec { attribute key : String; attribute anchor : String; attribute responsibility : String; attribute replacement : String; }
 part component0 : ComponentSpec { attribute :>> key = "snapshot-broker"; attribute :>> anchor = "std/make.ss:246-290; runtime/loader.ss:14-30"; attribute :>> responsibility = "Resolve all files, absence, paths, environment and admitted native reads in an immutable input epoch"; attribute :>> replacement = "Replace temporary global path/timestamp authority with tracked observations; opaque effects stay owned and nonreusable"; }
 part component1 : ComponentSpec { attribute :>> key = "query-engine"; attribute :>> anchor = "std/make.ss:299-343; compiler/driver.ss:621-641"; attribute :>> responsibility = "Demand phase-specific compiler results; record dynamic reads and validate prior traces"; attribute :>> replacement = "Replaces whole-module completion as the sole dependency boundary; no top-level form caching without separate semantic proof"; }
 part component2 : ComponentSpec { attribute :>> key = "semantic-session"; attribute :>> anchor = "compiler/driver.ss:119-139,621-641; expander/module.ss:102-181"; attribute :>> responsibility = "Instantiate binding/mark/module identity and mutable overlays per session"; attribute :>> replacement = "Rebuild semantic versus instance versus attempt identity (driver timestamp/base gensym); migrate deep optimizer/expander state before retiring mutex"; }
 part component3 : ComponentSpec { attribute :>> key = "artifact-publisher"; attribute :>> anchor = "compiler/driver.ss:707-747; gsc/_t-c-1.scm"; attribute :>> responsibility = "Commit a coherent result manifest containing typed interface, executable support, semantic IR and native products"; attribute :>> replacement = "Replaces independent direct output writes only after all consumers use exact manifests"; }
 part component4 : ComponentSpec { attribute :>> key = "resource-scheduler"; attribute :>> anchor = "std/make.ss:220-232,345-358; compiler/base.ss:287-335"; attribute :>> responsibility = "Single-flight result keys, suspension on discovered dependencies, resource budgets and cancellation custody"; attribute :>> replacement = "Replace redundant pools and global completion waits; independent processes can parallelize before same-VM SMP qualifies"; }
 part component5 : ComponentSpec { attribute :>> key = "backend-runtime"; attribute :>> anchor = "GVM/FrameSpec/ModuleSpec; mem.c; include/gambit.h.in"; attribute :>> responsibility = "Generated modern C consumes the semantic result and runtime contract; LLVM/MLIR optional consumers use the same contract"; attribute :>> replacement = "Runtime GC/SMP redesign is a separate T0 lane; retirement/notifier work is an admission subproblem, not a build speed result"; }
 part def StageSpec { attribute key : String; attribute role : String; attribute inputs : String; attribute result : String; }
 part stage0 : StageSpec { attribute :>> key = "source-syntax"; attribute :>> role = "Reader and source resolution"; attribute :>> inputs = "Input cohort + dialect/reader/effect identity"; attribute :>> result = "Syntax with locations/identity; no mutable port state in a reusable result"; }
 part stage1 : StageSpec { attribute :>> key = "binding-interface"; attribute :>> role = "Module export/binding contract"; attribute :>> inputs = "Module + phase + canonical binding identities + producer inputs"; attribute :>> result = "Consumer-specific projection; signature stability alone cannot validate transformer code"; }
 part stage2 : StageSpec { attribute :>> key = "phase-program"; attribute :>> role = "Executable macro support closure"; attribute :>> inputs = "Transformer bytes + positive-phase dependencies + native helper ABI + initializer plan"; attribute :>> result = "Reusable program instructions; initialization effects and mutable instances are separately owned"; }
 part stage3 : StageSpec { attribute :>> key = "session-instance"; attribute :>> role = "Context/overlay instantiation"; attribute :>> inputs = "Phase program + fresh session identity + dependency instances + effect order"; attribute :>> result = "Per-session state; no cross-session cache of live mutable closure graphs"; }
 part stage4 : StageSpec { attribute :>> key = "expanded-semantic-ir"; attribute :>> role = "Expand and normalize"; attribute :>> inputs = "Syntax + interface + executable support + owned instance + traced capabilities"; attribute :>> result = "Completed semantic graph plus origin/control/failure observations; consumed projections include relevant diagnostics"; }
 part stage5 : StageSpec { attribute :>> key = "gvm-contract"; attribute :>> role = "Analyze/optimize and lower"; attribute :>> inputs = "Semantic IR + optimizer/SSXI facts + options + target semantic contract"; attribute :>> result = "GVM with explicit ModuleSpec/FrameSpec/PointId/root/effect duties"; }
 part stage6 : StageSpec { attribute :>> key = "generated-modern-c"; attribute :>> role = "Native C emission"; attribute :>> inputs = "GVM contract + emitter/version + layout/ABI policy"; attribute :>> result = "Modern C units and shared runtime descriptors; LLVM upgrade does not automatically invalidate expansion"; }
 part stage7 : StageSpec { attribute :>> key = "native-manifest"; attribute :>> role = "C compilation and link"; attribute :>> inputs = "Generated C + effective headers/defines/compiler + link closure"; attribute :>> result = "Content-addressed native artifacts and atomic publication manifest"; }
 part def NodeSpec { attribute key : String; attribute number : Integer; attribute dependencySet : String; attribute anchor : String; attribute contract : String; }
 part node0 : NodeSpec { attribute :>> key = "iter-interface"; attribute :>> number = 0; attribute :>> dependencySet = "Set()"; attribute :>> anchor = "iter/macros.ss; iter/api.ss; iter.ss"; attribute :>> contract = "Coherent binding interface projection"; }
 part node1 : NodeSpec { attribute :>> key = "iter-support"; attribute :>> number = 1; attribute :>> dependencySet = "Set(0)"; attribute :>> anchor = "expander/module.ss:839-875; compiler/driver.ss:707-747"; attribute :>> contract = "Executable positive-phase closure, not only SSI existence"; }
 part node2 : NodeSpec { attribute :>> key = "expand-misc"; attribute :>> number = 2; attribute :>> dependencySet = "Set(0,1)"; attribute :>> anchor = "std/string/misc.ss:227-234"; attribute :>> contract = "Fresh session; dynamic extra support may be discovered"; }
 part node3 : NodeSpec { attribute :>> key = "expand-wg"; attribute :>> number = 3; attribute :>> dependencySet = "Set(0,1)"; attribute :>> anchor = "std/sync/wg.ss:37-38"; attribute :>> contract = "Independent owned session with full support closure"; }
 part node4 : NodeSpec { attribute :>> key = "native-misc"; attribute :>> number = 4; attribute :>> dependencySet = "Set(2)"; attribute :>> anchor = "compiler/driver.ss:647-705"; attribute :>> contract = "Bounded model groups GVM/C/native stages; production graph splits them"; }
 part node5 : NodeSpec { attribute :>> key = "native-wg"; attribute :>> number = 5; attribute :>> dependencySet = "Set(3)"; attribute :>> anchor = "compiler/driver.ss:647-705"; attribute :>> contract = "May overlap expand-misc or native-misc when dependencies and budget permit"; }
 part node6 : NodeSpec { attribute :>> key = "target-link"; attribute :>> number = 6; attribute :>> dependencySet = "Set(4,5)"; attribute :>> anchor = "compiler/driver.ss native consumer boundary"; attribute :>> contract = "One demanded target; same result requested twice joins one producer"; }
 part node7 : NodeSpec { attribute :>> key = "dynamic-support"; attribute :>> number = 7; attribute :>> dependencySet = "Set()"; attribute :>> anchor = "Capability broker design; actual initializer closure unresolved"; attribute :>> contract = "Hypothetical discovered dependency; not a claim of an observed extra import"; }
 part def GateSpec { attribute key : String; attribute qualified : Boolean; attribute condition : String; }
 part gate0 : GateSpec { attribute :>> key = "observational-semantics"; attribute :>> qualified = false; attribute :>> condition = "Clean-build equivalence includes binding identity, expansion, diagnostics, exceptions and relevant effects; arbitrary syntax/macro heap serialization is not admitted"; }
 part gate1 : GateSpec { attribute :>> key = "tracked-inputs"; attribute :>> qualified = false; attribute :>> condition = "All dynamic reads, negative lookups, compiler/tool descriptions and source epochs tracked; opaque native/time/random/network effects deny reusable credentials"; }
 part gate2 : GateSpec { attribute :>> key = "session-isolation"; attribute :>> qualified = false; attribute :>> condition = "Deep expander/optimizer/loader/phase instance state owned or proven immutable; lock deletion follows caller migration"; }
 part gate3 : GateSpec { attribute :>> key = "projection-cutoff"; attribute :>> qualified = false; attribute :>> condition = "Each consumer names exactly the interface/support/IR/native observations it consumes; unchanged signature cannot hide changed transformer code"; }
 part gate4 : GateSpec { attribute :>> key = "scheduler-publication"; attribute :>> qualified = false; attribute :>> condition = "Single-flight keys, suspension/resource release, cycle diagnostics, unknown/cancel custody and atomic result groups refine to actual code"; }
 part gate5 : GateSpec { attribute :>> key = "backend-cohort"; attribute :>> qualified = false; attribute :>> condition = "Modern-C runtime/GC/SMP and generation/compile/link cohorts qualified independently; binary GC maps do not prove dead registers or build acceleration"; }
 part gate6 : GateSpec { attribute :>> key = "production-refinement"; attribute :>> qualified = false; attribute :>> condition = "Eight-node model refines actual module/phase/action population; observed avoided work, critical path and added overhead must establish benefit"; }
 part def GainSpec { attribute key : String; attribute avoided : String; attribute added : String; attribute condition : String; }
 part gain0 : GainSpec { attribute :>> key = "no-change"; attribute :>> avoided = "Re-execution of unchanged demanded compiler/native stages"; attribute :>> added = "Trace validation, file/absence validation and result materialization"; attribute :>> condition = "Zero recomputation only for admitted unchanged queries, not zero filesystem or validation work"; }
 part gain1 : GainSpec { attribute :>> key = "leaf-edit"; attribute :>> avoided = "Unrelated module expansion/native generation and unnecessary whole-module barriers"; attribute :>> added = "Invalidate affected trace closure; compare consumer-visible outputs"; attribute :>> condition = "Unchanged wg may already be skipped today; no new gain credited for that alone. New opportunity is finer phase cutoff and less import/support reconstruction, pending actual baseline evidence"; }
 part gain2 : GainSpec { attribute :>> key = "macro-edit"; attribute :>> avoided = "Downstream work after genuinely unchanged consumed projections"; attribute :>> added = "Recompute changed macro support; invalidate both consumers when transformer semantics change"; attribute :>> condition = "An unchanged interface alone is insufficient; no false early cutoff"; }
 part gain3 : GainSpec { attribute :>> key = "parallel-span"; attribute :>> avoided = "Waiting for unrelated runtime object completion before independent consumer expansion"; attribute :>> added = "Owned sessions/processes, memory budgets, IPC and broker contention"; attribute :>> condition = "T >= max(W/P,S); reducing span S differs from reducing total work W; no claimed 12-core speedup"; }
 part gain4 : GainSpec { attribute :>> key = "shared-support"; attribute :>> avoided = "Duplicated immutable phase-program preparation across otherwise isolated sessions"; attribute :>> added = "Program serialization/validation and fresh per-session instance/identity work remain"; attribute :>> condition = "Positive work saving only if avoided work R exceeds H_validation + H_instantiation + H_transfer; current sticky reuse is baseline"; }
 part gain5 : GainSpec { attribute :>> key = "native-cost"; attribute :>> avoided = "Repeated generated-C/native work for unchanged semantic/native keys"; attribute :>> added = "ABI/header/compiler-specific keys and atomic manifests; emitter refactoring can affect GCC work"; attribute :>> condition = "Darwin macro tracking costs and frontend dependency costs are separate; 5x observation is unverified here"; }
 attribute nodeCount : Integer = 8;
 attribute capacity : Integer = 2;
 attribute actualAdmitted : Boolean = false;
 part history : GambitAssuranceRouting::ModelNeed { ref part :>> owner = GambitBuildAssurance::planner.component; attribute :>> obligationId = "IC-H"; attribute :>> kind = "interleaving"; attribute :>> subjectPath = "models/build/incremental_compiler_architecture.qnt"; attribute :>> subjectScope = "incremental_compiler_architecture:Test$"; attribute :>> premise = "Eight-node proposed query graph: trace validation, per-key single flight, dynamic suspension, immutable epochs and publication; not production compiler simulation"; }
 part induction : GambitAssuranceRouting::ModelNeed { ref part :>> owner = GambitBuildAssurance::planner.component; attribute :>> obligationId = "IC-I"; attribute :>> kind = "induction"; attribute :>> subjectPath = "models/build/IncrementalCompilerArchitecture.lean"; attribute :>> subjectScope = "IncrementalCompilerArchitecture:workPositive;spanLowerBound;interfaceNotSupport;cohortNeeded;opaqueRejects;projectionNeedsSupport;publicationNeedsSuccess;sourceProofSeparate"; attribute :>> premise = "Conditional work/span and admission kernels; clean-build equivalence and production refinement remain open"; }
 part source : GambitAssuranceRouting::ModelNeed { ref part :>> owner = GambitBuildAssurance::planner.component; attribute :>> obligationId = "IC-S"; attribute :>> kind = "source-refinement"; attribute :>> subjectPath = "dev/architecture/toolchain/incremental-compiler-architecture-design.org"; attribute :>> subjectScope = "IC-S:compiler-architecture-source"; attribute :>> premise = "Actual monolithic completion, locked mutable state and output paths mapped to replacement modules; complete macro/capability/identity source simulation open"; }
 part platform : GambitAssuranceRouting::ModelNeed { ref part :>> owner = GambitBuildAssurance::planner.component; attribute :>> obligationId = "IC-E"; attribute :>> kind = "environment-refinement"; attribute :>> subjectPath = "dev/architecture/toolchain/incremental-compiler-architecture-design.org"; attribute :>> subjectScope = "IC-E:compiler-architecture-platform"; attribute :>> premise = "Process/VM execution, memory/IPC costs, runtime GC/SMP and actual Darwin pipeline cost unqualified; no implementation/native tests"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = GerbilSessionClosure::source; }
}
