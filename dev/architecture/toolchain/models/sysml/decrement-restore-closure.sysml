package DecrementRestoreClosure {
 private import ScalarValues::*;
 part def Contract { attribute key : String; attribute anchor : String; attribute actionName : String; attribute lemmaName : String; attribute guardName : String; attribute duty : String; attribute status : String; }
 part contract0 : Contract { attribute :>> key = "derived-credit"; attribute :>> anchor = "setup.c:3383-3390; gambit.h.in:9981-9988"; attribute :>> actionName = "decrementClaim"; attribute :>> lemmaName = "handoffReleaseCovered"; attribute :>> guardName = "s.published[i]"; attribute :>> duty = "Release claim only after published and acknowledged execution-session ownership; subsequent PSTATE accesses remain covered"; attribute :>> status = "new handoff contract"; }
 part contract1 : Contract { attribute :>> key = "execution-owner"; attribute :>> anchor = "setup.c:3276-3390; gambit.h.in:6815-6841"; attribute :>> actionName = "prepareOwner"; attribute :>> lemmaName = "adoptedCovers"; attribute :>> guardName = "s.claim[i]"; attribute :>> duty = "Adopt original VM execution context before claim release; retain owner through host epilogue, catch restoration and caller tail"; attribute :>> status = "stable native anchor required"; }
 part contract2 : Contract { attribute :>> key = "host-restore"; attribute :>> anchor = "gambit.h.in:6815-6841,6909,6956,7082-7098,8109-8117"; attribute :>> actionName = "reenterHost"; attribute :>> lemmaName = "activeRestoreNeedsOwner"; attribute :>> guardName = "s.phase[i]==3"; attribute :>> duty = "R1 to SELF and host spill/reload remain under execution ownership; same-host edges need their own live-carrier proof"; attribute :>> status = "effective generated mask open"; }
 part contract3 : Contract { attribute :>> key = "storage-commit"; attribute :>> anchor = "gambit.h.in:6377-6387,6587-6605,6654-6667"; attribute :>> actionName = "retireVm"; attribute :>> lemmaName = "captureBlocksVmRetirement"; attribute :>> guardName = "not(futureVm)"; attribute :>> duty = "VM retirement requires settled execution and exported continuation/invocation authority; native empty receipt is narrower"; attribute :>> status = "parent source/native closure retained"; }
 part contract4 : Contract { attribute :>> key = "catch-restore"; attribute :>> anchor = "gambit.h.in:9981-9988; setup.c:3383-3389"; attribute :>> actionName = "restoreCatcher"; attribute :>> lemmaName = "noBareReleaseDuringRestore"; attribute :>> guardName = "s.phase[i]==5"; attribute :>> duty = "THROW and END_TRY access catcher and longjmp_err; call epilogue still accesses fp and PSR0"; attribute :>> status = "last decrement cannot precede these without handoff"; }
 part contract5 : Contract { attribute :>> key = "abnormal-guard"; attribute :>> anchor = "setup.c:3383-3417; c_intf.c:6555-6563; gambit.h.in:10043-10059"; attribute :>> actionName = "unwindGuard"; attribute :>> lemmaName = "deadMarkerDeniesC"; attribute :>> guardName = "s.error[i]"; attribute :>> duty = "Required abnormal completion guard invalidates C marker and settles roots even when lexical normal cleanup is bypassed"; attribute :>> status = "current all-caller cleanup not proved"; }
 part contract6 : Contract { attribute :>> key = "continuation-context"; attribute :>> anchor = "_kernel.scm:1020-1065; gambit.h.in:6377-6387,6654-6667"; attribute :>> actionName = "invokeK"; attribute :>> lemmaName = "captureDoesNotPinOldProcessor"; attribute :>> guardName = "s.processors.contains(p)"; attribute :>> duty = "Retained continuation holds VM/frame authority; restore acquires a valid current processor in same VM, not resurrected original PSTATE"; attribute :>> status = "export and arena handoff premises open"; }
 part contract7 : Contract { attribute :>> key = "leaf-release"; attribute :>> anchor = "setup.c:3383-3417; gambit.h.in:10043-10059"; attribute :>> actionName = "decrementLeaf"; attribute :>> lemmaName = "leafRequiresSettled"; attribute :>> guardName = "s.phase[i]==9"; attribute :>> duty = "Leaf decrement only in stable outer custodian after marker, conversion/error propagation and restoration boundary settle"; attribute :>> status = "no universal existing source line"; }
 part def Gain { attribute key : String; attribute avoided : String; attribute added : String; attribute condition : String; }
 part gain0 : Gain { attribute :>> key = "session-reuse"; attribute :>> avoided = "For b batches sharing s execution sessions, potentially replace b per-batch session lease pairs by s pairs when s<=b"; attribute :>> added = "Still b claim settlements and handoff receipts plus session lifetime and root accounting"; attribute :>> condition = "Only a proved shared-session contract permits b-s lease-pair reduction; current code has no such receipt and no speed gain is established"; }
 part gain1 : Gain { attribute :>> key = "closure-retention"; attribute :>> avoided = "Avoid premature VM/PSTATE retirement and false completion at handler or host return"; attribute :>> added = "Retain actual restoration debt and exported-handle/invocation authority; memory retention lasts until those obligations close"; attribute :>> condition = "Continuation roots retain required VM state, not every original processor indefinitely; no arbitrary forced timeout"; }
 part gain2 : Gain { attribute :>> key = "guard-support"; attribute :>> avoided = "Share generated normal/abnormal completion metadata across Scheme, FFI and native entry boundaries"; attribute :>> added = "Completion guard records, catcher-stack integration, exactly-once settlement and unknown-result query"; attribute :>> condition = "Reuse must cover longjmp and multi-shot re-entry; ordinary local cleanup flag or lexical return is insufficient"; }
 part gain3 : Gain { attribute :>> key = "c-baseline"; attribute :>> avoided = "Modern C reuses existing GVM roots, host masks, markers and Scheme continuation semantics"; attribute :>> added = "Typed session/handle contract and C memory-model plus configuration/provenance obligations"; attribute :>> condition = "No measured throughput or build gain; Zig cannot remove these obligations and no additional net benefit is established"; }
 part def Gate { attribute key : String; attribute qualified : Boolean; attribute duty : String; }
 part gate0 : Gate { attribute :>> key = "darwin-artifact-match"; attribute :>> qualified = false; attribute :>> duty = "Installed driver/header statically pinned; effective argv, environment overrides, compiler macro identity and checked-in _kernel.c/object relation unresolved"; }
 part gate1 : Gate { attribute :>> key = "smp-profile"; attribute :>> qualified = false; attribute :>> duty = "Installed header defaults to single-threaded VM; not qualification of current SMP processor roster or native ABI"; }
 part gate2 : Gate { attribute :>> key = "restore-graph"; attribute :>> qualified = false; attribute :>> duty = "Exact R1/SELF masks, same-host and host-switch, catcher stacks, generated return and exceptional edges complete"; }
 part gate3 : Gate { attribute :>> key = "unwind-cleanup"; attribute :>> qualified = false; attribute :>> duty = "Every throw/escape caller invalidates markers and settles roots exactly once; existing lexical cleanup is not sufficient proof"; }
 part gate4 : Gate { attribute :>> key = "continuation-export"; attribute :>> qualified = false; attribute :>> duty = "All external continuation holders and invocation leases registered without VM self-retention cycle; processor/arena migration proof"; }
 part gate5 : Gate { attribute :>> key = "c11-publication"; attribute :>> qualified = false; attribute :>> duty = "Execution lease establishment before immutable handoff publication and claim decrement; full C/builtin-setjmp refinement open"; }
 part gate6 : Gate { attribute :>> key = "native-retirement"; attribute :>> qualified = false; attribute :>> duty = "Parent root/roster/OS cleanup and inherited host attestation unresolved; no native admission"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Six literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "DRC-H"; attribute :>> kind = "interleaving"; attribute :>> subjectPath = "models/build/decrement_restore_closure.qnt"; attribute :>> subjectScope = "safe: two guarded activations, session handoff, catch and marker completion, multi-shot export and current-processor admission"; attribute :>> premise = "Static declared SDK configuration is not matched SMP/native acceptance; abnormal guard and exported handle protocols are proposed"; }
 part induction : GambitAssuranceRouting::ModelNeed { ref part :>> owner = GambitBuildAssurance::planner.component; attribute :>> obligationId = "DRC-I"; attribute :>> kind = "induction"; attribute :>> subjectPath = "models/build/DecrementRestoreClosure.lean"; attribute :>> subjectScope = "handoff restoration coverage induction and distinct VM versus processor continuation lifetime"; attribute :>> premise = "Static declared SDK configuration is not matched SMP/native acceptance; abnormal guard and exported handle protocols are proposed"; }
 part source : GambitAssuranceRouting::ModelNeed { ref part :>> owner = GambitBuildAssurance::planner.component; attribute :>> obligationId = "DRC-S"; attribute :>> kind = "source-refinement"; attribute :>> subjectPath = "dev/architecture/toolchain/decrement-restore-closure-design.org"; attribute :>> subjectScope = "actual host/call/catcher/marker/continuation paths plus installed Darwin declarations and provenance gaps"; attribute :>> premise = "Static declared SDK configuration is not matched SMP/native acceptance; abnormal guard and exported handle protocols are proposed"; }
 part platform : GambitAssuranceRouting::ModelNeed { ref part :>> owner = GambitBuildAssurance::planner.component; attribute :>> obligationId = "DRC-E"; attribute :>> kind = "environment-refinement"; attribute :>> subjectPath = "dev/architecture/toolchain/decrement-restore-closure-design.org"; attribute :>> subjectScope = "effective Darwin argv and generated artifact, C11 publication and builtin-setjmp semantics"; attribute :>> premise = "Static declared SDK configuration is not matched SMP/native acceptance; abnormal guard and exported handle protocols are proposed"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = GateEmptyRootMaterialization::source; }
 part def ContractDependency { ref part dependent : Contract; ref part prerequisite : Contract; attribute reason : String; }
 part edge0 : ContractDependency { ref part :>> dependent = contract0; ref part :>> prerequisite = contract1; attribute :>> reason = "Execution owner established before published handoff release"; }
 part edge1 : ContractDependency { ref part :>> dependent = contract2; ref part :>> prerequisite = contract0; attribute :>> reason = "After claim decrement PSTATE use needs other owner"; }
 part edge2 : ContractDependency { ref part :>> dependent = contract4; ref part :>> prerequisite = contract2; attribute :>> reason = "Host restoration can reach catch and caller tail"; }
 part edge3 : ContractDependency { ref part :>> dependent = contract5; ref part :>> prerequisite = contract4; attribute :>> reason = "Catch completion is not abnormal marker completion"; }
 part edge4 : ContractDependency { ref part :>> dependent = contract7; ref part :>> prerequisite = contract5; attribute :>> reason = "Leaf release follows normal or abnormal boundary settlement"; }
 part edge5 : ContractDependency { ref part :>> dependent = contract6; ref part :>> prerequisite = contract5; attribute :>> reason = "Dead C marker does not remove continuation restore obligation"; }
 part edge6 : ContractDependency { ref part :>> dependent = contract3; ref part :>> prerequisite = contract6; attribute :>> reason = "Export and invocation can retain old VM after original processor exits"; }
 part edge7 : ContractDependency { ref part :>> dependent = contract3; ref part :>> prerequisite = contract7; attribute :>> reason = "Native return settlement precedes execution-owner retirement"; }
 part edge8 : ContractDependency { ref part :>> dependent = contract7; ref part :>> prerequisite = contract4; attribute :>> reason = "Leaf completion requires catcher restoration before caller tail settles"; }
 part edge9 : ContractDependency { ref part :>> dependent = contract3; ref part :>> prerequisite = contract1; attribute :>> reason = "Final retirement excludes all execution owners"; }
}
