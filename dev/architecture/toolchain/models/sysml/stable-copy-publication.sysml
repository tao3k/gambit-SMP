package StableCopyPublication {
 private import ScalarValues::*;
 part def WriterSpec { attribute key : String; attribute anchor : String; attribute condition : String; }
 part writer0 : WriterSpec { attribute :>> key = "macro-eval"; attribute :>> anchor = "_ptree1.scm:2931-2962; _host.scm:852-853"; attribute :>> condition = "Actual macro definition evaluates code; extension effects require resolved binding/capability closure; iter registry mutation is not established"; }
 part writer1 : WriterSpec { attribute :>> key = "macro-call"; attribute :>> anchor = "_ptree1.scm:1004-1012"; attribute :>> condition = "Actual expander callback can call retained procedures or mutate reachable pairs; do not hold a nonreentrant sealing lock across it"; }
 part writer2 : WriterSpec { attribute :>> key = "global-store"; attribute :>> anchor = "_eval.scm:2079-2104,3417-3434,532-533"; attribute :>> condition = "Interpreter set! routes to global store; qualified compiler binding reachability remains profile-specific"; }
 part writer3 : WriterSpec { attribute :>> key = "payload-store"; attribute :>> anchor = "_env.scm:327-343; _t-c-2.scm:3737-3738; gambit.h.in:5328-5329,5482"; attribute :>> condition = "Borrowed names and exposed records can reach direct pair/vector writes; helper interception alone cannot close arbitrary aliases"; }
 part writer4 : WriterSpec { attribute :>> key = "namespace"; attribute :>> anchor = "gsc/makefile.in:255; gsc/fixnum.scm:382-425"; attribute :>> condition = "c# is the compiler namespace and includes registry/helper/accessor names; spelling does not itself prove an admitted runtime binding"; }
 part def CopySpec { attribute key : String; attribute anchor : String; attribute condition : String; }
 part copy0 : CopySpec { attribute :>> key = "source-conversion"; attribute :>> anchor = "_source.scm:267-324"; attribute :>> condition = "Visited-table private copy preserves cycles/sharing but is not a stable snapshot or a generic declaration freezer"; }
 part copy1 : CopySpec { attribute :>> key = "exclusive-copy"; attribute :>> anchor = "proposed managed contract"; attribute :>> condition = "Close every writer before read; pin source and privately rooted destination; copy under exclusion with no arbitrary callback"; }
 part copy2 : CopySpec { attribute :>> key = "immutable-generation"; attribute :>> anchor = "proposed managed contract"; attribute :>> condition = "Capture complete immutable registry/view generation and roots; concurrent writers create new generations without changing captured data"; }
 part copy3 : CopySpec { attribute :>> key = "release-cut"; attribute :>> anchor = "proposed managed contract"; attribute :>> condition = "After complete identity-preserving private copy, source custody can retire before publication; result key stays the captured generation"; }
 part copy4 : CopySpec { attribute :>> key = "raw-optimism"; attribute :>> anchor = "gambit.h.in:5328-5329; proposed admission"; attribute :>> condition = "A version comparison does not legalize plain C data races, uncounted alias writes, ABA or incomplete writer updates"; }
 part def RouteSpec { attribute key : String; attribute anchor : String; attribute qntAction : String; attribute leanLemma : String; attribute condition : String; }
 part route0 : RouteSpec { attribute :>> key = "stable-acquisition"; attribute :>> anchor = "_env.scm:290-314; _source.scm:278-304"; attribute :>> qntAction = "acquire"; attribute :>> leanLemma = "exclusiveBlocksWriter"; attribute :>> condition = "Capture coherent registry/view under excluded writers or an immutable-generation lease"; }
 part route1 : RouteSpec { attribute :>> key = "copy-prefix"; attribute :>> anchor = "_env.scm:327-331; _source.scm:278-304"; attribute :>> qntAction = "copyTail"; attribute :>> leanLemma = "copyEquality"; attribute :>> condition = "Partial graph cannot certify semantic payload equality; source and destination roots retained"; }
 part route2 : RouteSpec { attribute :>> key = "ownership-cut"; attribute :>> anchor = "_env.scm:102-127; proposed service seam"; attribute :>> qntAction = "releaseSource"; attribute :>> leanLemma = "releasePreservesCopy"; attribute :>> condition = "Release only after independent owned copy; raw aliases/native pins are not covered"; }
 part route3 : RouteSpec { attribute :>> key = "publication"; attribute :>> anchor = "_ptree1.scm:347-378; _prims.scm:1793-1835"; attribute :>> qntAction = "publishResult"; attribute :>> leanLemma = "generationMismatch"; attribute :>> condition = "Publish old generation under its own request key; never rekey to current source generation"; }
 part route4 : RouteSpec { attribute :>> key = "abandonment"; attribute :>> anchor = "_ptree1.scm:1004-1012,2954-2962; proposed service seam"; attribute :>> qntAction = "abortAttempt"; attribute :>> leanLemma = "taintBlocksPublication"; attribute :>> condition = "Exceptions/unknown continuation delivery retain holders until explicit retirement; stale saved PCs cannot mint receipts"; }
 part def GainSpec { attribute key : String; attribute avoided : String; attribute added : String; attribute condition : String; }
 part gain0 : GainSpec { attribute :>> key = "stable-service-input"; attribute :>> avoided = "Repeated reconstruction or global serialization for qualified contexts"; attribute :>> added = "Writer inventory, immutable identity, read/copy custody and admission guards"; attribute :>> condition = "Reuse only if saved work exceeds sealing/key/materialization and invalidation cost"; }
 part gain1 : GainSpec { attribute :>> key = "early-source-release"; attribute :>> avoided = "Keeping all mutable inputs locked until downstream publication"; attribute :>> added = "Private owned copy and completion receipt"; attribute :>> condition = "Copy cost and destination retention must be smaller than removed contention/retention"; }
 part gain2 : GainSpec { attribute :>> key = "immutable-sharing"; attribute :>> avoided = "Repeated names/registry copying for matching consumers"; attribute :>> added = "Immutable generation roots and old-generation drain"; attribute :>> condition = "Benefit depends on actual demand and bounded retained generations; unsafe raw aliases deny sharing"; }
 part def RefinementSpec { attribute key : String; attribute qntScope : String; attribute leanScope : String; attribute sourceDuty : String; }
 part refinement0 : RefinementSpec { attribute :>> key = "stable-copy"; attribute :>> qntScope = "acquire;copyHead;copyTail"; attribute :>> leanScope = "exclusiveBlocksWriter;copyEquality;tornCounterexample"; attribute :>> sourceDuty = "Exact symbol/record graph simulation plus stable C reads and complete writer closure"; }
 part refinement1 : RefinementSpec { attribute :>> key = "commit"; attribute :>> qntScope = "validateCopy;publishResult"; attribute :>> leanScope = "generationMismatch;noABA"; attribute :>> sourceDuty = "Atomic metadata/key publication, no stale completion or counter wrap assumption"; }
 part refinement2 : RefinementSpec { attribute :>> key = "retire"; attribute :>> qntScope = "releaseSource;abortAttempt;drain"; attribute :>> leanScope = "releasePreservesCopy;taintBlocksPublication"; attribute :>> sourceDuty = "GC roots, native borrowers, exceptions and multishot continuation lifetimes"; }
 part refinement3 : RefinementSpec { attribute :>> key = "benefit"; attribute :>> qntScope = "publishResult"; attribute :>> leanScope = "costPositive"; attribute :>> sourceDuty = "Observed demand/work/span and actual modern C consumer migration"; }
 part def GateSpec { attribute key : String; attribute qualified : Boolean; attribute condition : String; }
 part gate0 : GateSpec { attribute :>> key = "indirect-writers"; attribute :>> qualified = false; attribute :>> condition = "Profile-specific macro/eval/global/pair/native reachability closure"; }
 part gate1 : GateSpec { attribute :>> key = "stable-c-read"; attribute :>> qualified = false; attribute :>> condition = "Exclusive writer discipline or immutable publication with actual C memory-order proof"; }
 part gate2 : GateSpec { attribute :>> key = "graph-copy"; attribute :>> qualified = false; attribute :>> condition = "Complete graph/symbol identity, allocation and exception refinement"; }
 part gate3 : GateSpec { attribute :>> key = "publication"; attribute :>> qualified = false; attribute :>> condition = "Atomic captured-key output publication and independent stale receipt validation"; }
 part gate4 : GateSpec { attribute :>> key = "continuation"; attribute :>> qualified = false; attribute :>> condition = "Saved PCs/native holders and unknown delivery cannot outlive root custody"; }
 part gate5 : GateSpec { attribute :>> key = "retirement"; attribute :>> qualified = false; attribute :>> condition = "Old registry/helper/borrowed-list authority removed after all real consumers migrate"; }
 part gate6 : GateSpec { attribute :>> key = "platform"; attribute :>> qualified = false; attribute :>> condition = "Runtime/native/host attestation and measured work/span/memory remain unqualified"; }
 attribute workspaceCount : Integer = 2;
 attribute actualAdmitted : Boolean = false;
 part history : GambitAssuranceRouting::ModelNeed { ref part :>> owner = GambitBuildAssurance::planner.component; attribute :>> obligationId = "SC-H"; attribute :>> kind = "interleaving"; attribute :>> subjectPath = "models/build/stable_copy_publication.qnt"; attribute :>> subjectScope = "stable_copy_publication:Test$"; attribute :>> premise = "Conditional source correspondence; local checks do not establish native writer/lifetime closure"; }
 part induction : GambitAssuranceRouting::ModelNeed { ref part :>> owner = GambitBuildAssurance::planner.component; attribute :>> obligationId = "SC-I"; attribute :>> kind = "induction"; attribute :>> subjectPath = "models/build/StableCopyPublication.lean"; attribute :>> subjectScope = "StableCopyPublication:exclusiveBlocksWriter;copyEquality;tornCounterexample;releasePreservesCopy;generationMismatch;noABA;taintBlocksPublication;costPositive"; attribute :>> premise = "Conditional source correspondence; local checks do not establish native writer/lifetime closure"; }
 part source : GambitAssuranceRouting::ModelNeed { ref part :>> owner = GambitBuildAssurance::planner.component; attribute :>> obligationId = "SC-S"; attribute :>> kind = "source-refinement"; attribute :>> subjectPath = "dev/architecture/toolchain/stable-copy-publication-design.org"; attribute :>> subjectScope = "SC-S:source"; attribute :>> premise = "Conditional source correspondence; local checks do not establish native writer/lifetime closure"; }
 part platform : GambitAssuranceRouting::ModelNeed { ref part :>> owner = GambitBuildAssurance::planner.component; attribute :>> obligationId = "SC-E"; attribute :>> kind = "environment-refinement"; attribute :>> subjectPath = "dev/architecture/toolchain/stable-copy-publication-design.org"; attribute :>> subjectScope = "SC-E:platform"; attribute :>> premise = "Conditional source correspondence; local checks do not establish native writer/lifetime closure"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = RegistryViewSealing::source; }
}
