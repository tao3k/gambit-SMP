package WillDomainMigration {
 private import ScalarValues::*;
 part def CallerSpec { attribute key : String; attribute anchor : String; attribute condition : String; }
 part caller0 : CallerSpec { attribute :>> key = "registration-and-writers"; attribute :>> anchor = "gambit.h.in:5997-6027; _t-c-2.scm:2668-2675,3786-3790"; attribute :>> condition = "MAKEWILL prepends movable will to current PSTATE nonexec list; raw field setters and explicit execution are distinct managed writers"; }
 part caller1 : CallerSpec { attribute :>> key = "decision-and-rebuild"; attribute :>> anchor = "mem.c:3990-3998,4039-4064,4997-5105"; attribute :>> condition = "Testator must be memory allocated and unmarked; follow forwarding before reading; preserve tagged next flags and rebuild moved list heads"; }
 part caller2 : CallerSpec { attribute :>> key = "automatic-and-explicit"; attribute :>> anchor = "mem.c:7054-7071; _kernel.scm:2082-2116,2153-2162; _nonstd.scm:1892-1895"; attribute :>> condition = "Current GC raises interrupt only on p0; finalizer pops current PSTATE list; public explicit execution need not wait for eligibility; Scheme owns action context"; }
 part caller3 : CallerSpec { attribute :>> key = "shutdown-and-real-users"; attribute :>> anchor = "_kernel.scm:2118-2151,4722-4728; std/db/sqlite.ss:35-74; srfi/124/124.scm:56-65"; attribute :>> condition = "Exit final-will FIFO is separate; real SQLite and ephemeron callbacks mutate resources/state and require explicit context and failure policy"; }
 part caller4 : CallerSpec { attribute :>> key = "processor-exit"; attribute :>> anchor = "setup.c:918-978; mem.c:308-309,4685-4689,6896-6900"; attribute :>> condition = "Storage handoff does not transfer semantic weak membership; creator exit must preserve both lists, pending work and rooted action frames"; }
 part def ProtocolSpec { attribute key : String; attribute anchor : String; attribute condition : String; }
 part protocol0 : ProtocolSpec { attribute :>> key = "weak-domain-transfer"; attribute :>> anchor = "mem.c:243-249,308-309; proposed migration"; attribute :>> condition = "Same VM weak-domain membership, not ordinary strong RootRegistry payload; close producers and list consumers; exact durable transfer before creator cleanup"; }
 part protocol1 : ProtocolSpec { attribute :>> key = "strong-decision-cut"; attribute :>> anchor = "mem.c:4997-5046,6896-6900"; attribute :>> condition = "Freeze strong reachability for every relevant decision; prevent earlier weak marking from changing later eligibility; cross-domain source refinement remains open"; }
 part protocol2 : ProtocolSpec { attribute :>> key = "moving-list-rebuild"; attribute :>> anchor = "mem.c:5011-5014,5061-5104"; attribute :>> condition = "Preserve per-origin list sequence and tag semantics; rewrite heads and links after forwarding; keep weak-derived work until completion receipt"; }
 part protocol3 : ProtocolSpec { attribute :>> key = "dispatch-and-capture"; attribute :>> anchor = "_kernel.scm:2087-2115; _nonstd.scm:1892-1895"; attribute :>> condition = "Pop acquires rooted action frame; capture testator/action before clearing; no safepoint in unprotected pop-to-capture quantum; Scheme context executes action"; }
 part protocol4 : ProtocolSpec { attribute :>> key = "continuation-and-shutdown"; attribute :>> anchor = "_kernel.scm:2110-2151,4722-4728"; attribute :>> condition = "Cleared fields forbid fresh dispatch of same payload but continuations may repeat body effects; escaped roots remain owned; no timeout-based retirement or destructor equivalence"; }
 part def RouteSpec { attribute key : String; attribute anchor : String; attribute qntAction : String; attribute leanLemma : String; attribute condition : String; }
 part route0 : RouteSpec { attribute :>> key = "registration"; attribute :>> anchor = "gambit.h.in:6014-6021; mem.c:308-309"; attribute :>> qntAction = "transfer"; attribute :>> leanLemma = "writerBlocksTransfer"; attribute :>> condition = "Exact weak membership survives source exit without upgrading list nodes to strong roots"; }
 part route1 : RouteSpec { attribute :>> key = "decision"; attribute :>> anchor = "mem.c:5011-5026; 5046"; attribute :>> qntAction = "decide"; attribute :>> leanLemma = "strongNotEligible"; attribute :>> condition = "Decide from immutable strong snapshot plus allocated testator predicate; weak preservation is a later phase"; }
 part route2 : RouteSpec { attribute :>> key = "coverage"; attribute :>> anchor = "mem.c:5061-5104; 6898-6900"; attribute :>> qntAction = "rebuild"; attribute :>> leanLemma = "oldHeadInvalid"; attribute :>> condition = "Rebuild forwarding-aware heads/links and preserve order; all weak-derived work must settle before finish"; }
 part route3 : RouteSpec { attribute :>> key = "execution"; attribute :>> anchor = "_kernel.scm:2087-2115; _nonstd.scm:1892-1895"; attribute :>> qntAction = "captureAndClear"; attribute :>> leanLemma = "clearedNoFreshCall"; attribute :>> condition = "Protect captures before clearing shared will fields; explicit and automatic callers share controlled admission"; }
 part route4 : RouteSpec { attribute :>> key = "retirement"; attribute :>> anchor = "_kernel.scm:2113-2115,4722-4728; setup.c:930-933"; attribute :>> qntAction = "retireContinuation"; attribute :>> leanLemma = "retainedCapture"; attribute :>> condition = "Source-bound frames/continuations prevent unsafe departure; safe retirement requires independently proved no-future-resume evidence"; }
 part def GainSpec { attribute key : String; attribute avoided : String; attribute added : String; attribute condition : String; }
 part gain0 : GainSpec { attribute :>> key = "weak-membership"; attribute :>> avoided = "Creator affinity and duplicated rediscovery solely needed to preserve per-PSTATE will lists"; attribute :>> added = "Typed VM weak domains, epoch membership, forwarding-aware list rewrite and publication receipts"; attribute :>> condition = "Positive work benefit only if removed affinity/reconstruction exceeds metadata; all required weak scans remain"; }
 part gain1 : GainSpec { attribute :>> key = "action-ownership"; attribute :>> avoided = "Lost or ambiguous action dispatch responsibility when creator exits"; attribute :>> added = "Scheme execution lane, explicit-call synchronization, capture roots and continuation custody"; attribute :>> condition = "May reduce critical-path affinity; arbitrary action context, resource ordering and escaped frames can negate parallel gain"; }
 part gain2 : GainSpec { attribute :>> key = "single-authority"; attribute :>> avoided = "Independent old list head and new VM head mutating same membership"; attribute :>> added = "One root/classification/dispatch authority; separate final FIFO obligations and resource admission"; attribute :>> condition = "Modern C can express full contract; Zig supplies no demonstrated unique semantic saving; no speedup asserted"; }
 part def RefinementSpec { attribute key : String; attribute qntScope : String; attribute leanScope : String; attribute sourceDuty : String; }
 part refinement0 : RefinementSpec { attribute :>> key = "migration"; attribute :>> qntScope = "closeAdmission;transfer;depart"; attribute :>> leanScope = "writerBlocksTransfer;continuationBlocksTransfer"; attribute :>> sourceDuty = "All registration, raw setters, direct execution, GC roots and list consumers mediated; exact commit and unknown result custody inherited from storage/root design"; }
 part refinement1 : RefinementSpec { attribute :>> key = "eligibility"; attribute :>> qntScope = "beginGC;decide;rebuild;scanWeak;endGC"; attribute :>> leanScope = "immediateNotEligible;strongNotEligible;weakNotStrong;pendingBlocksFinish;oldHeadInvalid;appendPreservesOldPrefix"; attribute :>> sourceDuty = "Movable/forwarded will links and strong reachability epoch; cross-domain decision barrier or immutable classification; weak body work and termination refine to real collector"; }
 part refinement2 : RefinementSpec { attribute :>> key = "action"; attribute :>> qntScope = "popExecutable;explicitClaim;captureAndClear;invoke"; attribute :>> leanScope = "clearedNoFreshCall;resumedEffectsMayRepeat"; attribute :>> sourceDuty = "Execution context, interrupt/no-safepoint quantum, strong captured roots and exact explicit-call order; no assertion of exactly-once action effects"; }
 part refinement3 : RefinementSpec { attribute :>> key = "lifetime"; attribute :>> qntScope = "captureContinuation;returnAction;resume;retireContinuation"; attribute :>> leanScope = "retainedCapture;netBenefit"; attribute :>> sourceDuty = "Actual exceptions, dynamic-wind/multi-shot continuation roots, resource owner affinity and shutdown drain remain source/native obligations"; }
 part def GateSpec { attribute key : String; attribute qualified : Boolean; attribute condition : String; }
 part gate0 : GateSpec { attribute :>> key = "producer-closure"; attribute :>> qualified = false; attribute :>> condition = "All generated MAKEWILL, internal field setters, explicit calls, GC and final registry writers classified and mediated"; }
 part gate1 : GateSpec { attribute :>> key = "vm-ownership"; attribute :>> qualified = false; attribute :>> condition = "Weak-domain heads and action contexts preserved independently of creator and still storage; no accidental strong rooting"; }
 part gate2 : GateSpec { attribute :>> key = "gc-seal"; attribute :>> qualified = false; attribute :>> condition = "Cross-domain strong snapshot versus weak-mark interference and real forwarding/termination/C memory order refined"; }
 part gate3 : GateSpec { attribute :>> key = "scan-coverage"; attribute :>> qualified = false; attribute :>> condition = "List flags/order, copied will roots, captured frame relocation and weak-derived work covered; old source ordering not assumed equivalent"; }
 part gate4 : GateSpec { attribute :>> key = "retirement"; attribute :>> qualified = false; attribute :>> condition = "Exception and multi-shot continuation root retirement, native action affinity, unknown handoff and shutdown closure proved"; }
 part gate5 : GateSpec { attribute :>> key = "source-replacement"; attribute :>> qualified = false; attribute :>> condition = "Per-PSTATE registration/weak walk/pop authorities retired only after all accepted managed users migrate"; }
 part gate6 : GateSpec { attribute :>> key = "platform"; attribute :>> qualified = false; attribute :>> condition = "Actual configured GC/interrupts/ABI, host attestation, native correctness and measured benefit remain open"; }
 attribute workspaceCount : Integer = 2;
 attribute actualAdmitted : Boolean = false;
 part history : GambitAssuranceRouting::ModelNeed { ref part :>> owner = GambitBuildAssurance::planner.component; attribute :>> obligationId = "WM-H"; attribute :>> kind = "interleaving"; attribute :>> subjectPath = "models/build/will_domain_migration.qnt"; attribute :>> subjectScope = "will_domain_migration:Test$"; attribute :>> premise = "Conditional movable will weak-domain and Scheme action contract; actual source/native qualification remains open"; }
 part induction : GambitAssuranceRouting::ModelNeed { ref part :>> owner = GambitBuildAssurance::planner.component; attribute :>> obligationId = "WM-I"; attribute :>> kind = "induction"; attribute :>> subjectPath = "models/build/WillDomainMigration.lean"; attribute :>> subjectScope = "WillDomainMigration:immediateNotEligible;strongNotEligible;weakNotStrong;writerBlocksTransfer;continuationBlocksTransfer;pendingBlocksFinish;clearedNoFreshCall;resumedEffectsMayRepeat;oldHeadInvalid;appendPreservesOldPrefix;retainedCapture;netBenefit"; attribute :>> premise = "Conditional movable will weak-domain and Scheme action contract; actual source/native qualification remains open"; }
 part source : GambitAssuranceRouting::ModelNeed { ref part :>> owner = GambitBuildAssurance::planner.component; attribute :>> obligationId = "WM-S"; attribute :>> kind = "source-refinement"; attribute :>> subjectPath = "dev/architecture/toolchain/will-domain-migration-design.org"; attribute :>> subjectScope = "WM-S:source"; attribute :>> premise = "Conditional movable will weak-domain and Scheme action contract; actual source/native qualification remains open"; }
 part platform : GambitAssuranceRouting::ModelNeed { ref part :>> owner = GambitBuildAssurance::planner.component; attribute :>> obligationId = "WM-E"; attribute :>> kind = "environment-refinement"; attribute :>> subjectPath = "dev/architecture/toolchain/will-domain-migration-design.org"; attribute :>> subjectScope = "WM-E:platform"; attribute :>> premise = "Conditional movable will weak-domain and Scheme action contract; actual source/native qualification remains open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = VMArenaCollector::source; }
}
