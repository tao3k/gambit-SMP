package AliasWorkspaceReconstruction {
 private import ScalarValues::*;
 part def AliasSpec { attribute key : String; attribute anchor : String; attribute path : String; attribute rebuild : String; attribute gap : String; }
 part alias0 : AliasSpec { attribute :>> key = "target-capture"; attribute :>> anchor = "_back.scm:171-189; _t-c-1.scm:243-277"; attribute :>> path = "registry -> target vector -> default label/jump closures -> original targ"; attribute :>> rebuild = "Allocate private target shell first; install providers bound to the new shell"; attribute :>> gap = "All higher-order target extras and dynamically registered providers still require census"; }
 part alias1 : AliasSpec { attribute :>> key = "primitive-self"; attribute :>> anchor = "_gvm.scm:165-190; _back.scm:288-301"; attribute :>> path = "primitive table -> proc vector -> specialize closure -> same proc vector"; attribute :>> rebuild = "Preserve self cycle by a workspace-wide relocation map; rebuild closure using private proc handle"; attribute :>> gap = "Copying a vector or closure code pointer alone cannot retarget its environment"; }
 part alias2 : AliasSpec { attribute :>> key = "cross-primitive"; attribute :>> anchor = "_prims.scm:1790-1835"; attribute :>> path = "def-spec -> specializer-maker -> get-prim-info -> spec/proc/specs captured objects"; attribute :>> rebuild = "Allocate all primitive shells before wiring same-context specialization edges"; attribute :>> gap = "Safe/unsafe, nargs and arithmetic/environment-dependent choices retain behavior and order"; }
 part alias3 : AliasSpec { attribute :>> key = "inline-context"; attribute :>> anchor = "_t-c-2.scm:934-941,2870-2884"; attribute :>> path = "GVM primitive -> inline closure -> target emitter/frame/global state"; attribute :>> rebuild = "Rebuild approved provider with explicit private emission-context capability"; attribute :>> gap = "Current closures call global targ routines; a private table alone does not isolate those routines"; }
 part alias4 : AliasSpec { attribute :>> key = "canonical-tag"; attribute :>> anchor = "_gvm.scm:192-197"; attribute :>> path = "proc vector slot zero -> proc-obj-tag; proc-obj? compares eq?"; attribute :>> rebuild = "Reconstruct the destination canonical type tag rather than duplicating its list"; attribute :>> gap = "Never infer runtime instance equality merely from equal semantic names"; }
 part alias5 : AliasSpec { attribute :>> key = "gvm-cintf"; attribute :>> anchor = "_front.scm:785-823; _t-c-1.scm:337-346,764-775"; attribute :>> path = "GVM/constants and c-intf/queues retain references to procedures and foreign metadata"; attribute :>> rebuild = "One relocation domain covers procedures, operands, constants and consumed C-interface payloads"; attribute :>> gap = "Nested foreign objects, raw writes and unknown closures remain nontransferable"; }
 part def ProviderSpec { attribute key : String; attribute captured : String; attribute semantics : String; attribute anchor : String; }
 part provider0 : ProviderSpec { attribute :>> key = "target-calling"; attribute :>> captured = "target ObjectId + label/jump signature"; attribute :>> semantics = "Recreate default-label-info/default-jump-info closure bound to the new target"; attribute :>> anchor = "_back.scm:181-189"; }
 part provider1 : ProviderSpec { attribute :>> key = "self-specializer"; attribute :>> captured = "self primitive ObjectId"; attribute :>> semantics = "Return destination self, not a source object"; attribute :>> anchor = "_gvm.scm:189"; }
 part provider2 : ProviderSpec { attribute :>> key = "safe-specializer"; attribute :>> captured = "selected primitive ObjectId"; attribute :>> semantics = "Return destination selected primitive"; attribute :>> anchor = "_prims.scm:1798-1801"; }
 part provider3 : ProviderSpec { attribute :>> key = "unsafe-specializer"; attribute :>> captured = "self + selected primitive ObjectIds"; attribute :>> semantics = "Preserve safe? environment branch before choosing destination primitive"; attribute :>> anchor = "_prims.scm:1803-1806"; }
 part provider4 : ProviderSpec { attribute :>> key = "nargs-specializer"; attribute :>> captured = "self + ordered optional primitive ObjectIds"; attribute :>> semantics = "Preserve argument-count indexing, missing entry and self fallback"; attribute :>> anchor = "_prims.scm:1808-1816"; }
 part provider5 : ProviderSpec { attribute :>> key = "arith-specializer"; attribute :>> captured = "self + proc-name + fix/flo/unsafe primitive ObjectIds"; attribute :>> semantics = "Preserve declaration-sensitive arithmetic, safe? and eq? branch semantics"; attribute :>> anchor = "_prims.scm:1818-1835"; }
 part provider6 : ProviderSpec { attribute :>> key = "force-inline"; attribute :>> captured = "approved provider body identity + emission context capability"; attribute :>> semantics = "Rebind frame/label/emission operations to private context; no assumed generic closure copy"; attribute :>> anchor = "_t-c-2.scm:2870-2884"; }
 part provider7 : ProviderSpec { attribute :>> key = "ordered-folders"; attribute :>> captured = "ordered qualified folder records and their own ObjectId captures"; attribute :>> semantics = "Preserve first successful folder and exception/effect order; unknown folder denies transfer"; attribute :>> anchor = "_prims.scm:6249-6261"; }
 part def PhaseSpec { attribute key : String; attribute precondition : String; attribute actionContract : String; attribute failureCustody : String; }
 part phase0 : PhaseSpec { attribute :>> key = "classify"; attribute :>> precondition = "Writer admission closed; admitted writers settled; graph/profile/cohort known"; attribute :>> actionContract = "Separate immutable data, relocated mutable nodes, canonical tags and approved provider recipes"; attribute :>> failureCustody = "Unknown provider/native closure denies reusable snapshot; retain live owned path if otherwise safe"; }
 part phase1 : PhaseSpec { attribute :>> key = "allocate-shells"; attribute :>> precondition = "Snapshot rooted; target and primitive identity inventory complete"; attribute :>> actionContract = "Allocate all destination shells in one private rooted arena; define injective ObjectId to handle map"; attribute :>> failureCustody = "Partial arena remains owned; snapshot and destination roots coexist until cleanup settles"; }
 part phase2 : PhaseSpec { attribute :>> key = "wire-graph"; attribute :>> precondition = "All referenced ObjectIds allocated"; attribute :>> actionContract = "Patch graph sharing/cycles, canonical tags and all GVM/C-interface references through one map"; attribute :>> failureCustody = "Unresolved reference aborts before publication; no fallback to old source address"; }
 part phase3 : PhaseSpec { attribute :>> key = "bind-providers"; attribute :>> precondition = "Approved provider ID, captured-record schema and semantic profile match"; attribute :>> actionContract = "Generate self/cross-primitive and target/frame behavior bound to destination handles/context"; attribute :>> failureCustody = "No generic Scheme closure serialization; unknown result retains arena and execution custody"; }
 part phase4 : PhaseSpec { attribute :>> key = "validate"; attribute :>> precondition = "No source mutable edges; declarations/identity/origin/outcome observations match"; attribute :>> actionContract = "Validate mapping, provider coverage and observational projection; close construction authority"; attribute :>> failureCustody = "A source fingerprint is not itself a semantic equivalence proof"; }
 part phase5 : PhaseSpec { attribute :>> key = "publish"; attribute :>> precondition = "Destination initialized; attempt current; private roots/borrows accounted"; attribute :>> actionContract = "Publish ready workspace once, then allow destructive C emission using private payloads"; attribute :>> failureCustody = "Failure/unknown never publishes success; settle callbacks before arena release"; }
 part def FidelitySpec { attribute key : String; attribute baseline : String; attribute reconstruction : String; attribute unresolved : String; }
 part fidelity0 : FidelitySpec { attribute :>> key = "identity"; attribute :>> baseline = "iter for1 syntax/loc and Gerbil namespace/phi/gensym/mark reconstruction"; attribute :>> reconstruction = "Preserve equality and distinction inside a session; fresh mutable instances across sessions; stable names are not eq?"; attribute :>> unresolved = "Complete macro/prelude/initializer closure and real binder reconstruction relation"; }
 part fidelity1 : FidelitySpec { attribute :>> key = "origin"; attribute :>> baseline = "Generated UTF-8/LF Scheme reader view plus original expansion provenance where available"; attribute :>> reconstruction = "Carry generated-view locations separately from optional original-source map; retain source in abort diagnostics"; attribute :>> unresolved = "Direct datum/sourcify input is not assumed reader-equivalent"; }
 part fidelity2 : FidelitySpec { attribute :>> key = "declarations"; attribute :>> baseline = "Ordered scoped declarations, module reset and positive-phase inlining policy"; attribute :>> reconstruction = "Rebuild the same scoped declaration tree before selecting semantic target profile"; attribute :>> unresolved = "No scope flattening or signature-only macro cutoff"; }
 part fidelity3 : FidelitySpec { attribute :>> key = "exceptions"; attribute :>> baseline = "Gerbil raise-compile-error / invoke status and phase-specific output delivery"; attribute :>> reconstruction = "Provider/patch failure produces admitted observer-compatible outcome; original resources stay owned until settled"; attribute :>> unresolved = "Native exception identity, continuation and stack transport are not generically transferable"; }
 part def GainSpec { attribute key : String; attribute removed : String; attribute added : String; attribute positiveCondition : String; }
 part gain0 : GainSpec { attribute :>> key = "shared-template"; attribute :>> removed = "Repeated admitted declarative preparation and frontend lowering across k uses"; attribute :>> added = "Freeze Fz + k*(primitive/provider reconstruction R + relocation L) + validation V"; attribute :>> positiveCondition = "(k-1)*avoidedFront > Fz + k*(R+L) + V; raw closure copy has no automatic saving"; }
 part gain1 : GainSpec { attribute :>> key = "private-parallelism"; attribute :>> removed = "Serialization caused only by global target/primitive/emission authority"; attribute :>> added = "Private arenas/overlays, snapshot roots, coordination and potential IPC"; attribute :>> positiveCondition = "Removed critical-path delay exceeds added reconstruction/coordination; runtime SMP qualified separately"; }
 part gain2 : GainSpec { attribute :>> key = "exclusive-single-use"; attribute :>> removed = "Unnecessary snapshot creation for a noncached single consumer"; attribute :>> added = "Ownership checks and outcome settlement"; attribute :>> positiveCondition = "Exclusive transfer remains available; do not count it as simultaneous shared snapshot reuse"; }
 part gain3 : GainSpec { attribute :>> key = "retirement"; attribute :>> removed = "Global targ-target/primitive lookup and file-only authoritative handoff after full migration"; attribute :>> added = "Approved-provider schemas, reconstruction validation and ongoing source/observer proofs"; attribute :>> positiveCondition = "Every compile/link/provider caller migrates; unchanged C preprocessing costs remain separate"; }
 part def RefinementSpec { attribute key : String; attribute qntScope : String; attribute leanScope : String; attribute sourceDuty : String; }
 part refinement0 : RefinementSpec { attribute :>> key = "closure-cycles"; attribute :>> qntScope = "allocateShells;wireGraph;bindProviders"; attribute :>> leanScope = "relocationInjective;tagIsCanonical"; attribute :>> sourceDuty = "Prove recipe semantics for target capture, primitive self/cross edges and environment-dependent specialization"; }
 part refinement1 : RefinementSpec { attribute :>> key = "private-graph"; attribute :>> qntScope = "validateWorkspace;publishWorkspace"; attribute :>> leanScope = "privateDistinct;selfCycle"; attribute :>> sourceDuty = "Whole-graph aliases, roots, primitive lookups and emitter callbacks refine the relocation domain"; }
 part refinement2 : RefinementSpec { attribute :>> key = "observer"; attribute :>> qntScope = "changeOrigin;changeIdentity"; attribute :>> leanScope = "originDistinct;declarationDistinct"; attribute :>> sourceDuty = "Actual generated reader, binding/mark, declarations and diagnostic observations refine the symbolic record"; }
 part refinement3 : RefinementSpec { attribute :>> key = "abort"; attribute :>> qntScope = "unknownOutcome;settleOutcome;releaseArena"; attribute :>> leanScope = "unknownHolds;costPositive"; attribute :>> sourceDuty = "Truthful native settlement and callback/borrow/GC closure remain source/platform obligations"; }
 part def GateSpec { attribute key : String; attribute qualified : Boolean; attribute condition : String; }
 part gate0 : GateSpec { attribute :>> key = "alias-closure"; attribute :>> qualified = false; attribute :>> condition = "Every mutable reference and provider capture is classified; no unknown source edge"; }
 part gate1 : GateSpec { attribute :>> key = "provider-semantics"; attribute :>> qualified = false; attribute :>> condition = "Approved recipes preserve safe/unsafe/nargs/arithmetic behavior, declaration scope and initialization effects"; }
 part gate2 : GateSpec { attribute :>> key = "relocation-coverage"; attribute :>> qualified = false; attribute :>> condition = "Injective shared/cyclic graph map includes all GVM/C-interface referents; canonical tags and roots preserved"; }
 part gate3 : GateSpec { attribute :>> key = "observer-equivalence"; attribute :>> qualified = false; attribute :>> condition = "Identity, generated-reader origin, declarations and exceptions preserve the actual iter consumer observer"; }
 part gate4 : GateSpec { attribute :>> key = "abort-custody"; attribute :>> qualified = false; attribute :>> condition = "Unknown/partial construction retains source and destination custody until a truthful completion"; }
 part gate5 : GateSpec { attribute :>> key = "caller-retirement"; attribute :>> qualified = false; attribute :>> condition = "Compile and link consumers use private context-bound provider dispatch before globals retire"; }
 part gate6 : GateSpec { attribute :>> key = "platform-benefit"; attribute :>> qualified = false; attribute :>> condition = "Native runtime/memory-order/GC and actual work/span/retention evidence remain unqualified"; }
 attribute workspaceCount : Integer = 2;
 attribute actualAdmitted : Boolean = false;
 part history : GambitAssuranceRouting::ModelNeed { ref part :>> owner = GambitBuildAssurance::planner.component; attribute :>> obligationId = "AR-H"; attribute :>> kind = "interleaving"; attribute :>> subjectPath = "models/build/alias_workspace_reconstruction.qnt"; attribute :>> subjectScope = "alias_workspace_reconstruction:Test$"; attribute :>> premise = "Conditional workspace reconstruction and observer model; source and platform simulation remain open"; }
 part induction : GambitAssuranceRouting::ModelNeed { ref part :>> owner = GambitBuildAssurance::planner.component; attribute :>> obligationId = "AR-I"; attribute :>> kind = "induction"; attribute :>> subjectPath = "models/build/AliasWorkspaceReconstruction.lean"; attribute :>> subjectScope = "AliasWorkspaceReconstruction:relocationInjective;tagIsCanonical;privateDistinct;selfCycle;originDistinct;declarationDistinct;unknownHolds;costPositive"; attribute :>> premise = "Conditional workspace reconstruction and observer model; source and platform simulation remain open"; }
 part source : GambitAssuranceRouting::ModelNeed { ref part :>> owner = GambitBuildAssurance::planner.component; attribute :>> obligationId = "AR-S"; attribute :>> kind = "source-refinement"; attribute :>> subjectPath = "dev/architecture/toolchain/alias-workspace-reconstruction-design.org"; attribute :>> subjectScope = "AR-S:source"; attribute :>> premise = "Conditional workspace reconstruction and observer model; source and platform simulation remain open"; }
 part platform : GambitAssuranceRouting::ModelNeed { ref part :>> owner = GambitBuildAssurance::planner.component; attribute :>> obligationId = "AR-E"; attribute :>> kind = "environment-refinement"; attribute :>> subjectPath = "dev/architecture/toolchain/alias-workspace-reconstruction-design.org"; attribute :>> subjectScope = "AR-E:platform"; attribute :>> premise = "Conditional workspace reconstruction and observer model; source and platform simulation remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = TargetStageSealing::source; }
}
