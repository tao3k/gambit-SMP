package GambitVmLayoutAudit {
 private import ScalarValues::*;
 attribute scope:String="Complete dormant VM authority representation retirement, native ABI/source consumers and exact queue/evidence companion. Existing actual lifecycle/RC source authority unchanged.";
 attribute stage:String="vm-layout-audit";
 attribute formalDuty:String="Native SDK and ASCENT bind actual layout/descriptor/owner/consumer source refinements. Existing entry/root-store QNT and RootSpan Lean remain sole logical/arithmetic owners. No duplicate model or source-code theorem.39 unchanged framework tests are identity-reused, not whole CI.";
 part submission:GambitCommitGates::SubmissionUnit {
 attribute :>> kind="support"; attribute :>> result=""; attribute :>> progressDelta=0;
 attribute :>> supportPaths="dev/refactoring/modern-c/diagrams/vm-layout-retirement.d2;dev/refactoring/modern-c/diagrams/vm-layout-retirement.svg;dev/refactoring/modern-c/index.org;dev/refactoring/modern-c/models/sysml/delivery-outcomes.sysml;dev/refactoring/modern-c/models/sysml/pending-cuts.sysml;dev/refactoring/modern-c/models/sysml/vm-layout-audit.sysml;dev/refactoring/modern-c/models/sysml/vm-layout-retirement.sysml;dev/refactoring/modern-c/revision-checklist.org;dev/refactoring/modern-c/vm-layout-retirement.org;evidence/research/retained/modern-c/vm-layout-retirement/ascent-observation.json;evidence/research/retained/modern-c/vm-layout-retirement/ci-context.json;evidence/research/retained/modern-c/vm-layout-retirement/ci-deny-source-review.json;evidence/research/retained/modern-c/vm-layout-retirement/ci-process.log;evidence/research/retained/modern-c/vm-layout-retirement/ci-receipt.json;evidence/research/retained/modern-c/vm-layout-retirement/consumer-sources/layout-full.scm.json;evidence/research/retained/modern-c/vm-layout-retirement/consumer-sources/layout-witness.scm.json;evidence/research/retained/modern-c/vm-layout-retirement/consumer-sources/layout.c.json;evidence/research/retained/modern-c/vm-layout-retirement/delivery.json;evidence/research/retained/modern-c/vm-layout-retirement/framework-reuse.json;evidence/research/retained/modern-c/vm-layout-retirement/framework-submission/review.json;evidence/research/retained/modern-c/vm-layout-retirement/framework-submission/validation.json;evidence/research/retained/modern-c/vm-layout-retirement/metrics.json;evidence/research/retained/modern-c/vm-layout-retirement/model-binding.json;evidence/research/retained/modern-c/vm-layout-retirement/model-sources.json;evidence/research/retained/modern-c/vm-layout-retirement/one-argument-source-review.json;evidence/research/retained/modern-c/vm-layout-retirement/pending-after.json;evidence/research/retained/modern-c/vm-layout-retirement/pending-inventory.json;evidence/research/retained/modern-c/vm-layout-retirement/post-ascent-observation.json;evidence/research/retained/modern-c/vm-layout-retirement/post-model-binding.json;evidence/research/retained/modern-c/vm-layout-retirement/post-model-sources.json;evidence/research/retained/modern-c/vm-layout-retirement/qualification.json;evidence/research/retained/modern-c/vm-layout-retirement/runs/vm-layout-cost-1.json;evidence/research/retained/modern-c/vm-layout-retirement/runs/vm-layout-division-1.json;evidence/research/retained/modern-c/vm-layout-retirement/runs/vm-layout-frame-baseline-default-1.json;evidence/research/retained/modern-c/vm-layout-retirement/runs/vm-layout-native-1.json;evidence/research/retained/modern-c/vm-layout-retirement/runs/vm-layout-native-observation-1.json;evidence/research/retained/modern-c/vm-layout-retirement/runs/vm-layout-original-1.json;evidence/research/retained/modern-c/vm-layout-retirement/runs/vm-layout-original-argument-assembly-1.json;evidence/research/retained/modern-c/vm-layout-retirement/runs/vm-layout-original-make-1.json;evidence/research/retained/modern-c/vm-layout-retirement/runs/vm-layout-roots-1.json;evidence/research/retained/modern-c/vm-layout-retirement/runs/vm-layout-roots-profile-1.json;evidence/research/retained/modern-c/vm-layout-retirement/selected-source.json;evidence/research/retained/modern-c/vm-layout-retirement/source-review.json;evidence/research/retained/modern-c/vm-layout-retirement/submission/admission.json;evidence/research/retained/modern-c/vm-layout-retirement/submission/comment.json;evidence/research/retained/modern-c/vm-layout-retirement/submission/model-contract.json;evidence/research/retained/modern-c/vm-layout-retirement/submission/revision.json;evidence/research/retained/modern-c/vm-layout-retirement/submission/source-manifest.json;evidence/research/retained/modern-c/vm-layout-retirement/submission/source.json;src/gambit_smp/native_development.py;src/gambit_smp/runtime_binding.py;tests/test_native_development.py;tests/test_runtime_binding.py";
 attribute :>> testModules="tests/test_native_development.py;tests/test_runtime_binding.py";
 }
 part def Need { ref part gate:GambitCommitGates::Gate; attribute id:String; attribute method:String; attribute artifact:String; attribute scope:String; }
 part tests:Need { ref part :>> gate=GambitCommitGates::tests; attribute :>> id="VM-LAYOUT-AUDIT-TESTS"; attribute :>> method="native"; attribute :>> artifact="evidence/research/retained/modern-c/vm-layout-retirement/framework-submission/validation.json"; attribute :>> scope="39 unchanged source-qualified framework tests reused. Independent native five-gate layout delivery: old module refusal/new runs, actual roots/SFUN/RC/frame and original Make ut408 per role under existing p1."; }
 part learning:Need { ref part :>> gate=GambitCommitGates::learning; attribute :>> id="VM-LAYOUT-AUDIT-LEARNING"; attribute :>> method="source-analysis"; attribute :>> artifact="dev/refactoring/modern-c/vm-layout-retirement.org"; attribute :>> scope="Actual activation/RC authority replaces final dormant fixed table storage. Module versus standalone compiler contexts and hardcoded official child execution paths are explicit."; }
 part process:Need { ref part :>> gate=GambitCommitGates::process; attribute :>> id="VM-LAYOUT-AUDIT-PROCESS"; attribute :>> method="source-analysis"; attribute :>> artifact="dev/refactoring/modern-c/vm-layout-retirement.org"; attribute :>> scope="Two final VM representation templates close41→39 paths; seven original owners remain nonempty. Whole SMP1/12 unchanged, no other owner credit."; }
 part models:Need { ref part :>> gate=GambitCommitGates::models; attribute :>> id="VM-LAYOUT-AUDIT-MODELS"; attribute :>> method="native"; attribute :>> artifact="evidence/research/retained/modern-c/vm-layout-retirement/framework-submission/review.json"; attribute :>> scope="Native SDK7 obligations/3 adapters and ASCENT missing/stale controls; disjoint existing QNT/Lean reused. Pre/post model source snapshots retained separately."; }
 part questions:Need { ref part :>> gate=GambitCommitGates::questions; attribute :>> id="VM-LAYOUT-AUDIT-QUESTIONS"; attribute :>> method="source-analysis"; attribute :>> artifact="dev/refactoring/modern-c/vm-layout-retirement.org"; attribute :>> scope="Old ABI rejection, actual memory saving, rebuilt native object cost, noisy1-arg/static footprint mechanism and pre-existing CI producer identity mismatch answered with explicit open boundaries."; }
}
