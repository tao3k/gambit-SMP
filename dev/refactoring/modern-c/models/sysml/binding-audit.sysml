package GambitBindingAudit {
 private import ScalarValues::*;
 attribute scope:String="Complete binding-read evidence, native-consumer source custody and source-selected reusable framework support; zero runtime or SMP promotion from this companion commit.";
 attribute stage:String="binding-read-audit";
 attribute formalDuty:String="SysML scope and source epochs drive ASCENT; new fixup QNT owns publication interleavings, existing QNT entry/unload and Lean representation duties remain distinct. Framework tests do not prove C semantics.";
 part submission:GambitCommitGates::SubmissionUnit {
  attribute :>> kind="support"; attribute :>> result=""; attribute :>> progressDelta=0;
  attribute :>> supportPaths="dev/modeling/ascent/binding-activation.rules.scm;dev/refactoring/modern-c/binding-activation.org;dev/refactoring/modern-c/diagrams/binding-activation.d2;dev/refactoring/modern-c/index.org;dev/refactoring/modern-c/models/quint/module_fixup.qnt;dev/refactoring/modern-c/models/sysml/binding-activation.sysml;dev/refactoring/modern-c/models/sysml/binding-audit.sysml;dev/refactoring/modern-c/models/sysml/delivery-outcomes.sysml;dev/refactoring/modern-c/models/sysml/pending-cuts.sysml;dev/refactoring/modern-c/revision-checklist.org;evidence/research/retained/modern-c/binding-activation/ascent-observation.json;evidence/research/retained/modern-c/binding-activation/binding-activation-observation-control.trace;evidence/research/retained/modern-c/binding-activation/binding-activation-production.trace;evidence/research/retained/modern-c/binding-activation/ci-attribution.json;evidence/research/retained/modern-c/binding-activation/current-official-comparison.json;evidence/research/retained/modern-c/binding-activation/delivery.json;evidence/research/retained/modern-c/binding-activation/framework-submission/review.json;evidence/research/retained/modern-c/binding-activation/framework-submission/validation.json;evidence/research/retained/modern-c/binding-activation/historical-inputs.json;evidence/research/retained/modern-c/binding-activation/inventory-transition.json;evidence/research/retained/modern-c/binding-activation/metrics.json;evidence/research/retained/modern-c/binding-activation/model-binding.json;evidence/research/retained/modern-c/binding-activation/model-snapshots/binding-activation.org;evidence/research/retained/modern-c/binding-activation/model-snapshots/binding-activation.sysml;evidence/research/retained/modern-c/binding-activation/model-snapshots/delivery-outcomes.sysml;evidence/research/retained/modern-c/binding-activation/model-snapshots/pending-cuts.sysml;evidence/research/retained/modern-c/binding-activation/native-complete.json;evidence/research/retained/modern-c/binding-activation/native-observations.json;evidence/research/retained/modern-c/binding-activation/observation.json;evidence/research/retained/modern-c/binding-activation/official-comparison.json;evidence/research/retained/modern-c/binding-activation/pending-after.json;evidence/research/retained/modern-c/binding-activation/pending-inventory.json;evidence/research/retained/modern-c/binding-activation/post-ascent-observation.json;evidence/research/retained/modern-c/binding-activation/post-model-binding.json;evidence/research/retained/modern-c/binding-activation/pre-staging-custody.json;evidence/research/retained/modern-c/binding-activation/prior-observation.json;evidence/research/retained/modern-c/binding-activation/product-restoration.json;evidence/research/retained/modern-c/binding-activation/source-manifest.json;evidence/research/retained/modern-c/binding-activation/source-refinement.json;evidence/research/retained/modern-c/binding-activation/staging-resolution.json;evidence/research/retained/modern-c/binding-activation/submission/admission.json;evidence/research/retained/modern-c/binding-activation/submission/comment.json;evidence/research/retained/modern-c/binding-activation/submission/model-contract.json;evidence/research/retained/modern-c/binding-activation/submission/revision.json;evidence/research/retained/modern-c/binding-activation/submission/source-manifest.json;evidence/research/retained/modern-c/binding-activation/submission/source.json;src/gambit_smp/native_development.py;src/gambit_smp/runtime_binding.py;tests/test_native_development.py;tests/test_runtime_binding.py";
  attribute :>> testModules="tests/test_native_development.py;tests/test_runtime_binding.py";
 }
 part def Need { ref part gate:GambitCommitGates::Gate; attribute id:String; attribute method:String; attribute artifact:String; attribute scope:String; }
 part tests:Need { ref part :>> gate=GambitCommitGates::tests; attribute :>> id="BA-AUDIT-TESTS"; attribute :>> method="native"; attribute :>> artifact="evidence/research/retained/modern-c/binding-activation/framework-submission/validation.json"; attribute :>> scope="All37 exact source-selected tests pass; published native-development tests retained. Native runtime consumers have independent vendor admission."; }
 part learning:Need { ref part :>> gate=GambitCommitGates::learning; attribute :>> id="BA-AUDIT-LEARNING"; attribute :>> method="source-analysis"; attribute :>> artifact="dev/refactoring/modern-c/binding-activation.org"; attribute :>> scope="No stable runtime speedup; retain rejected designs and actual negative controls."; }
 part process:Need { ref part :>> gate=GambitCommitGates::process; attribute :>> id="BA-AUDIT-PROCESS"; attribute :>> method="source-analysis"; attribute :>> artifact="dev/refactoring/modern-c/binding-activation.org"; attribute :>> scope="One complete post-foundation binding owner; primary path inventory is not progress; independent1/12 unchanged."; }
 part models:Need { ref part :>> gate=GambitCommitGates::models; attribute :>> id="BA-AUDIT-MODELS"; attribute :>> method="native"; attribute :>> artifact="evidence/research/retained/modern-c/binding-activation/framework-submission/review.json"; attribute :>> scope="Strict native SDK eight obligations and shared five-gate vendor admission; distinct QNT/Lean duties."; }
 part questions:Need { ref part :>> gate=GambitCommitGates::questions; attribute :>> id="BA-AUDIT-QUESTIONS"; attribute :>> method="source-analysis"; attribute :>> artifact="dev/refactoring/modern-c/binding-activation.org"; attribute :>> scope="Explicit metadata cost, read/lifetime preconditions, code-layout sensitivity and retained whole-SMP failures."; }
}
