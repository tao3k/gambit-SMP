package GambitInputOwners {
 private import ScalarValues::*;
 attribute scope:String="Complete input-owner refinement across historical views, mutable fixtures, immutable output transport and verified installed package inputs. No scheduler or runtime change.";
 attribute stage:String="Support only, progressDelta0; architecture3/4 and independent SMP1/12. Fourth integration requires full framework/build and matched macOS evidence.";
 attribute sourceRule:String="Original source7c490 and current modern-c3d42 are distinct. Preserve view facts/SHA/ranges and bind three entry references to original reachable commit/blob. Audit registered views plus explicit authored action contexts, not registry names alone.";
 attribute fixtureRule:String="Mutable test files acquire fixture ownership from verified declared bytes; immutable original source is unchanged. Output fixtures retain only selected origins and borrow the genuine owning Git object DB. Borrowing is never a checkout or build proof. Git author is fixture-local.";
 attribute packageRule:String="Use the existing verified API owner inventory and its before/after checks. Package resources use package labels even when installed outside the repository. Other external paths and digest drift refuse. Repository references remain project-relative.";
 attribute writerRule:String="No global Git config, copied runtime workspace, refreshed historical SHA, weakened source identity, test skip, heap/wait change, or unregistered sealed provider loading.";
 attribute formalDuty:String="SysML owns roles and refinement premises; ASCENT owns submission admission. Existing QNT scheduling and Lean algebraic obligations remain distinct, unchanged. Real source/host/test observations are not duplicated formal proofs.";
 attribute testScope:String="Three full modules plus all11 original ProgressiveClueTests IDs; its other38 CLI tests and all full remote CI tests remain separate. Full native-retry module uses original60s sealed domain. All required scopes must pass with no skip before support admission.";
 attribute diagram:String="direction: right\norig: Original Git source epoch\nview: Historical view with exact source locator\nlive: Isolated mutable test snapshot\nobjects: Read-only Git object borrow\npackage: Verified installed package inventory\nrepo: Exact project inputs\nlabels: Shared owner-aware input attestations\nquery: Existing native ASCENT queries\nchecks: Existing currentness and byte checks\nremote: Full CI and matched macOS remain independent\norig -> view: keep SHA and facts\nview -> live: explicit fixture ownership transfer\norig -> objects: no checkout or source copy\npackage -> labels: package label\nrepo -> labels: project-relative label\nlabels -> checks\nchecks -> query\nobjects -> query: immutable output reader\nlive -> query: mutation tests\nquery -> remote: scope is not product acceptance\n";
 part def OwnerRole { attribute path:String; attribute anchor:String; attribute obligation:String; }
 part origin:OwnerRole { attribute :>> path="evidence/scenarios/stack-header/entry-preflight.view.json"; attribute :>> anchor="base-handler;base-poll;base-fudge"; attribute :>> obligation="Read original commit/blob bytes; no current native result transfer."; }
 part fixture:OwnerRole { attribute :>> path="tests/support.py"; attribute :>> anchor="copy_live_view;borrow_git_sources;copy_output_observations"; attribute :>> obligation="Transfer a mutable view or immutable object access explicitly; reject wrong owner and conflicting path epochs."; }
 part installedOwner:OwnerRole { attribute :>> path="src/gambit_smp/ascent_program.py"; attribute :>> anchor="input_attestations"; attribute :>> obligation="Map only verified installed or actual repository inputs; preserve digest and API owner lifetime checks."; }
 part consumer:OwnerRole { attribute :>> path="src/gambit_smp/trajectory_exploration.py"; attribute :>> anchor="_native_exchange;read_view"; attribute :>> obligation="Use identical owner labels for regular view, unavailable-view and relation-read paths; retain _current checks."; }
 part def Need { attribute id:String; ref part gate:GambitCommitGates::Gate; attribute method:String; attribute artifact:String; attribute scope:String; }
 part tests:Need { attribute :>> id="INPUT-OWNERS-TESTS"; ref part :>> gate=GambitCommitGates::tests; attribute :>> method="native"; attribute :>> artifact="evidence/research/retained/modern-c/input-owners/receipt.json"; attribute :>> scope="Explicit input owner refinement only; all runtime and full-platform gates retained"; }
 part learning:Need { attribute :>> id="INPUT-OWNERS-LEARNING"; ref part :>> gate=GambitCommitGates::learning; attribute :>> method="source-refinement"; attribute :>> artifact="evidence/research/retained/modern-c/input-owners/receipt.json"; attribute :>> scope="Explicit input owner refinement only; all runtime and full-platform gates retained"; }
 part process:Need { attribute :>> id="INPUT-OWNERS-PROCESS"; ref part :>> gate=GambitCommitGates::process; attribute :>> method="source-refinement"; attribute :>> artifact="evidence/research/retained/modern-c/input-owners/receipt.json"; attribute :>> scope="Explicit input owner refinement only; all runtime and full-platform gates retained"; }
 part models:Need { attribute :>> id="INPUT-OWNERS-MODELS"; ref part :>> gate=GambitCommitGates::models; attribute :>> method="source-refinement"; attribute :>> artifact="evidence/research/retained/modern-c/input-owners/receipt.json"; attribute :>> scope="Explicit input owner refinement only; all runtime and full-platform gates retained"; }
 part questions:Need { attribute :>> id="INPUT-OWNERS-QUESTIONS"; ref part :>> gate=GambitCommitGates::questions; attribute :>> method="source-refinement"; attribute :>> artifact="evidence/research/retained/modern-c/input-owners/receipt.json"; attribute :>> scope="Explicit input owner refinement only; all runtime and full-platform gates retained"; }
 part submission:GambitCommitGates::SubmissionUnit { attribute :>> kind="support"; attribute :>> result=""; attribute :>> progressDelta=0; attribute :>> supportPaths="src/gambit_smp/ascent_program.py;src/gambit_smp/trajectory_exploration.py;tests/support.py;tests/test_source_identity.py;tests/test_real_source_impact.py;tests/test_revision_submission.py;tests/test_progressive_clues.py;tests/test_native_retry_review.py;evidence/scenarios/stack-header/entry-preflight.view.json;dev/refactoring/modern-c/models/sysml/input-owners.sysml;dev/refactoring/modern-c/input-owners.org;dev/refactoring/modern-c/diagrams/input-owners.d2;dev/refactoring/modern-c/diagrams/input-owners.svg;dev/refactoring/modern-c/branch-checklist.org;evidence/research/retained/modern-c/input-owners/receipt.json;evidence/research/retained/modern-c/input-owners/qualification-history.json;evidence/research/retained/modern-c/input-owners/remote.json;evidence/research/retained/modern-c/input-owners/open-obligations.json"; attribute :>> testModules="tests/test_source_identity.py;tests/test_real_source_impact.py;tests/test_revision_submission.py;tests/test_progressive_clues.py;tests/test_native_retry_review.py"; }
}
