package GambitRestoreEntryGuard { private import ScalarValues::*;
part def Owner { attribute componentId:String; }
part entryOwner:Owner { attribute :>> componentId="entry"; }
part guardOwner:Owner { attribute :>> componentId="guard"; }
part rootsOwner:Owner { attribute :>> componentId="roots"; }
part def SourceRow { attribute key:String; attribute path:String; attribute needle:String; attribute obligation:String; }
part source0:SourceRow { attribute :>> key="scheduler-local"; attribute :>> path="vendor/gambit/lib/_thread.scm"; attribute :>> needle="(macro-thread-restore!"; attribute :>> obligation="Local, stealing and non-SMP scheduling restore an existing suspended activation"; }
part source1:SourceRow { attribute :>> key="scheduler-pinned"; attribute :>> path="vendor/gambit/lib/_thread.scm"; attribute :>> needle="(macro-thread-pinned stolen-thread)"; attribute :>> obligation="Steal admission checks affinity; a guard cannot relax return-to-C affinity"; }
part source2:SourceRow { attribute :>> key="thread-wrapper"; attribute :>> path="vendor/gambit/lib/_thread.scm"; attribute :>> needle="(define-prim ##thread-restore!"; attribute :>> obligation="Rest wrapper applies procedure; not the sole generated inline entry"; }
part source3:SourceRow { attribute :>> key="graft-wrapper"; attribute :>> path="vendor/gambit/lib/_thread.scm"; attribute :>> needle="(define-prim ##continuation-graft-no-winding"; attribute :>> obligation="Direct low-level graft can bypass winding hooks"; }
part source4:SourceRow { attribute :>> key="return-wrapper"; attribute :>> path="vendor/gambit/lib/_thread.scm"; attribute :>> needle="(define-prim ##continuation-return-no-winding"; attribute :>> obligation="Direct return cannot rely on a before hook"; }
part source5:SourceRow { attribute :>> key="wind-before"; attribute :>> path="vendor/gambit/lib/_thread.scm"; attribute :>> needle="((macro-dynwind-before dst))"; attribute :>> obligation="Internal graft navigation invokes arbitrary user hook; keep one restore transaction"; }
part source6:SourceRow { attribute :>> key="wind-after"; attribute :>> path="vendor/gambit/lib/_thread.scm"; attribute :>> needle="((macro-dynwind-after src))"; attribute :>> obligation="After hook is neither last use nor exact exit witness"; }
part source7:SourceRow { attribute :>> key="fast-return"; attribute :>> path="vendor/gambit/lib/_thread.scm"; attribute :>> needle="(if (or (##eq? src dst) ;; check common case (same dynamic-wind context)"; attribute :>> obligation="Same denv fast path bypasses winding"; }
part source8:SourceRow { attribute :>> key="scheduler-syntax"; attribute :>> path="vendor/gambit/lib/_thread#.scm"; attribute :>> needle="(##thread-restore!"; attribute :>> obligation="Scheduler macro directly targets primitive"; }
part source9:SourceRow { attribute :>> key="emit-thread"; attribute :>> path="vendor/gambit/gsc/_t-c-2.scm"; attribute :>> needle="(targ-emit-jump-inline \"THREAD_RESTORE\" safe? nb-args)"; attribute :>> obligation="GVM emitter must carry explicit restore intent before destructive jump"; }
part source10:SourceRow { attribute :>> key="emit-graft"; attribute :>> path="vendor/gambit/gsc/_t-c-2.scm"; attribute :>> needle="(targ-emit-jump-inline \"CONTINUATION_GRAFT_NO_WINDING\" safe? nb-args)"; attribute :>> obligation="FrameSpec root and restore intent needed at actual emitter"; }
part source11:SourceRow { attribute :>> key="emit-return"; attribute :>> path="vendor/gambit/gsc/_t-c-2.scm"; attribute :>> needle="(targ-emit-jump-inline \"CONTINUATION_RETURN_NO_WINDING\" safe? nb-args)"; attribute :>> obligation="Return point metadata and private guard binding required"; }
part source12:SourceRow { attribute :>> key="native-thread"; attribute :>> path="vendor/gambit/include/gambit.h"; attribute :>> needle="#define ___THREAD_RESTORE"; attribute :>> obligation="Current thread and frame change; guard handoff precedes destructive switch"; }
part source13:SourceRow { attribute :>> key="native-graft"; attribute :>> path="vendor/gambit/include/gambit.h"; attribute :>> needle="#define ___CONTINUATION_GRAFT_NO_WINDING"; attribute :>> obligation="FP, denv and caches replaced; frame-local ticket is insufficient"; }
part source14:SourceRow { attribute :>> key="native-return"; attribute :>> path="vendor/gambit/include/gambit.h"; attribute :>> needle="#define ___JUMP_CONTINUATION_RETURN_NO_WINDING2"; attribute :>> obligation="Arguments popped and frame replaced; preserve rooted incoming values"; }
part source15:SourceRow { attribute :>> key="catcher"; attribute :>> path="vendor/gambit/include/gambit.h"; attribute :>> needle="#define ___END_TRY } ___ps->catcher = ___old_catcher; }"; attribute :>> obligation="Outer catcher restoration is distinct from Scheme body return"; }
part source16:SourceRow { attribute :>> key="sfun-error"; attribute :>> path="vendor/gambit/include/gambit.h"; attribute :>> needle="#define ___SFUN_ERROR_VOID"; attribute :>> obligation="Conversion handler can call ___call repeatedly with the same marker"; }
part source17:SourceRow { attribute :>> key="sfun-exit"; attribute :>> path="vendor/gambit/include/gambit.h"; attribute :>> needle="#define ___END_SFUN_VOID"; attribute :>> obligation="Kill marker before propagation on shown normal macro path; exceptional census remains open"; }
part source18:SourceRow { attribute :>> key="call-unwind"; attribute :>> path="vendor/gambit/lib/setup.c"; attribute :>> needle="stack_marker != ___ps->context->fp[___FRAME_SPACE(2)-2]"; attribute :>> obligation="Mismatched unwind continues outward instead of authorizing local completion"; }
part source19:SourceRow { attribute :>> key="run-root"; attribute :>> path="vendor/gambit/lib/setup.c"; attribute :>> needle="___make_sfun_stack_marker_from_root"; attribute :>> obligation="Managed startup distinguishes rooted thunk from legacy raw endpoint"; }
part source20:SourceRow { attribute :>> key="run-exit"; attribute :>> path="vendor/gambit/lib/setup.c"; attribute :>> needle="___kill_sfun_stack_marker (marker);"; attribute :>> obligation="Marker invalidation and startup result publication are distinct duties"; }
part source21:SourceRow { attribute :>> key="root-reload"; attribute :>> path="vendor/gambit/lib/c_intf.c"; attribute :>> needle="proc_or_false = *proc_root; /* reload after allocating the marker */"; attribute :>> obligation="Root slot must be registered and updated by GC before allocation"; }
part source22:SourceRow { attribute :>> key="legacy-root"; attribute :>> path="vendor/gambit/lib/c_intf.c"; attribute :>> needle="Legacy raw SFUN entry is not made a registered-root interface"; attribute :>> obligation="C local wrapper does not close roots for arbitrary native entry"; }
part source23:SourceRow { attribute :>> key="marker-kill"; attribute :>> path="vendor/gambit/lib/c_intf.c"; attribute :>> needle="___VECTORELEM(marker, 0) = ___FAL; /* invalidate the C stack frame */"; attribute :>> obligation="C stack liveness marker is not a completion record"; }
part source24:SourceRow { attribute :>> key="wrong-processor"; attribute :>> path="vendor/gambit/lib/_kernel.scm"; attribute :>> needle="___COVER_RETURN_TO_C_HANDLER_WRONG_PROCESSOR;"; attribute :>> obligation="Must preserve destination processor semantics"; }
part source25:SourceRow { attribute :>> key="dead-c-frame"; attribute :>> path="vendor/gambit/lib/_kernel.scm"; attribute :>> needle="___COVER_RETURN_TO_C_HANDLER_MULTIPLE_RETURN;"; attribute :>> obligation="Multi-shot Scheme cannot revive a dead C activation"; }
part source26:SourceRow { attribute :>> key="ffi-caller"; attribute :>> path="vendor/gambit/examples/tcltk/tcltk.scm"; attribute :>> needle="char *result = tcltk_call"; attribute :>> obligation="Concrete native callback obtains Scheme payload from data_rc"; }
part source27:SourceRow { attribute :>> key="ffi-body"; attribute :>> path="vendor/gambit/examples/tcltk/tcltk.scm"; attribute :>> needle="(c-define (##tcltk-call vect args)"; attribute :>> obligation="Real callback applies Scheme closure; nested reentry needs child guard"; }
part def IdentityRow { attribute key:String; attribute structure:String; attribute rule:String; attribute caveat:String; }
part identity0:IdentityRow { attribute :>> key="ticket"; attribute :>> structure="SessionNonce + DomainId + Generation + AttemptId"; attribute :>> rule="Mint outside restored graph for each new semantic invocation"; attribute :>> caveat="Addresses or captured counters do not establish freshness"; }
part identity1:IdentityRow { attribute :>> key="guard"; attribute :>> structure="Full TicketId + GuardSerial + OwnerGeneration"; attribute :>> rule="A completion witness names its immutable guard"; attribute :>> caveat="Never look up destination from ambient currentTicket"; }
part identity2:IdentityRow { attribute :>> key="semantic"; attribute :>> structure="Continuation invoke or admitted raw no-winding transfer"; attribute :>> rule="Fresh ticket before restoring; old activation retained until classified"; attribute :>> caveat="Raw escape or unknown issuer denies optimization receipt"; }
part identity3:IdentityRow { attribute :>> key="navigation"; attribute :>> structure="Internal dynamic-wind graft transaction"; attribute :>> rule="Keep same ticket through before/after navigation"; attribute :>> caveat="Hook may escape; no completion inferred"; }
part identity4:IdentityRow { attribute :>> key="scheduler"; attribute :>> structure="Suspended activation binding"; attribute :>> rule="Resume same ticket; transfer carrier under owner protocol"; attribute :>> caveat="Processor affinity qualification remains separate"; }
part identity5:IdentityRow { attribute :>> key="foreign"; attribute :>> structure="HostEntryId plus optional child TicketId"; attribute :>> rule="Nested callback new child; conversion retries retain host identity"; attribute :>> caveat="Every ___call is not automatically a new SFUN invocation"; }
part identity6:IdentityRow { attribute :>> key="transport"; attribute :>> structure="OperationId plus immutable TicketId and payload binding"; attribute :>> rule="Lost reply queries exact record"; attribute :>> caveat="Same arguments do not identify a fresh execution"; }
part def IssuerRow { attribute key:String; attribute proposedIssuer:String; attribute actualSource:String; attribute status:String; attribute responsibility:String; }
part issuer0:IssuerRow { attribute :>> key="semantic-entry"; attribute :>> proposedIssuer="Native restore admission owner"; attribute :>> actualSource="no-winding inline emitters and macros identified"; attribute :>> status="Required refactoring; not implemented"; attribute :>> responsibility="Register guard and roots before destructive transfer"; }
part issuer1:IssuerRow { attribute :>> key="intent"; attribute :>> proposedIssuer="Scheme/GVM semantic classifier"; attribute :>> actualSource="Scheduler macros and internal wind grafts share low-level primitives"; attribute :>> status="Caller census incomplete"; attribute :>> responsibility="Distinguish fresh invoke, navigation, scheduling and foreign entry"; }
part issuer2:IssuerRow { attribute :>> key="scheduler"; attribute :>> proposedIssuer="Execution-context owner"; attribute :>> actualSource="Local and stealing scheduler invoke thread-restore"; attribute :>> status="Existing restore located; guard transfer absent"; attribute :>> responsibility="Keep same ticket and roots; obey C affinity"; }
part issuer3:IssuerRow { attribute :>> key="foreign"; attribute :>> proposedIssuer="Stable host entry owner"; attribute :>> actualSource="Tcl callback and SFUN error loop located"; attribute :>> status="Generic managed entry still open"; attribute :>> responsibility="Register child before allocating marker; preserve parent binding"; }
part issuer4:IssuerRow { attribute :>> key="exit"; attribute :>> proposedIssuer="Stable outer completion guard"; attribute :>> actualSource="___call unwinds and ___run kills marker; catcher macro restores"; attribute :>> status="No trusted keyed guard signer found"; attribute :>> responsibility="Classify exit and restore outer binding before witness"; }
part issuer5:IssuerRow { attribute :>> key="settlement"; attribute :>> proposedIssuer="Per-ticket ledger owner"; attribute :>> actualSource="No new native ledger implemented"; attribute :>> status="Conditional algebra only"; attribute :>> responsibility="Commit exact outcome before ack; query immutable target"; }
part issuer6:IssuerRow { attribute :>> key="roots"; attribute :>> proposedIssuer="VM RootRegistry and context scan owner"; attribute :>> actualSource="Rooted startup helper reloads slot after marker allocation"; attribute :>> status="All callbacks and GVM maps unqualified"; attribute :>> responsibility="Keep rooted payload/result through error and unknown exit"; }
part def ClaimRow { attribute key:String; attribute mechanism:String; attribute condition:String; attribute result:String; attribute gap:String; }
part claim0:ClaimRow { attribute :>> key="same-id"; attribute :>> mechanism="Separate semantic intent from physical jump"; attribute :>> condition="Trusted caller classification"; attribute :>> result="No ticket per scheduler hop or winding graft"; attribute :>> gap="All raw entry producers remain to be qualified"; }
part claim1:ClaimRow { attribute :>> key="old-receipt"; attribute :>> mechanism="Immutable full GuardId dispatch"; attribute :>> condition="Guard equality and surviving owner record"; attribute :>> result="Old receipt does not modify new guard"; attribute :>> gap="Native key allocator and generation overflow open"; }
part claim2:ClaimRow { attribute :>> key="exit-order"; attribute :>> mechanism="Body return then outer restore then marker close then witness"; attribute :>> condition="Real outer catch and root coverage"; attribute :>> result="No early settlement from Scheme return"; attribute :>> gap="Native exception and profile refinement open"; }
part claim3:ClaimRow { attribute :>> key="unknown"; attribute :>> mechanism="Retain old guard and roots across cross restore"; attribute :>> condition="No invented absence receipt"; attribute :>> result="New execution cannot erase unclassified old custody"; attribute :>> gap="Liveness and bounded retained-memory guarantee open"; }
part claim4:ClaimRow { attribute :>> key="generic"; attribute :>> mechanism="Arbitrary-key Lean guard map"; attribute :>> condition="Faithful full-key equality and trusted witness"; attribute :>> result="Wrong owner, serial or ticket retained; ambient cannot retarget"; attribute :>> gap="Finite QNT to arbitrary nested native product not proved"; }
part claim5:ClaimRow { attribute :>> key="normalization"; attribute :>> mechanism="Use completed capability retirement as admission premise"; attribute :>> condition="All metadata writers and late callbacks closed"; attribute :>> result="Second normalization potentially removable"; attribute :>> gap="This study retires zero native paths"; }
part def MemoryRow { attribute key:String; attribute publication:String; attribute observation:String; attribute obligation:String; attribute overhead:String; }
part memory0:MemoryRow { attribute :>> key="reserve"; attribute :>> publication="Owner serializes full key and reserved guard before exposure"; attribute :>> observation="Restore gateway sees reserved record"; attribute :>> obligation="Allocation failure before admission has no runnable ticket"; attribute :>> overhead="One record per semantic or host entry"; }
part memory1:MemoryRow { attribute :>> key="roots"; attribute :>> publication="RootRegistry publishes live scanned slots before possible GC"; attribute :>> observation="Marker allocator reloads rooted incoming values"; attribute :>> obligation="Release only after scanner and executor handoff acknowledged"; attribute :>> overhead="Root carrier plus scan lease"; }
part memory2:MemoryRow { attribute :>> key="switch"; attribute :>> publication="Admission joins source and destination owner under stable guard"; attribute :>> observation="FP/denv/current-thread switch consumes intent token"; attribute :>> obligation="No locks across hooks, Scheme, FFI or GC"; attribute :>> overhead="Short handoff; source guard remains owned on unknown"; }
part memory3:MemoryRow { attribute :>> key="exit"; attribute :>> publication="Outer owner records catcher and parent-binding restoration plus marker status"; attribute :>> observation="Exact GuardId witness"; attribute :>> obligation="Result remains rooted until terminal ownership transfers"; attribute :>> overhead="One completion transition per logical entry"; }
part memory4:MemoryRow { attribute :>> key="commit"; attribute :>> publication="One owner transaction publishes terminal outcome before acknowledgement"; attribute :>> observation="Pinned record queried by immutable key"; attribute :>> obligation="C23 ordering is not GC rooting or crash durability"; attribute :>> overhead="Mutex or qualified atomics; avoid unnecessary global CAS"; }
part memory5:MemoryRow { attribute :>> key="reclaim"; attribute :>> publication="Close admission and drain accepted readers and executors"; attribute :>> observation="Generation-safe tombstone or non-replay response"; attribute :>> obligation="No generation wrap or address reuse while stale receipts survive"; attribute :>> overhead="Retained tombstones and unknown roots require capacity policy"; }
part def GainRow { attribute key:String; attribute avoided:String; attribute added:String; attribute condition:String; }
part gain0:GainRow { attribute :>> key="navigation"; attribute :>> avoided="h tickets and ledger entries for h internal grafts"; attribute :>> added="h intent checks; zero fresh tickets"; attribute :>> condition="One known restore transaction; user callback new entry classified separately"; }
part gain1:GainRow { attribute :>> key="scheduler"; attribute :>> avoided="s fresh ticket allocations for s scheduler resumes"; attribute :>> added="s carrier handoffs; zero fresh tickets"; attribute :>> condition="Suspended activation ownership and affinity proven"; }
part gain2:GainRow { attribute :>> key="retry"; attribute :>> avoided="r executions and side effects for r lost replies"; attribute :>> added="r keyed reads; retained outcome"; attribute :>> condition="Single surviving ledger; no crash exactly-once claim"; }
part gain3:GainRow { attribute :>> key="foreign"; attribute :>> avoided="Unsafe early root release and parent mis-settlement"; attribute :>> added="One child guard per logical callback plus outer cleanup"; attribute :>> condition="All entry roots and exceptions qualified"; }
part gain4:GainRow { attribute :>> key="shared-support"; attribute :>> avoided="Duplicate per-component root and outcome custody mechanisms"; attribute :>> added="Shared registry ABI and scanner integration once"; attribute :>> condition="Do not count reused support as new implementation savings twice"; }
part gain5:GainRow { attribute :>> key="second-pass"; attribute :>> avoided="At most one resource normalization traversal"; attribute :>> added="Intent, guard, root and capability accounting"; attribute :>> condition="Removed traversal cost must exceed all marginal hot-path and retention costs; currently not qualified"; }
part def ContractRow { attribute fromNode:String; attribute toNode:String; attribute custody:String; }
part contract0:ContractRow { attribute :>> fromNode="Scheme GVM intent"; attribute :>> toNode="Native restore gateway"; attribute :>> custody="fresh semantic / navigation / scheduler / foreign"; }
part contract1:ContractRow { attribute :>> fromNode="Native restore gateway"; attribute :>> toNode="Stable owner guard"; attribute :>> custody="reserve immutable key outside restored frames"; }
part contract2:ContractRow { attribute :>> fromNode="Stable owner guard"; attribute :>> toNode="GC root carrier"; attribute :>> custody="publish and scan before allocating marker"; }
part contract3:ContractRow { attribute :>> fromNode="GC root carrier"; attribute :>> toNode="FP denv thread switch"; attribute :>> custody="incoming values remain rooted across transfer"; }
part contract4:ContractRow { attribute :>> fromNode="FP denv thread switch"; attribute :>> toNode="Restored execution"; attribute :>> custody="bind current guard from runtime context"; }
part contract5:ContractRow { attribute :>> fromNode="Restored execution"; attribute :>> toNode="Stable owner guard"; attribute :>> custody="unknown escape retains old custody"; }
part contract6:ContractRow { attribute :>> fromNode="Restored execution"; attribute :>> toNode="Outer completion"; attribute :>> custody="body return alone insufficient"; }
part contract7:ContractRow { attribute :>> fromNode="Outer completion"; attribute :>> toNode="Exact ticket ledger"; attribute :>> custody="restore catcher and parent; close marker; commit before ack"; }
part contract8:ContractRow { attribute :>> fromNode="Old captured receipt"; attribute :>> toNode="Exact ticket ledger"; attribute :>> custody="immutable old target; never ambient current"; }
part contract9:ContractRow { attribute :>> fromNode="Exact ticket ledger"; attribute :>> toNode="Next semantic invocation"; attribute :>> custody="fresh external ID; old outcome remains queryable"; }
part contract10:ContractRow { attribute :>> fromNode="Stable owner guard"; attribute :>> toNode="Scheduler resume"; attribute :>> custody="same activation ID; carrier handoff"; }
part contract11:ContractRow { attribute :>> fromNode="Scheduler resume"; attribute :>> toNode="Restored execution"; attribute :>> custody="preserve affinity and roots"; }
part def BindingRow { attribute actionName:String; attribute lemma:String; attribute scope:String; }
part binding0:BindingRow { attribute :>> actionName="restore_entry_guard.reserveInitial0"; attribute :>> lemma="RestoreEntry.reserveInitial0Preserves"; attribute :>> scope="typed QNT AST step; source simulation open"; }
part binding1:BindingRow { attribute :>> actionName="restore_entry_guard.publishRoot0"; attribute :>> lemma="RestoreEntry.publishRoot0Preserves"; attribute :>> scope="typed QNT AST step; source simulation open"; }
part binding2:BindingRow { attribute :>> actionName="restore_entry_guard.enterInitial0"; attribute :>> lemma="RestoreEntry.enterInitial0Preserves"; attribute :>> scope="typed QNT AST step; source simulation open"; }
part binding3:BindingRow { attribute :>> actionName="restore_entry_guard.internalGraft0"; attribute :>> lemma="RestoreEntry.internalGraft0Preserves"; attribute :>> scope="typed QNT AST step; source simulation open"; }
part binding4:BindingRow { attribute :>> actionName="restore_entry_guard.suspend0"; attribute :>> lemma="RestoreEntry.suspend0Preserves"; attribute :>> scope="typed QNT AST step; source simulation open"; }
part binding5:BindingRow { attribute :>> actionName="restore_entry_guard.schedulerResume0"; attribute :>> lemma="RestoreEntry.schedulerResume0Preserves"; attribute :>> scope="typed QNT AST step; source simulation open"; }
part binding6:BindingRow { attribute :>> actionName="restore_entry_guard.bodyReturn0"; attribute :>> lemma="RestoreEntry.bodyReturn0Preserves"; attribute :>> scope="typed QNT AST step; source simulation open"; }
part binding7:BindingRow { attribute :>> actionName="restore_entry_guard.restoreOuter0"; attribute :>> lemma="RestoreEntry.restoreOuter0Preserves"; attribute :>> scope="typed QNT AST step; source simulation open"; }
part binding8:BindingRow { attribute :>> actionName="restore_entry_guard.observeExit0"; attribute :>> lemma="RestoreEntry.observeExit0Preserves"; attribute :>> scope="typed QNT AST step; source simulation open"; }
part binding9:BindingRow { attribute :>> actionName="restore_entry_guard.settle0"; attribute :>> lemma="RestoreEntry.settle0Preserves"; attribute :>> scope="typed QNT AST step; source simulation open"; }
part binding10:BindingRow { attribute :>> actionName="restore_entry_guard.reserveSemantic1"; attribute :>> lemma="RestoreEntry.reserveSemantic1Preserves"; attribute :>> scope="typed QNT AST step; source simulation open"; }
part binding11:BindingRow { attribute :>> actionName="restore_entry_guard.reserveCrossRestore1"; attribute :>> lemma="RestoreEntry.reserveCrossRestore1Preserves"; attribute :>> scope="typed QNT AST step; source simulation open"; }
part binding12:BindingRow { attribute :>> actionName="restore_entry_guard.reserveForeignChild1"; attribute :>> lemma="RestoreEntry.reserveForeignChild1Preserves"; attribute :>> scope="typed QNT AST step; source simulation open"; }
part binding13:BindingRow { attribute :>> actionName="restore_entry_guard.publishRoot1"; attribute :>> lemma="RestoreEntry.publishRoot1Preserves"; attribute :>> scope="typed QNT AST step; source simulation open"; }
part binding14:BindingRow { attribute :>> actionName="restore_entry_guard.allocateMarker1"; attribute :>> lemma="RestoreEntry.allocateMarker1Preserves"; attribute :>> scope="typed QNT AST step; source simulation open"; }
part binding15:BindingRow { attribute :>> actionName="restore_entry_guard.enter1"; attribute :>> lemma="RestoreEntry.enter1Preserves"; attribute :>> scope="typed QNT AST step; source simulation open"; }
part binding16:BindingRow { attribute :>> actionName="restore_entry_guard.internalGraft1"; attribute :>> lemma="RestoreEntry.internalGraft1Preserves"; attribute :>> scope="typed QNT AST step; source simulation open"; }
part binding17:BindingRow { attribute :>> actionName="restore_entry_guard.bodyReturn1"; attribute :>> lemma="RestoreEntry.bodyReturn1Preserves"; attribute :>> scope="typed QNT AST step; source simulation open"; }
part binding18:BindingRow { attribute :>> actionName="restore_entry_guard.restoreOuter1"; attribute :>> lemma="RestoreEntry.restoreOuter1Preserves"; attribute :>> scope="typed QNT AST step; source simulation open"; }
part binding19:BindingRow { attribute :>> actionName="restore_entry_guard.invalidateMarker1"; attribute :>> lemma="RestoreEntry.invalidateMarker1Preserves"; attribute :>> scope="typed QNT AST step; source simulation open"; }
part binding20:BindingRow { attribute :>> actionName="restore_entry_guard.observeExit1"; attribute :>> lemma="RestoreEntry.observeExit1Preserves"; attribute :>> scope="typed QNT AST step; source simulation open"; }
part binding21:BindingRow { attribute :>> actionName="restore_entry_guard.settle1"; attribute :>> lemma="RestoreEntry.settle1Preserves"; attribute :>> scope="typed QNT AST step; source simulation open"; }
part binding22:BindingRow { attribute :>> actionName="restore_entry_guard.abortMarkerAllocation1"; attribute :>> lemma="RestoreEntry.abortMarkerAllocation1Preserves"; attribute :>> scope="typed QNT AST step; source simulation open"; }
part binding23:BindingRow { attribute :>> actionName="restore_entry_guard.unknownForeignExit1"; attribute :>> lemma="RestoreEntry.unknownForeignExit1Preserves"; attribute :>> scope="typed QNT AST step; source simulation open"; }
part binding24:BindingRow { attribute :>> actionName="restore_entry_guard.confirmOuterCatch1"; attribute :>> lemma="RestoreEntry.confirmOuterCatch1Preserves"; attribute :>> scope="typed QNT AST step; source simulation open"; }
part binding25:BindingRow { attribute :>> actionName="restore_entry_guard.presentOld"; attribute :>> lemma="RestoreEntry.presentOldPreserves"; attribute :>> scope="typed QNT AST step; source simulation open"; }
part binding26:BindingRow { attribute :>> actionName="restore_entry_guard.presentNew"; attribute :>> lemma="RestoreEntry.presentNewPreserves"; attribute :>> scope="typed QNT AST step; source simulation open"; }
part binding27:BindingRow { attribute :>> actionName="restore_entry_guard.presentOldAsNew"; attribute :>> lemma="RestoreEntry.presentOldAsNewPreserves"; attribute :>> scope="typed QNT AST step; source simulation open"; }
part binding28:BindingRow { attribute :>> actionName="restore_entry_guard.rejectMismatchedGuard"; attribute :>> lemma="RestoreEntry.rejectMismatchedGuardPreserves"; attribute :>> scope="typed QNT AST step; source simulation open"; }
part binding29:BindingRow { attribute :>> actionName="restore_entry_guard.repeatOldReceipt"; attribute :>> lemma="RestoreEntry.repeatOldReceiptPreserves"; attribute :>> scope="typed QNT AST step; source simulation open"; }
part binding30:BindingRow { attribute :>> actionName="restore_entry_guard.rejectUnobservedOldExit"; attribute :>> lemma="RestoreEntry.rejectUnobservedOldExitPreserves"; attribute :>> scope="typed QNT AST step; source simulation open"; }
part binding31:BindingRow { attribute :>> actionName="restore_entry_guard.loseReply0"; attribute :>> lemma="RestoreEntry.loseReply0Preserves"; attribute :>> scope="typed QNT AST step; source simulation open"; }
part binding32:BindingRow { attribute :>> actionName="restore_entry_guard.query0"; attribute :>> lemma="RestoreEntry.query0Preserves"; attribute :>> scope="typed QNT AST step; source simulation open"; }
part binding33:BindingRow { attribute :>> actionName="restore_entry_guard.loseReply1"; attribute :>> lemma="RestoreEntry.loseReply1Preserves"; attribute :>> scope="typed QNT AST step; source simulation open"; }
part binding34:BindingRow { attribute :>> actionName="restore_entry_guard.query1"; attribute :>> lemma="RestoreEntry.query1Preserves"; attribute :>> scope="typed QNT AST step; source simulation open"; }
part def ProofRow { attribute key:String; attribute lemma:String; }
part proof0:ProofRow { attribute :>> key="schedulerPreservesTicket"; attribute :>> lemma="RestoreEntry.schedulerPreservesTicket"; }
part proof1:ProofRow { attribute :>> key="navigationPreservesTicket"; attribute :>> lemma="RestoreEntry.navigationPreservesTicket"; }
part proof2:ProofRow { attribute :>> key="oldReceiptCannotSettleNew"; attribute :>> lemma="RestoreEntry.oldReceiptCannotSettleNew"; }
part proof3:ProofRow { attribute :>> key="newSettlementNeedsNewGuard"; attribute :>> lemma="RestoreEntry.newSettlementNeedsNewGuard"; }
part proof4:ProofRow { attribute :>> key="oldNonceCannotSettleNew"; attribute :>> lemma="RestoreEntry.oldNonceCannotSettleNew"; }
part proof5:ProofRow { attribute :>> key="completionRequiresRestoration"; attribute :>> lemma="RestoreEntry.completionRequiresRestoration"; }
part proof6:ProofRow { attribute :>> key="unknownRetainsGuard"; attribute :>> lemma="RestoreEntry.unknownRetainsGuard"; }
part proof7:ProofRow { attribute :>> key="queryKeepsInvocation"; attribute :>> lemma="RestoreEntry.queryKeepsInvocation"; }
part proof8:ProofRow { attribute :>> key="atMostOnce"; attribute :>> lemma="RestoreEntry.atMostOnce"; }
part proof9:ProofRow { attribute :>> key="wrongTicketRetained"; attribute :>> lemma="RestoreGuardAlgebra.wrongTicketRetained"; }
part proof10:ProofRow { attribute :>> key="wrongSerialRetained"; attribute :>> lemma="RestoreGuardAlgebra.wrongSerialRetained"; }
part proof11:ProofRow { attribute :>> key="wrongOwnerRetained"; attribute :>> lemma="RestoreGuardAlgebra.wrongOwnerRetained"; }
part proof12:ProofRow { attribute :>> key="markerStillLiveRetained"; attribute :>> lemma="RestoreGuardAlgebra.markerStillLiveRetained"; }
part proof13:ProofRow { attribute :>> key="unrestoredRetained"; attribute :>> lemma="RestoreGuardAlgebra.unrestoredRetained"; }
part proof14:ProofRow { attribute :>> key="acceptIdempotent"; attribute :>> lemma="RestoreGuardAlgebra.acceptIdempotent"; }
part proof15:ProofRow { attribute :>> key="ambientCannotRetarget"; attribute :>> lemma="RestoreGuardAlgebra.ambientCannotRetarget"; }
part proof16:ProofRow { attribute :>> key="otherGuardUntouched"; attribute :>> lemma="RestoreGuardAlgebra.otherGuardUntouched"; }
part proof17:ProofRow { attribute :>> key="step-preservation"; attribute :>> lemma="RestoreEntry.stepPreserves"; }
part proof18:ProofRow { attribute :>> key="reachable-safety"; attribute :>> lemma="RestoreEntry.reachableSafe"; }
part def RouteRow { attribute component:String; attribute actionName:String; attribute lemma:String; attribute producerAnchor:String; attribute obligationId:String; }
part route0:RouteRow { attribute :>> component="entry"; attribute :>> actionName="restore_entry_guard.reserveInitial0"; attribute :>> lemma="RestoreEntry.reserveInitial0Preserves"; attribute :>> producerAnchor="emit-return"; attribute :>> obligationId="RE-entry"; }
part route1:RouteRow { attribute :>> component="entry"; attribute :>> actionName="restore_entry_guard.reserveSemantic1"; attribute :>> lemma="RestoreEntry.reserveSemantic1Preserves"; attribute :>> producerAnchor="graft-wrapper"; attribute :>> obligationId="RE-entry"; }
part route2:RouteRow { attribute :>> component="entry"; attribute :>> actionName="restore_entry_guard.reserveCrossRestore1"; attribute :>> lemma="RestoreEntry.reserveCrossRestore1Preserves"; attribute :>> producerAnchor="native-graft"; attribute :>> obligationId="RE-entry"; }
part route3:RouteRow { attribute :>> component="entry"; attribute :>> actionName="restore_entry_guard.internalGraft0"; attribute :>> lemma="RestoreEntry.internalGraft0Preserves"; attribute :>> producerAnchor="wind-before"; attribute :>> obligationId="RE-entry"; }
part route4:RouteRow { attribute :>> component="entry"; attribute :>> actionName="restore_entry_guard.schedulerResume0"; attribute :>> lemma="RestoreEntry.schedulerResume0Preserves"; attribute :>> producerAnchor="scheduler-local"; attribute :>> obligationId="RE-entry"; }
part route5:RouteRow { attribute :>> component="guard"; attribute :>> actionName="restore_entry_guard.reserveForeignChild1"; attribute :>> lemma="RestoreEntry.reserveForeignChild1Preserves"; attribute :>> producerAnchor="ffi-caller"; attribute :>> obligationId="RE-execution"; }
part route6:RouteRow { attribute :>> component="guard"; attribute :>> actionName="restore_entry_guard.restoreOuter1"; attribute :>> lemma="RestoreEntry.restoreOuter1Preserves"; attribute :>> producerAnchor="catcher"; attribute :>> obligationId="RE-execution"; }
part route7:RouteRow { attribute :>> component="guard"; attribute :>> actionName="restore_entry_guard.observeExit1"; attribute :>> lemma="RestoreEntry.observeExit1Preserves"; attribute :>> producerAnchor="sfun-exit"; attribute :>> obligationId="RE-execution"; }
part route8:RouteRow { attribute :>> component="guard"; attribute :>> actionName="restore_entry_guard.settle1"; attribute :>> lemma="RestoreEntry.settle1Preserves"; attribute :>> producerAnchor="call-unwind"; attribute :>> obligationId="RE-execution"; }
part route9:RouteRow { attribute :>> component="roots"; attribute :>> actionName="restore_entry_guard.publishRoot1"; attribute :>> lemma="RestoreEntry.publishRoot1Preserves"; attribute :>> producerAnchor="legacy-root"; attribute :>> obligationId="RE-roots"; }
part route10:RouteRow { attribute :>> component="roots"; attribute :>> actionName="restore_entry_guard.allocateMarker1"; attribute :>> lemma="RestoreEntry.allocateMarker1Preserves"; attribute :>> producerAnchor="root-reload"; attribute :>> obligationId="RE-roots"; }
part route11:RouteRow { attribute :>> component="guard"; attribute :>> actionName="restore_entry_guard.repeatOldReceipt"; attribute :>> lemma="RestoreEntry.repeatOldReceiptPreserves"; attribute :>> producerAnchor="dead-c-frame"; attribute :>> obligationId="RE-execution"; }
part def Need { attribute obligationId:String; attribute kind:String; attribute subjectPath:String; attribute subjectScope:String; ref owner:Owner; }
part formal:Need { attribute :>> obligationId="RE-formal"; attribute :>> kind="induction"; attribute :>> subjectPath="dev/refactoring/modern-c/models/lean/RestoreEntry.lean"; attribute :>> subjectScope="two-ticket intent and completion safety; all modeled steps"; ref :>> owner=guardOwner; }
part algebra:Need { attribute :>> obligationId="RE-algebra"; attribute :>> kind="algebra"; attribute :>> subjectPath="dev/refactoring/modern-c/models/lean/RestoreGuardAlgebra.lean"; attribute :>> subjectScope="arbitrary GuardId dispatch and immutable outcome; trusted witness"; ref :>> owner=guardOwner; }
part ingress:Need { attribute :>> obligationId="RE-entry"; attribute :>> kind="source"; attribute :>> subjectPath="vendor/gambit/gsc/_t-c-2.scm"; attribute :>> subjectScope="complete caller intent and generated point/root/restore mapping"; ref :>> owner=entryOwner; }
part execution:Need { attribute :>> obligationId="RE-execution"; attribute :>> kind="source"; attribute :>> subjectPath="vendor/gambit/lib/setup.c"; attribute :>> subjectScope="real stable guard and outer exit signer including all exceptional exits"; ref :>> owner=guardOwner; }
part roots:Need { attribute :>> obligationId="RE-roots"; attribute :>> kind="source"; attribute :>> subjectPath="vendor/gambit/lib/c_intf.c"; attribute :>> subjectScope="all FFI and restored GVM slots rooted across allocating and scan cut"; ref :>> owner=rootsOwner; }
part platform:Need { attribute :>> obligationId="RE-platform"; attribute :>> kind="platform"; attribute :>> subjectPath="dev/refactoring/modern-c/language-baseline-design.org"; attribute :>> subjectScope="C23 locking or atomics, finite IDs and effective Darwin ABI identity"; ref :>> owner=guardOwner; }
part emission:Need { attribute :>> obligationId="RE-emission"; attribute :>> kind="equivalence"; attribute :>> subjectPath="dev/refactoring/modern-c/ticket-capability-retirement-design.org"; attribute :>> subjectScope="complete late writers and normalization equivalence before retirement"; ref :>> owner=entryOwner; }
}
