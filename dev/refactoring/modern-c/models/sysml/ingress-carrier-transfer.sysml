package GambitIngressCarrierTransfer { private import ScalarValues::*;
part def Route { attribute key:String; attribute sourcePath:String; attribute needle:String; attribute obligation:String; }
part route0:Route { attribute :>> key="data-rc-load"; attribute :>> sourcePath="vendor/gambit/lib/mem.c"; attribute :>> needle="return h->data;"; attribute :>> obligation="RC data load returns a plain value; owning root and source borrow are separate"; }
part route1:Route { attribute :>> key="rc-payload-scan"; attribute :>> sourcePath="vendor/gambit/lib/mem.c"; attribute :>> needle="mark_array (work, &h->data, 1);"; attribute :>> obligation="Current collector updates RC data slot through the frozen execution context"; }
part route2:Route { attribute :>> key="frozen-context-roots"; attribute :>> sourcePath="vendor/gambit/lib/mem.c"; attribute :>> needle="require_gc_phase (participant, ___GC_ROOTS_FROZEN);"; attribute :>> obligation="Root publication must join the collector membership/freeze cut"; }
part route3:Route { attribute :>> key="context-rc-all-participants"; attribute :>> sourcePath="vendor/gambit/lib/mem.c"; attribute :>> needle="mark_rc (work, context);"; attribute :>> obligation="Current checkout scans RC in each execution root context; do not inherit processor-zero-only claim"; }
part route4:Route { attribute :>> key="tcl-still-source"; attribute :>> sourcePath="vendor/gambit/examples/tcltk/tcltk.scm"; attribute :>> needle="counted object that contains a ___STILL Scheme vector"; attribute :>> obligation="Vector address is stable; contained procedure may move and root lifetime still needs a lease"; }
part route5:Route { attribute :>> key="tcl-read-entry"; attribute :>> sourcePath="vendor/gambit/examples/tcltk/tcltk.scm"; attribute :>> needle="char *result = tcltk_call (___EXT(___data_rc)"; attribute :>> obligation="Borrow native header before root handshake and load protected payload under collector coordination"; }
part route6:Route { attribute :>> key="tcl-delete-release"; attribute :>> sourcePath="vendor/gambit/examples/tcltk/tcltk.scm"; attribute :>> needle="___EXT(___release_scmobj) (___EXT(___data_rc)"; attribute :>> obligation="Deletion must defer root/header reclamation until nested borrows drain"; }
part route7:Route { attribute :>> key="run-processor-caller"; attribute :>> sourcePath="vendor/gambit/lib/setup.c"; attribute :>> needle="___err = ___run (___PSP thunk);"; attribute :>> obligation="Direct run helper receives a value; replace with owned carrier or qualified protected handoff"; }
part route8:Route { attribute :>> key="thread-thunk-source"; attribute :>> sourcePath="vendor/gambit/lib/setup.c"; attribute :>> needle="___SCMOBJ thunk = self->data_scmobj;"; attribute :>> obligation="Thread payload copy precedes sync participation; no independent thread field scan proved"; }
part route9:Route { attribute :>> key="bootstrap-thunk-source"; attribute :>> sourcePath="vendor/gambit/lib/setup.c"; attribute :>> needle="___MODULE_DESCR_THUNK));"; attribute :>> obligation="Bootstrap thunk comes from program descriptors; exact freeze and root lease still need qualification"; }
part route10:Route { attribute :>> key="still-root-release"; attribute :>> sourcePath="vendor/gambit/lib/mem.c"; attribute :>> needle="___EXP_FUNC(___SCMOBJ,___release_scmobj)"; attribute :>> obligation="Still refcount decrement is distinct from retiring a root view or freeing RC header"; }
part route11:Route { attribute :>> key="retained-result-code"; attribute :>> sourcePath="vendor/gambit/examples/tcltk/tcltk.scm"; attribute :>> needle="___CAST(Tcl_FreeProc*,___EXT(___release_string))"; attribute :>> obligation="Result destructor code lease can outlive RC header independently"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule6; ref part :>> counterpart=GambitRuntimeComposition::blueprintModule3; attribute :>> key="source-carrier"; attribute :>> owner="foreign/roots"; attribute :>> actionName="beginCut readSource"; attribute :>> invariant="Source native and Scheme lifetimes remain protected before any value load"; attribute :>> gap="Raw SCMOBJ and VM storage borrow alone do not prove root freshness"; }
part contract1:Contract { ref part :>> accountable=GambitRuntimeComposition::blueprintModule3; ref part :>> counterpart=GambitRuntimeComposition::blueprintModule4; attribute :>> key="target-root-publication"; attribute :>> owner="roots/collector"; attribute :>> actionName="registerTarget publishTarget"; attribute :>> invariant="Initialize target from current source under collector cut then make scanner visible"; attribute :>> gap="Root adapter must join context freeze and future GC membership; distinct writable slots or one canonical scanner"; }
part contract2:Contract { ref part :>> accountable=GambitRuntimeComposition::blueprintModule7; ref part :>> counterpart=GambitRuntimeComposition::blueprintModule3; attribute :>> key="overlap-custody"; attribute :>> owner="release/roots"; attribute :>> actionName="publishUnknown queryReceipt releaseSource"; attribute :>> invariant="Release source registration only after exact target receipt; unknown retains source"; attribute :>> gap="Source registration release is not a still decrement RC free or code unload"; }
part contract3:Contract { ref part :>> accountable=GambitRuntimeComposition::blueprintModule6; ref part :>> counterpart=GambitRuntimeComposition::blueprintModule5; attribute :>> key="nested-native-lifetime"; attribute :>> owner="foreign/control"; attribute :>> actionName="enterChild requestDelete leaveChild dropRoot"; attribute :>> invariant="Parent exit and deletion do not clear child native borrow or Scheme root"; attribute :>> gap="Real nested Tcl behavior and late callback closure require owner-side evidence"; }
part contract4:Contract { ref part :>> accountable=GambitRuntimeComposition::blueprintModule2; ref part :>> counterpart=GambitRuntimeComposition::blueprintModule3; attribute :>> key="run-source-family"; attribute :>> owner="execution/roots"; attribute :>> actionName="readSource registerTarget"; attribute :>> invariant="Bootstrap descriptors thread data and caller handles keep source identity through all safepoints"; attribute :>> gap="Complete public run callers and thread data alias scan closure remain open"; }
part contract5:Contract { ref part :>> accountable=GambitRuntimeComposition::blueprintModule8; ref part :>> counterpart=GambitRuntimeComposition::blueprintModule0; attribute :>> key="evidence-publication"; attribute :>> owner="build/semantic"; attribute :>> actionName="registerTarget publishTarget releaseSource"; attribute :>> invariant="Actual guard/update meaning and source-bound endorsements need exact identity"; attribute :>> gap="C11 extraction and all-action simulation remain unproved"; }
part def Obligation { attribute key:String; attribute status:String; attribute scope:String; attribute counterexample:String; }
part obligation0:Obligation { attribute :>> key="handoff-coverage"; attribute :>> status="bounded-checked"; attribute :>> scope="One source target and bounded GC validity stamps; successful and unknown publication"; attribute :>> counterexample="Source-first release and stale target after collection lose admitted coverage"; }
part obligation1:Obligation { attribute :>> key="nested-custody"; attribute :>> status="bounded-checked"; attribute :>> scope="One parent child deletion unknown exit and independent result destructor"; attribute :>> counterexample="Parent return or delete notification cannot release child lifetime"; }
part obligation2:Obligation { attribute :>> key="release-coverage"; attribute :>> status="conditional-proved"; attribute :>> scope="Source release guard preserves target root coverage; stale values reject registration"; attribute :>> counterexample="Assumes collector cut and authentic target receipt"; }
part obligation3:Obligation { attribute :>> key="c11-order"; attribute :>> status="conditional-proved"; attribute :>> scope="Publication observation precedes source release given HB embedding"; attribute :>> counterexample="No C11 memory-model execution or effective backend proof"; }
part obligation4:Obligation { attribute :>> key="actual-expressions"; attribute :>> status="conditional-proved"; attribute :>> scope="Actual registerTarget publishTarget releaseSource expressions"; attribute :>> counterexample="Restricted JSON projector remains trusted"; }
part obligation5:Obligation { attribute :>> key="source-bridge"; attribute :>> status="open"; attribute :>> scope="Root adapter freeze integration source carrier users and actual exception closure"; attribute :>> counterexample="Current context RC scan does not prove arbitrary external raw values are rooted"; }
part obligation6:Obligation { attribute :>> key="json-domain"; attribute :>> status="partially-proved"; attribute :>> scope="91-row checked finite environment and strict projection controls"; attribute :>> counterexample="Full parser/extractor and source correspondence remain open"; }
part def Gain { attribute key:String; attribute avoided:String; attribute added:String; attribute condition:String; }
part gain0:Gain { attribute :>> key="overlap-registration"; attribute :>> avoided="Redundant retained source registration after known successful target handoff"; attribute :>> added="One source/target overlap per entry and exact receipt/query on unknown result"; attribute :>> condition="Target scan coverage and identity proven before source registration release"; }
part gain1:Gain { attribute :>> key="existing-context-scan"; attribute :>> avoided="A parallel duplicate RC scanner is unnecessary if current participant adapter qualifies"; attribute :>> added="Integrate RootBundle membership with frozen execution roots and future round roster"; attribute :>> condition="Current source includes per-context RC scan but no native carrier API is established"; }
part gain2:Gain { attribute :>> key="still-vector-reuse"; attribute :>> avoided="Copying Tcl still vectors solely to stabilize their address"; attribute :>> added="Native borrow root lifetime and synchronized procedure-field reads still required"; attribute :>> condition="Still identity already stable; do not invent relocation or remove moving-field scan"; }
part gain3:Gain { attribute :>> key="independent-result"; attribute :>> avoided="Retaining RC/Scheme root solely for an independent native string result"; attribute :>> added="Separate destructor code lease resident decoder and result delivery record"; attribute :>> condition="No Scheme alias in result; retain actual destructor provider until its last use"; }
part gain4:Gain { attribute :>> key="modern-c-service"; attribute :>> avoided="Second-language implementation is unnecessary for carrier registration protocol"; attribute :>> added="Generated entry root spec resident lease/custody and qualified collector cut"; attribute :>> condition="Zig does not eliminate source validity nested borrow or GC handshake obligations"; }
part def Binding { attribute key:String; attribute qntAction:String; attribute leanLemma:String; attribute refinement:String; attribute guardLemma:String; attribute updateLemma:String; }
part binding0:Binding { attribute :>> key="guard"; attribute :>> qntAction="registerTarget"; attribute :>> leanLemma="staleLocalRejects"; attribute :>> refinement="Actual selected action meaning checked with source and C11 premises open"; attribute :>> guardLemma="registerTargetGuardMeaning"; attribute :>> updateLemma="registerTargetNextMeaning"; }
part binding1:Binding { attribute :>> key="roots"; attribute :>> qntAction="publishTarget"; attribute :>> leanLemma="noCutRejectsPublish"; attribute :>> refinement="Actual selected action meaning checked with source and C11 premises open"; attribute :>> guardLemma="publishTargetGuardMeaning"; attribute :>> updateLemma="publishTargetNextMeaning"; }
part binding2:Binding { attribute :>> key="release"; attribute :>> qntAction="releaseSource"; attribute :>> leanLemma="releasePreservesCoverage"; attribute :>> refinement="Actual selected action meaning checked with source and C11 premises open"; attribute :>> guardLemma="releaseSourceGuardMeaning"; attribute :>> updateLemma="releaseSourceNextMeaning"; }
part def Flow { attribute fromNode:String; attribute toNode:String; attribute reason:String; }
part flow0:Flow { attribute :>> fromNode="c0"; attribute :>> toNode="c1"; attribute :>> reason="Protected source value initializes target"; }
part flow1:Flow { attribute :>> fromNode="c1"; attribute :>> toNode="c2"; attribute :>> reason="Target scan visibility precedes source release"; }
part flow2:Flow { attribute :>> fromNode="c2"; attribute :>> toNode="c3"; attribute :>> reason="Source-root handoff does not settle nested native borrows"; }
part flow3:Flow { attribute :>> fromNode="c4"; attribute :>> toNode="c0"; attribute :>> reason="Run source families require protected carriers"; }
part flow4:Flow { attribute :>> fromNode="c1"; attribute :>> toNode="o0"; attribute :>> reason="Current epoch and registered root coverage"; }
part flow5:Flow { attribute :>> fromNode="c2"; attribute :>> toNode="o2"; attribute :>> reason="Guard preserves target coverage"; }
part flow6:Flow { attribute :>> fromNode="c3"; attribute :>> toNode="o1"; attribute :>> reason="Nested callback and destructor lifetime checks"; }
part flow7:Flow { attribute :>> fromNode="c1"; attribute :>> toNode="o3"; attribute :>> reason="Actual release-acquire and collector cut needed"; }
part flow8:Flow { attribute :>> fromNode="c5"; attribute :>> toNode="o4"; attribute :>> reason="Selected typed action meanings"; }
part flow9:Flow { attribute :>> fromNode="c5"; attribute :>> toNode="o6"; attribute :>> reason="Exact finite JSON reference domain"; }
part flow10:Flow { attribute :>> fromNode="o4"; attribute :>> toNode="o5"; attribute :>> reason="Expression meaning is not source simulation"; }
part flow11:Flow { attribute :>> fromNode="c0"; attribute :>> toNode="o5"; attribute :>> reason="Raw source identity and public caller closure"; }
part history:GambitAssuranceRouting::ModelNeed { ref part :>> owner=GambitBuildAssurance::planner.component; attribute :>> obligationId="IC-H"; attribute :>> kind="interleaving"; attribute :>> subjectPath="dev/refactoring/modern-c/models/quint/ingress_carrier_transfer.qnt"; attribute :>> subjectScope="Source-target overlap GC validity updates target receipts and retained source on failure"; attribute :>> premise="Bounded models and restricted algebra only; no runtime implementation or native acceptance"; }
part shards:GambitAssuranceRouting::ModelNeed { ref part :>> owner=GambitBuildAssurance::planner.component; attribute :>> obligationId="IC-B"; attribute :>> kind="interleaving"; attribute :>> subjectPath="dev/refactoring/modern-c/models/quint/ingress_nested_custody.qnt"; attribute :>> subjectScope="Parent child deletion unknown completion and independent result destructor lifetime"; attribute :>> premise="Bounded models and restricted algebra only; no runtime implementation or native acceptance"; }
part induction:GambitAssuranceRouting::ModelNeed { ref part :>> owner=GambitBuildAssurance::planner.component; attribute :>> obligationId="IC-I"; attribute :>> kind="induction"; attribute :>> subjectPath="dev/refactoring/modern-c/models/lean/IngressCarrierTransfer.lean"; attribute :>> subjectScope="Source-release coverage stale-value rejection and conditional publication order"; attribute :>> premise="Bounded models and restricted algebra only; no runtime implementation or native acceptance"; }
part expression:GambitAssuranceRouting::ModelNeed { ref part :>> owner=GambitBuildAssurance::planner.component; attribute :>> obligationId="IC-X"; attribute :>> kind="induction"; attribute :>> subjectPath="dev/refactoring/modern-c/models/lean/IngressCarrierAst.lean"; attribute :>> subjectScope="Actual registerTarget publishTarget releaseSource meanings and finite row domain"; attribute :>> premise="Bounded models and restricted algebra only; no runtime implementation or native acceptance"; }
part source:GambitAssuranceRouting::ModelNeed { ref part :>> owner=GambitBuildAssurance::planner.component; attribute :>> obligationId="IC-S"; attribute :>> kind="source-refinement"; attribute :>> subjectPath="dev/refactoring/modern-c/ingress-carrier-transfer-design.org"; attribute :>> subjectScope="Current context GC source callers nested Tcl and raw run carrier closure OPEN"; attribute :>> premise="Bounded models and restricted algebra only; no runtime implementation or native acceptance"; }
part platform:GambitAssuranceRouting::ModelNeed { ref part :>> owner=GambitBuildAssurance::planner.component; attribute :>> obligationId="IC-E"; attribute :>> kind="environment-refinement"; attribute :>> subjectPath="dev/refactoring/modern-c/ingress-carrier-transfer-design.org"; attribute :>> subjectScope="C11 root freeze roster admission storage and object lifetime composition OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitFfiScopeRootAdmission::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; attribute sourcePath:String; attribute needle:String; }
part endorsement0:Endorsement { attribute :>> roleName="semantic"; attribute :>> scope="Source-target root overlap current epoch and exact registered destination"; attribute :>> issuer="Execution-root and collector adapter owner"; attribute :>> sourcePath="vendor/gambit/lib/mem.c"; attribute :>> needle="mark_rc (work, context);"; }
part endorsement1:Endorsement { attribute :>> roleName="foreign"; attribute :>> scope="All parent child native borrows and deletion effects drained"; attribute :>> issuer="Tcl command adapter owner"; attribute :>> sourcePath="vendor/gambit/examples/tcltk/tcltk.scm"; attribute :>> needle="___HIDDEN void scheme_delete_cmd"; }
part endorsement2:Endorsement { attribute :>> roleName="resident"; attribute :>> scope="Immutable result delivery and independently retained destructor provider"; attribute :>> issuer="Resident result and cleanup owner"; attribute :>> sourcePath="vendor/gambit/examples/tcltk/tcltk.scm"; attribute :>> needle="___CAST(Tcl_FreeProc*,___EXT(___release_string))"; }
part flow12:Flow { attribute :>> fromNode="c3"; attribute :>> toNode="o5"; attribute :>> reason="Tcl owner and exception qualification"; }
part flow13:Flow { attribute :>> fromNode="c2"; attribute :>> toNode="c5"; attribute :>> reason="Receipt identity and evidence binding"; }
part flow14:Flow { attribute :>> fromNode="c4"; attribute :>> toNode="o5"; attribute :>> reason="Thread and bootstrap safepoint coverage"; }
part flow15:Flow { attribute :>> fromNode="c1"; attribute :>> toNode="o5"; attribute :>> reason="Current frozen participant source integration"; }
}
