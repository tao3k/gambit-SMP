package GambitSourceEpochs {
 private import ScalarValues::*;
 attribute scope:String="Whole source-epoch refinement: immutable study proof, unchanged committed-checkout gate, retired rule projections and documentary causal-source borrowing. No runtime or scheduler changes.";
 attribute stage:String="Support only; progressDelta0.156 scoped cases in10 complete modules. Architecture3/4 and independent SMP1/12. Full framework and matched hosted release remain independent.";
 attribute sourceRule:String="binding validates the original declaration/transport; validate retains the original exact index gate. Immutable audit verifies commit/tree/parents and regular blob identities, applies the existing bounded exact patch to selected files and checks every candidate SHA. No full source archive or native workspace is created by that audit.";
 attribute checkoutRule:String="require_committed retains the original committed gitlink, current file bytes and document checks, adds exact index validation and rechecks after audit. Object proof never substitutes for checkout proof; default checkoutChecked is false.";
 attribute fixtureRule:String="Retired fixture view SHA, statuses and negative current-loader gate are unchanged. One explicit original Git source fills the source-reference role only. Five real caller modules retain their original assertions; raw model import closure remains byte-bound.";
 attribute causalRule:String="Only supporting claim references may name immutable Git regular sources. Baseline identities, tested changes, causal documents, archives, runtime/campaign and budget checks keep physical binding. Borrowed bytes are reread after real ASCENT inference; wrong owner/blob/SHA, missing objects and log-reader substitution refuse.";
 attribute closureRule:String="Seven explicit references bind two original source objects. Twelve live caller documents update only required dependent hashes; original whitespace, reasoning, statuses, failure identities and budgets stay fixed.21 existing Recipes and48 views validate; one unchanged unregistered legacy context stays REFUSED_UNRESOLVED, never a view pass.";
 attribute formalDuty:String="SysML owns proof roles and submission needs; ASCENT owns conditional review/submission. Existing QNT owns scheduling/epoch properties and Lean conditional algebra. This source/host refinement neither duplicates them nor claims modern-c runtime acceptance.";
 attribute remoteRule:String="807 framework runs all2421 with0 missing,36 failures20 errors2 skips. A new10s process-birth failure is retained and unassigned; the local original1-case module passes but is not a matched Linux attribution. Threads GSC step retains300s budget; the numeric _num.scm child times out at90s,exit-9, reaped/quiescent, compile/execute phase unresolved; hosted macOS pair remains queued. Fourth result stays blocked.";
 attribute diagram:String="direction: right\nlock: Original lock and commit / tree / parent identities\nobjects: Exact regular Git source objects\nindex: Current index / HEAD / working file proof\nstatic: Selected-file patch audit\nresult: Immutable source proof; checkoutChecked false\nstrict: require_committed retains all checkout gates\nretired: Retired rule fixtures; never current input\nclaim: Documentary causal-source borrow\ninfer: Existing ASCENT eligibility and final source recheck\nruntime: Actual runtime and campaign recheck\nremote: Full CI and matched macOS still required\nlock -> objects\nlock -> index\nobjects -> static: five selected files; no full archive\nstatic -> result\nindex -> strict: unchanged refusal gates\nobjects -> retired: original view SHA / status unchanged\nobjects -> claim: exact original payload\nclaim -> infer: source citations only\nruntime -> infer: no artifact substitution\ninfer -> remote: eligibility does not grant execution\n";
 part def ProofRole { attribute path:String; attribute anchor:String; attribute duty:String; }
 part objectProof:ProofRole { attribute :>> path="src/gambit_smp/source_materialize.py"; attribute :>> anchor="source_binding;audit_slice"; attribute :>> duty="Regular locked blobs, absence distinct from empty file, exact patch inventory and candidate bytes; leave newer dirty checkout unchanged."; }
 part checkoutProof:ProofRole { attribute :>> path="src/gambit_smp/source_provision.py;src/gambit_smp/reproduction_check.py"; attribute :>> anchor="binding;validate;verify_object_identity;verify_committed;check_source;check"; attribute :>> duty="Separate immutable source truth from index/HEAD/working-file truth without disabling either guard."; }
 part retiredFixture:ProofRole { attribute :>> path="tests/historical_view.py;tests/fixtures/historical-view-pointers.json"; attribute :>> anchor="projection;identities"; attribute :>> duty="Exact original bytes for retired test rules, never current research/admission inputs."; }
 part causalBorrow:ProofRole { attribute :>> path="src/gambit_smp/native_review.py"; attribute :>> anchor="review_source_bytes;project_review;preflight"; attribute :>> duty="Typed supporting-source borrow across inference; no current artifact, raw-log, runtime or execution substitution."; }
 part actionInputs:ProofRole { attribute :>> path="src/gambit_smp/research_actions.py"; attribute :>> anchor="_inputs -> ascent_program.input_attestations"; attribute :>> duty="Reuse the existing verified installed/project owner adapter; reject every undeclared external owner."; }
 part def Need { attribute id:String; ref part gate:GambitCommitGates::Gate; attribute method:String; attribute artifact:String; attribute scope:String; }
 part tests:Need { attribute :>> id="SOURCE-EPOCHS-TESTS"; ref part :>> gate=GambitCommitGates::tests; attribute :>> method="native"; attribute :>> artifact="evidence/research/retained/modern-c/source-epochs/receipt.json"; attribute :>> scope="Whole source-epoch support only; no full framework or native SMP admission"; }
 part learning:Need { attribute :>> id="SOURCE-EPOCHS-LEARNING"; ref part :>> gate=GambitCommitGates::learning; attribute :>> method="source-refinement"; attribute :>> artifact="evidence/research/retained/modern-c/source-epochs/receipt.json"; attribute :>> scope="Whole source-epoch support only; no full framework or native SMP admission"; }
 part process:Need { attribute :>> id="SOURCE-EPOCHS-PROCESS"; ref part :>> gate=GambitCommitGates::process; attribute :>> method="source-refinement"; attribute :>> artifact="evidence/research/retained/modern-c/source-epochs/receipt.json"; attribute :>> scope="Whole source-epoch support only; no full framework or native SMP admission"; }
 part models:Need { attribute :>> id="SOURCE-EPOCHS-MODELS"; ref part :>> gate=GambitCommitGates::models; attribute :>> method="source-refinement"; attribute :>> artifact="evidence/research/retained/modern-c/source-epochs/receipt.json"; attribute :>> scope="Whole source-epoch support only; no full framework or native SMP admission"; }
 part questions:Need { attribute :>> id="SOURCE-EPOCHS-QUESTIONS"; ref part :>> gate=GambitCommitGates::questions; attribute :>> method="source-refinement"; attribute :>> artifact="evidence/research/retained/modern-c/source-epochs/receipt.json"; attribute :>> scope="Whole source-epoch support only; no full framework or native SMP admission"; }
 part submission:GambitCommitGates::SubmissionUnit { attribute :>> kind="support"; attribute :>> result=""; attribute :>> progressDelta=0; attribute :>> supportPaths="evidence/research/current-source-full-bootstrap/fdset-interpreted-intent.json;evidence/research/current-source-full-bootstrap/interpreted-intent.json;evidence/research/incremental-builds/qualified-unit-intent.json;evidence/research/smp-threaded-vm-native-grid/bazel-profile-gsi-intent.json;evidence/research/smp-threaded-vm-native-grid/btq-retry-gsi-intent.json;evidence/research/smp-threaded-vm-native-grid/environment-causal-evidence.json;evidence/research/smp-threaded-vm-native-grid/global-cleanup-gsi-intent.json;evidence/research/smp-threaded-vm-native-grid/gsi-complete-reviewed-intent.json;evidence/research/smp-threaded-vm-native-grid/vector-arity-pr-full-scope-intent.json;evidence/research/smp-threaded-vm-native-grid/vector-arity-table-iteration-causal.json;evidence/research/smp-threaded-vm-native-grid/vector-arity-table-iteration-intent.json;evidence/research/smp-threaded-vm-native-grid/vector-arity-table-iteration-review-intent.json;src/gambit_smp/native_review.py;src/gambit_smp/reproduction_check.py;src/gambit_smp/research_actions.py;src/gambit_smp/source_materialize.py;src/gambit_smp/source_provision.py;tests/fixtures/historical-view-pointers.json;tests/historical_view.py;tests/test_concurrent_gc_evidence_view.py;tests/test_evidence_views.py;tests/test_ffi_execution_evidence_view.py;tests/test_gc_design_reasons.py;tests/test_native_retry_review.py;tests/test_payload_vm_evidence_view.py;tests/test_reproduction_check.py;tests/test_sealed_checkpoint_recovery.py;tests/test_source_materialize.py;tests/test_source_provision.py;dev/refactoring/modern-c/models/sysml/source-epochs.sysml;dev/refactoring/modern-c/source-epochs.org;dev/refactoring/modern-c/diagrams/source-epochs.d2;dev/refactoring/modern-c/diagrams/source-epochs.svg;dev/refactoring/modern-c/branch-checklist.org;evidence/research/retained/modern-c/source-epochs/receipt.json;evidence/research/retained/modern-c/source-epochs/native-domains.json;evidence/research/retained/modern-c/source-epochs/canonical.json;evidence/research/retained/modern-c/source-epochs/remote.json;evidence/research/retained/modern-c/source-epochs/open-obligations.json"; attribute :>> testModules="tests/test_source_provision.py;tests/test_reproduction_check.py;tests/test_source_materialize.py;tests/test_evidence_views.py;tests/test_gc_design_reasons.py;tests/test_concurrent_gc_evidence_view.py;tests/test_ffi_execution_evidence_view.py;tests/test_payload_vm_evidence_view.py;tests/test_native_retry_review.py;tests/test_sealed_checkpoint_recovery.py"; }
}
