/* Target architecture ownership, not a current repair workflow. */
package GambitRuntimeOwnership { private import ScalarValues::*;
part def CompositionContract { ref part enumeration:RootEnumerationProgram; ref part execution:GambitRuntimeComposition::BlueprintModule; ref part roots:GambitRuntimeComposition::BlueprintModule; ref part collector:GambitRuntimeComposition::BlueprintModule; ref part control:GambitRuntimeComposition::BlueprintModule; ref part foreign:GambitRuntimeComposition::BlueprintModule; }
part contract:CompositionContract { ref part :>> enumeration=program; ref part :>> execution=GambitRuntimeComposition::blueprintModule2; ref part :>> roots=GambitRuntimeComposition::blueprintModule3; ref part :>> collector=GambitRuntimeComposition::blueprintModule4; ref part :>> control=GambitRuntimeComposition::blueprintModule5; ref part :>> foreign=GambitRuntimeComposition::blueprintModule6; }
part def OwnershipDomain { ref part owner:GambitRuntimeComposition::BlueprintModule; attribute key:String; attribute role:String; attribute owns:String; attribute lifetime:String; attribute modelFields:String; attribute boundary:String; }
part def OwnershipLaw { attribute kernelPath:String; attribute modelPath:String; ref part domain:OwnershipDomain; ref part seam:GambitRuntimeComposition::BlueprintInterface; attribute sourceKey:String; attribute key:String; attribute predicate:String; attribute kernel:String; attribute law:String; attribute proofLimit:String; attribute refinement:String; }
part domain0:OwnershipDomain { ref part :>> owner=GambitRuntimeComposition::blueprintModule2; attribute :>> key="execution"; attribute :>> role="ExecutionContext"; attribute :>> owns="Scheme control/register/cache state and exclusive run grant"; attribute :>> lifetime="Logical suspend/restore/retire; does not own collector task lifetime"; attribute :>> modelFields="owners/cache/alive"; attribute :>> boundary="Source-causal usable host plus generated checkpoint, not just TLS"; }
part domain1:OwnershipDomain { ref part :>> owner=GambitRuntimeComposition::blueprintModule3; attribute :>> key="roots"; attribute :>> role="FrozenRootStore"; attribute :>> owns="Actual rooted slots, origin/generation, layout and mutable collector update address"; attribute :>> lifetime="VM custody survives logical context/physical execution-carrier removal"; attribute :>> modelFields="slots/manifest/frozen/view/location"; attribute :>> boundary="Closed writer set and last borrower; retained payload or real redirected slots"; }
part domain2:OwnershipDomain { ref part :>> owner=GambitRuntimeComposition::blueprintModule4; attribute :>> key="collector"; attribute :>> role="CollectorWorkContext"; attribute :>> owns="Task/producer/initialization/copy/Tail/queue/claim responsibility"; attribute :>> lifetime="Grant and phase outlive the original executing carrier"; attribute :>> modelFields="task/taskOwner/worker/childTicket"; attribute :>> boundary="An integer work ID is not a raw C cursor migration certificate"; }
part domain3:OwnershipDomain { ref part :>> owner=GambitRuntimeComposition::blueprintModule5; attribute :>> key="control"; attribute :>> role="CapturedFrame"; attribute :>> owns="Scheme continuation graph, FrameSpec and descriptor/code leases"; attribute :>> lifetime="Independent of source ExecutionContext and fresh for each activation"; attribute :>> modelFields="captured/resumes/resumeLease/descriptor"; attribute :>> boundary="Do not silently restrict Gambit to one-shot or consume a captured graph on restore"; }
part domain4:OwnershipDomain { ref part :>> owner=GambitRuntimeComposition::blueprintModule6; attribute :>> key="foreign"; attribute :>> role="NativeReturnSegment"; attribute :>> owns="Live native activation, catcher/marker ownership and legal origin"; attribute :>> lifetime="OS C stack cannot retire while return/escape origin remains live"; attribute :>> modelFields="native/retired"; attribute :>> boundary="Unknown return is retained; QNT pin is not complete foreign-root coverage"; }
part domain5:OwnershipDomain { ref part :>> owner=GambitRuntimeComposition::blueprintModule1; attribute :>> key="native"; attribute :>> role="ContractRealization"; attribute :>> owns="C23 layouts and generated call/checkpoint/restore operations"; attribute :>> lifetime="ABI-bound consumer of Scheme-owned semantic plan"; attribute :>> modelFields="Frame/Slot/Activation Lean kernels"; attribute :>> boundary="No new semantic owner in C macros, Zig or an ABI adapter"; }
part law0:OwnershipLaw { attribute :>> kernelPath="dev/refactoring/modern-c/models/lean/RuntimeOwnership.lean"; attribute :>> modelPath="dev/refactoring/modern-c/models/quint/runtime_ownership.qnt"; ref part :>> seam=GambitRuntimeComposition::blueprintInterface3; attribute :>> sourceKey="context-use"; ref part :>> domain=domain0; attribute :>> key="run-grant"; attribute :>> predicate="noExpiredOwner"; attribute :>> kernel="decodeRejectsWrongLayout"; attribute :>> law="Execution needs live context, legal carrier and post-GC cache; TLS pointer alone is insufficient"; attribute :>> proofLimit="Kernel rejects wrong layout; model ownership predicates still need complete source refinement"; attribute :>> refinement="Reacquire actual context identity and reload before every supported entry/reentry"; }
part law1:OwnershipLaw { attribute :>> kernelPath="dev/refactoring/modern-c/models/lean/RuntimeOwnership.lean"; attribute :>> modelPath="dev/refactoring/modern-c/models/quint/runtime_ownership.qnt"; ref part :>> seam=GambitRuntimeComposition::blueprintInterface1; attribute :>> sourceKey="rc-freeze"; ref part :>> domain=domain1; attribute :>> key="frozen-roots"; attribute :>> predicate="rootCustody"; attribute :>> kernel="rewriteCoversEveryDeclaredRoot"; attribute :>> law="A frozen authoritative slot store survives source-context retirement until scan/borrow completion"; attribute :>> proofLimit="Lean covers declared root slots only; concrete FrameSpec completeness and aliases remain open"; attribute :>> refinement="Map every register/saved/stack/RC/resize/still root plus retained descriptor interpretation"; }
part law2:OwnershipLaw { attribute :>> kernelPath="dev/refactoring/modern-c/models/lean/RuntimeOwnership.lean"; attribute :>> modelPath="dev/refactoring/modern-c/models/quint/runtime_ownership.qnt"; ref part :>> seam=GambitRuntimeComposition::blueprintInterface4; attribute :>> sourceKey="carrier-use"; ref part :>> domain=domain2; attribute :>> key="work-custody"; attribute :>> predicate="noHiddenWork"; attribute :>> kernel="scanPreservesFrameIdentity"; attribute :>> law="Child reservation is owned before parent finish; claimed work is not a public queue entry"; attribute :>> proofLimit="Frame identity kernel is supporting metadata, not a task-conservation or termination proof"; attribute :>> refinement="Refine reserve/init/publish/claim/scan/finish, private cursor/Tail, weak and resize work"; }
part law3:OwnershipLaw { attribute :>> kernelPath="dev/refactoring/modern-c/models/lean/RuntimeOwnership.lean"; attribute :>> modelPath="dev/refactoring/modern-c/models/quint/runtime_ownership.qnt"; ref part :>> seam=GambitRuntimeComposition::blueprintInterface2; attribute :>> sourceKey="frame-copy"; ref part :>> domain=domain3; attribute :>> key="multishot"; attribute :>> predicate="multishot"; attribute :>> kernel="multiShotHasFreshActivations"; attribute :>> law="Restoring creates a fresh activation while the captured graph remains rooted"; attribute :>> proofLimit="Pure snapshot kernel; no proof of frame/denv mutation, dynamic-wind or actual Scheme contextual equivalence"; attribute :>> refinement="Prove relocation, mutation and decode preserve all legal multiple restores"; }
part law4:OwnershipLaw { attribute :>> kernelPath="dev/refactoring/modern-c/models/lean/RuntimeOwnership.lean"; attribute :>> modelPath="dev/refactoring/modern-c/models/quint/runtime_ownership.qnt"; ref part :>> seam=GambitRuntimeComposition::blueprintInterface6; attribute :>> sourceKey="root-bridge"; ref part :>> domain=domain4; attribute :>> key="native-origin"; attribute :>> predicate="nativeLifetime"; attribute :>> kernel="returnIdentityPreserved"; attribute :>> law="Logical execution departure does not free live native return origin"; attribute :>> proofLimit="Code-point preservation kernel; native C stack and escape closure remain independent premises"; attribute :>> refinement="Trace actual call/run/SFUN landing and exceptional/nonreturning suffixes"; }
part law5:OwnershipLaw { attribute :>> kernelPath="dev/refactoring/modern-c/models/lean/RuntimeOwnership.lean"; attribute :>> modelPath="dev/refactoring/modern-c/models/quint/runtime_ownership.qnt"; ref part :>> seam=GambitRuntimeComposition::blueprintInterface4; attribute :>> sourceKey="work-premise"; ref part :>> domain=domain2; attribute :>> key="phase-commit"; attribute :>> predicate="closedComplete"; attribute :>> kernel="publicationReadOrdered"; attribute :>> law="Collection close excludes ready/owned/private obligations and acquires same-epoch updates"; attribute :>> proofLimit="Conditional happens-before kernel assumes actual reads-from and no missing producer"; attribute :>> refinement="Prove concrete C23 atomics/locks, phase cut, last borrower and ABI descriptor retirement"; }
part history:GambitAssuranceRouting::ModelNeed { ref part :>> owner=GambitRuntimeAssurance::roots.component; attribute :>> obligationId="OWNERSHIP-history"; attribute :>> kind="interleaving"; attribute :>> subjectPath="dev/refactoring/modern-c/models/quint/runtime_ownership.qnt"; attribute :>> subjectScope="Candidate ownership composition; two contexts, two logical workers, two GC epochs; no full graph/OS simulation"; attribute :>> premise="Complete source/semantic/C23 and QNT-to-Lean refinement remain open; completeCellUpdatesReflectDomainFresh is a conditional domain-to-cell semantic bridge, not extraction"; }
part induction:GambitAssuranceRouting::ModelNeed { ref part :>> owner=GambitRuntimeAssurance::roots.component; attribute :>> obligationId="OWNERSHIP-induction"; attribute :>> kind="induction"; attribute :>> subjectPath="dev/refactoring/modern-c/models/lean/RuntimeOwnership.lean"; attribute :>> subjectScope="Parametric typed root/frame kernels; no extraction from QNT or native semantic simulation"; attribute :>> premise="Complete source/semantic/C23 and QNT-to-Lean refinement remain open; completeCellUpdatesReflectDomainFresh is a conditional domain-to-cell semantic bridge, not extraction"; }
part def SourceRow { attribute key:String; attribute path:String; attribute needle:String; attribute limit:String; }
part source0:SourceRow { attribute :>> key="context-use"; attribute :>> path="vendor/gambit/lib/_mem/collection-round.inc"; attribute :>> needle="context = task->origin->context"; attribute :>> limit="Current candidate still dereferences context from origin; not independent slot storage by renaming"; }
part source1:SourceRow { attribute :>> key="carrier-use"; attribute :>> path="vendor/gambit/lib/_mem/collection-round.inc"; attribute :>> needle="___processor_state ___ps = work->carrier;"; attribute :>> limit="Logical worker split retains native carrier dependencies; physical worker independence is unproved"; }
part source2:SourceRow { attribute :>> key="rc-freeze"; attribute :>> path="vendor/gambit/lib/_mem/rc-roots.inc"; attribute :>> needle="RC root task requires a closed context domain"; attribute :>> limit="Writer closure exists as a source precondition; source-to-model census remains required"; }
part source3:SourceRow { attribute :>> key="frame-copy"; attribute :>> path="vendor/gambit/lib/_mem/continuation-roots.inc"; attribute :>> needle="mark_captured_continuation_locked"; attribute :>> limit="Actual frame traversal/copy/link layout, not pure Lean list identity"; }
part source4:SourceRow { attribute :>> key="vm-retained"; attribute :>> path="vendor/gambit/lib/_mem/root-origins.inc"; attribute :>> needle="resize_requests[i].thunk"; attribute :>> limit="VM-held retained roots are a real source seed for independent custody"; }
part source5:SourceRow { attribute :>> key="root-bridge"; attribute :>> path="evidence/research/smp-retirement-study/delivery-c38e-wait-handoff.json"; attribute :>> needle="sourceFix"; attribute :>> limit="Retained repair evidence constrains behavior; its call order is not this architecture"; }
part source6:SourceRow { attribute :>> key="pvm"; attribute :>> path="dev/refactoring/modern-c/modernization-target.org"; attribute :>> needle="Feeley and Miller"; attribute :>> limit="Existing primary-literature synthesis; proposal is our derived architecture"; }
part source7:SourceRow { attribute :>> key="work-premise"; attribute :>> path="models/gambit/lean/WorkAccounting.lean"; attribute :>> needle="ProducerLifetimeSafe"; attribute :>> limit="Reuse conditional work accounting; it does not discover all private producers"; }
part def ObligationRow { attribute key:String; attribute scope:String; attribute missing:String; }
part obligation0:ObligationRow { attribute :>> key="slot-census"; attribute :>> scope="source"; attribute :>> missing="All actual root locations, writer aliases, generation/ABI and authority transfer"; }
part obligation1:ObligationRow { attribute :>> key="frame-simulation"; attribute :>> scope="semantic"; attribute :>> missing="Frame layout, mutation, dynamic-wind, repeated restore and legal native boundaries"; }
part obligation2:ObligationRow { attribute :>> key="work-simulation"; attribute :>> scope="source"; attribute :>> missing="Every private/copy/Tail/chunk/weak/resize producer and physical cursor handoff"; }
part obligation3:ObligationRow { attribute :>> key="physical-workers"; attribute :>> scope="platform"; attribute :>> missing="Legal native hosts, collective membership, grants and worker/carrier shutdown"; }
part obligation4:ObligationRow { attribute :>> key="c23-refinement"; attribute :>> scope="platform"; attribute :>> missing="Actual atomic objects, reads-from, locks, epochs, lifetime and grace period"; }
part obligation5:ObligationRow { attribute :>> key="qnt-lean-bridge"; attribute :>> scope="formal"; attribute :>> missing="Relation between bounded QNT root-cell epochs and parametric Lean slot/activation semantics"; }
part obligation6:ObligationRow { attribute :>> key="progress-and-cost"; attribute :>> scope="performance"; attribute :>> missing="Fair service assumptions, useful work and per-target deadlines, overhead and peak retained bytes"; }
part obligation7:ObligationRow { attribute :>> key="whole-native"; attribute :>> scope="native"; attribute :>> missing="Same-source original inventories and full consumers; historical repair PASS cannot be imported"; }
part def EdgeRow { attribute fromNode:String; attribute toNode:String; attribute contract:String; }
part edge0:EdgeRow { attribute :>> fromNode="execution"; attribute :>> toNode="roots"; attribute :>> contract="publish/freeze; no writer after cut"; }
part edge1:EdgeRow { attribute :>> fromNode="roots"; attribute :>> toNode="collector"; attribute :>> contract="acquire actual slots and stable layout"; }
part edge2:EdgeRow { attribute :>> fromNode="collector"; attribute :>> toNode="roots"; attribute :>> contract="relocate and discharge tasks"; }
part edge3:EdgeRow { attribute :>> fromNode="roots"; attribute :>> toNode="execution"; attribute :>> contract="reacquire and reload into a legal grant"; }
part edge4:EdgeRow { attribute :>> fromNode="control"; attribute :>> toNode="roots"; attribute :>> contract="captured graph and descriptor consumers"; }
part edge5:EdgeRow { attribute :>> fromNode="control"; attribute :>> toNode="execution"; attribute :>> contract="fresh activation per restore"; }
part edge6:EdgeRow { attribute :>> fromNode="foreign"; attribute :>> toNode="execution"; attribute :>> contract="legal native return origin"; }
part edge7:EdgeRow { attribute :>> fromNode="foreign"; attribute :>> toNode="roots"; attribute :>> contract="registered incoming/return values"; }
part edge8:EdgeRow { attribute :>> fromNode="native"; attribute :>> toNode="execution"; attribute :>> contract="generated GC-capable call/return checkpoints"; }
part def AlternativeRow { attribute key:String; attribute choice:String; attribute benefit:String; attribute cost:String; attribute decision:String; }
part alternative0:AlternativeRow { attribute :>> key="coupled"; attribute :>> choice="PSTATE owns all lifetimes"; attribute :>> benefit="Few explicit descriptors"; attribute :>> cost="Departure can invalidate roots/work/control interpretation"; attribute :>> decision="Rejected as target ownership architecture; no allegation that every current path fails"; }
part alternative1:AlternativeRow { attribute :>> key="ownership-separated"; attribute :>> choice="Distinct logical custodians; replaceable physical realization"; attribute :>> benefit="Carrier/context may leave without losing rooted work or captured control"; attribute :>> cost="Root-domain publication, task accounting, layouts and restoration grants"; attribute :>> decision="Selected architecture research; old authority must actually retire"; }
part alternative2:AlternativeRow { attribute :>> key="worker-pool"; attribute :>> choice="Dedicated independently scheduled GC workers"; attribute :>> benefit="Potential scheduling flexibility and carrier-independent work execution"; attribute :>> cost="Native host enrollment, capacity, root interpretation and extra synchronization"; attribute :>> decision="Optional physical realization; not implied by logical separation or admitted by this model"; }
part law6:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="actual-slots"; attribute :>> key="slot-authority"; attribute :>> predicate="canonicalCoverage"; attribute :>> kernel="completeKeySelectionUpdatesEveryAlias"; attribute :>> law="Actual writable cell identity, not payload equality, defines scan coverage"; attribute :>> proofLimit="Selected keys cover all registered aliases; real addresses, layouts, overlaps and all slot producers still require source mapping"; attribute :>> refinement="Closed root domain supplies complete SlotKey inventory and scanner update addresses"; }
part law7:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="frame-runs"; attribute :>> key="alias-identity"; attribute :>> predicate="updatedActual"; attribute :>> kernel="canonicalAliasesShareUpdatedCell"; attribute :>> law="Two aliases name one storage cell; equal payloads at different keys do not collapse"; attribute :>> proofLimit="Per-cell rewrite is abstract; repeated physical mark_array visits may be safe if actual forwarding idempotence is proved"; attribute :>> refinement="Prove canonical cell coordinates, phase-specific rewrite law and generation lifetime"; }
part law8:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="actual-slots"; attribute :>> key="storage-lifetime"; attribute :>> predicate="storageCustody"; attribute :>> kernel="retainedBackingSufficesAfterLogicalExit"; attribute :>> law="Root storage survives context execution departure and every scanner/alias borrower; domain freshness requires all registered alias cells updated"; attribute :>> proofLimit="Registered implies live is an explicit premise; current source retains origin/context pointers"; attribute :>> refinement="Retain backing storage or redirect every writer; close all last borrowers before free"; }
part law9:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="rc-store"; attribute :>> key="generation-identity"; attribute :>> predicate="storageCustody"; attribute :>> kernel="recycledAddressIsDifferentKey"; attribute :>> law="A reused address is not the same registered slot incarnation"; attribute :>> proofLimit="Distinct key theorem does not prove pin acquisition, counter overflow or native allocator identity"; attribute :>> refinement="Pin stable allocation metadata before address lookup and hold through actual slot last use; storage borrow is not a writer or active-read grant"; }
part source8:SourceRow { attribute :>> key="actual-slots"; attribute :>> path="vendor/gambit/lib/_mem/root-origins.inc"; attribute :>> needle="mark_array (work, context->saved,"; attribute :>> limit="actual r/saved/type_cache/startup/marker slots remain in context backing"; }
part source9:SourceRow { attribute :>> key="frame-runs"; attribute :>> path="vendor/gambit/lib/_mem/continuation-roots.inc"; attribute :>> needle="mark_array (work, &___FP_STK(fp,past-1), past-first);"; attribute :>> limit="descriptor run coordinates produce physical scan spans; span/alias coverage is not complete merely from one witness"; }
part source10:SourceRow { attribute :>> key="rc-store"; attribute :>> path="vendor/gambit/lib/_mem/rc-allocation.inc"; attribute :>> needle="___CAST(___SCMOBJ*,ptr)[index] = value;"; attribute :>> limit="store checks domain/count/closed gate; raw and indirect aliases remain caller-closure obligations"; }
part slotProjection:GambitAssuranceRouting::ModelNeed { ref part :>> owner=GambitRuntimeAssurance::roots.component; attribute :>> obligationId="OWNERSHIP-SLOT-PROJECTION"; attribute :>> kind="interleaving"; attribute :>> subjectPath="dev/refactoring/modern-c/models/quint/root_store_projection.qnt"; attribute :>> subjectScope="Subordinate root-cell alias/generation/writer/scan realization; no complete inventory or native-refinement proof"; attribute :>> premise="Complete concrete root-key domain and QNT/Lean semantic relation remain open"; }
part def SlotFamily { attribute key:String; attribute sourceKey:String; attribute cells:String; attribute issuer:String; attribute custody:String; attribute order:String; attribute gap:String; }
part slotFamily0:SlotFamily { attribute :>> key="registers-saved-cache"; attribute :>> sourceKey="actual-slots"; attribute :>> cells="context->r; context->saved; context->type_cache"; attribute :>> issuer="generated writeback plus context fields; actual spans require configured array lengths"; attribute :>> custody="retain context backing under VM root-store custody; scanner rewrites same cells"; attribute :>> order="gc-task-acquire -> mark_array spans -> root-task-finish -> reload"; attribute :>> gap="all generated register materializers and saved/cache setters; no complete writer inventory claimed"; }
part slotFamily1:SlotFamily { attribute :>> key="startup-entry"; attribute :>> sourceKey="actual-slots"; attribute :>> cells="&context->startup_thunk; &context->entry_marker"; attribute :>> issuer="setup/native entry owns values before collecting bridge; closed ingress required"; attribute :>> custody="root store holds cells beyond logical run grant; marker lifecycle remains native-origin controlled"; attribute :>> order="publish initialized roots -> freeze -> scan -> same-origin/native landing"; attribute :>> gap="startup failures and nested native returns must not clear cells before last consumer"; }
part slotFamily2:SlotFamily { attribute :>> key="ordinary-captured-frames"; attribute :>> sourceKey="frame-runs"; attribute :>> cells="fp, RA, descriptor link, root runs; captured chain"; attribute :>> issuer="FrameSpec decoder and mutable frame/denv writers define root/nonroot/control roles"; attribute :>> custody="preserve actual stack/heap backing and layout/code descriptors until restore/scan borrowers finish"; attribute :>> order="descriptor acquire -> coordinate/run enumeration -> rewrite -> restore with fresh activation"; attribute :>> gap="overlapping runs, RETI, link rewrite, deserialization and multishot mutation remain source-refinement obligations"; }
part slotFamily3:SlotFamily { attribute :>> key="rc-payload-span"; attribute :>> sourceKey="rc-store"; attribute :>> cells="&h->data and (SCMOBJ*)(h+1)[0..root_count)"; attribute :>> issuer="RC registration plus initialized count; store checks same domain and rc_closed_ under gate"; attribute :>> custody="RC allocation generation and registered payload/span retain actual storage"; attribute :>> order="close native writers/borrows -> freeze gate -> mark_rc -> reopen and reload"; attribute :>> gap="unchecked or escaped raw writers; no registry abstraction can infer their absence"; }
part slotFamily4:SlotFamily { attribute :>> key="vm-retained-requests"; attribute :>> sourceKey="vm-retained"; attribute :>> cells="resize.thunk; resize_requests[i].thunk for all slots"; attribute :>> issuer="VM request registration outlives failed/removed origin; root inventory not limited to participants"; attribute :>> custody="VM-root record remains while operation/result unknown or any consumer retains it"; attribute :>> order="VM root cut -> scanner update -> successor execution reads updated slot"; attribute :>> gap="generation reuse, request replacement, completion-last-reader and accepted native outcomes remain obligations"; }
part slotFamily5:SlotFamily { attribute :>> key="phase-services"; attribute :>> sourceKey="context-use"; attribute :>> cells="PREPARE still setup; STRONG roots; WEAK wills; host CLEANUP"; attribute :>> issuer="separate authorities by phase; weak/cleanup work is not a root SlotKey alone"; attribute :>> custody="VM participant/host domains retain phase-specific state in addition to strong slots"; attribute :>> order="phase-specific claim -> work descendants drain -> coordinator advance"; attribute :>> gap="do not flatten still accounting, weak testators and thread-affine cleanup into a universal strong-root array"; }
part law10:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="actual-slots"; attribute :>> key="domain-cell-bridge"; attribute :>> predicate="complete"; attribute :>> kernel="completeCellUpdatesReflectDomainFresh"; attribute :>> law="Every registered alias resolves to an updated cell before domain freshness permits reload"; attribute :>> proofLimit="Conditional complete coverage theorem; no QNT extraction or native cell-enumeration proof"; attribute :>> refinement="Relate parent epoch/root record to keyed physical slots, generation, layout and actual scanner rewrite relation"; }
part source11:SourceRow { attribute :>> key="pin-not-writer"; attribute :>> path="vendor/gambit/lib/_mem/rc-allocation.inc"; attribute :>> needle="Closing writers must never"; attribute :>> limit="close_rc_roots closes writes without waiting borrowed-root storage pins; teardown separately rejects borrows"; }
part source12:SourceRow { attribute :>> key="marker-reload"; attribute :>> path="vendor/gambit/lib/c_intf.c"; attribute :>> needle="proc_or_false = *proc_root; /* reload after allocating the marker */"; attribute :>> limit="actual marker caller reloads the borrowed cell after potential GC; pointer pin does not protect a cached SCMOBJ"; }
part source13:SourceRow { attribute :>> key="bank-consumer"; attribute :>> path="vendor/gambit/lib/c_intf.c"; attribute :>> needle="if (bank) { ___return_rc_root(bank); ___release_rc(bank); }"; attribute :>> limit="bank retained through converter/argument/call/error paths; exit suffix must return borrow then release owner"; }
part source14:SourceRow { attribute :>> key="gvm-writeback"; attribute :>> path="vendor/gambit/include/_gambit/gvm_registers.h.in"; attribute :>> needle="#define ___W_R0 ___PSR0=___r0;"; attribute :>> limit="generated register materialization is a concrete root writer; target profile and generated call coverage still matter"; }
part source15:SourceRow { attribute :>> key="saved-writer"; attribute :>> path="vendor/gambit/lib/os_setup.c"; attribute :>> needle="___ps->context->saved[0] = hi;"; attribute :>> limit="native helper writes saved storage directly; source census must include helper and clear/reload paths, not just FrameSpec generated code"; }
part law11:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="pin-not-writer"; attribute :>> key="borrow-storage"; attribute :>> predicate="borrowLifetime"; attribute :>> kernel="collectionCanPreservePinnedLease"; attribute :>> law="Lifetime borrow pins the actual cell while GC rewrites it; it is not a mutator admission permit"; attribute :>> proofLimit="Park invalidates usable raw cache first; no native pointer safety or arbitrary callback proof"; attribute :>> refinement="Separate scanner lease, native storage pin and active access; GC cannot wait on a borrower needing that GC"; }
part law12:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="marker-reload"; attribute :>> key="borrow-access"; attribute :>> predicate="accessDiscipline"; attribute :>> kernel="storagePinIsNotAccessClosure"; attribute :>> law="A pinned borrower can still be actively accessing the slot; freeze needs access closure independently"; attribute :>> proofLimit="Existential counterexample distinguishes permissions; no actual raw reader enumeration theorem"; attribute :>> refinement="Trace all collecting converters and raw native uses; suspend access and reload before resume"; }
part law13:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_store_projection.qnt"; attribute :>> sourceKey="bank-consumer"; attribute :>> key="borrow-reload"; attribute :>> predicate="rawValid"; attribute :>> kernel="reloadRestoresValueAgreement"; attribute :>> law="After collecting calls the authoritative cell must be reloaded, rather than reusing a cached object value"; attribute :>> proofLimit="Value agreement under pinned live storage; post-GC execution access and acquire are separate premises"; attribute :>> refinement="Generated SFUN plan roots raw SCMOBJ inputs, reloads bank after GC and preserves exceptional release"; }
part source16:SourceRow { attribute :>> key="sfun-generator"; attribute :>> path="vendor/gambit/gsc/_ptree2.scm"; attribute :>> needle="(if sfun? \"BEGIN_SFUN_ARG_SCMOBJ(\" \"BEGIN_CFUN_ARG_SCMOBJ(\")"; attribute :>> limit="Generator distinguishes Scheme-object argument ingress from conversions; complete order/exception/indirect type coverage is not inferred from this selected emitter"; }
part def WriterFamily { attribute key:String; attribute sourceKey:String; attribute authority:String; attribute targetContract:String; attribute observed:String; attribute closure:String; }
part writerFamily0:WriterFamily { attribute :>> key="generated-registers"; attribute :>> sourceKey="gvm-writeback"; attribute :>> authority="Scheme GVM/FrameSpec compiler"; attribute :>> targetContract="Materialize register/return state at every collecting effect; issue exact target-profile root ranges"; attribute :>> observed="Current register macros write context r[]; native helpers also write saved[]"; attribute :>> closure="Complete generated calls plus native helper writers; no complete census receipt"; }
part writerFamily1:WriterFamily { attribute :>> key="native-saved-cells"; attribute :>> sourceKey="saved-writer"; attribute :>> authority="Runtime service contract + generated effect declaration"; attribute :>> targetContract="Register fixed saved-slot ranges; retain backing; close actual helper execution before scan"; attribute :>> observed="os_setup.c directly writes/clears saved[0] around native resource processing"; attribute :>> closure="Every helper, exceptional clear and reentry must map; generated FrameSpec alone cannot certify it"; }
part writerFamily2:WriterFamily { attribute :>> key="rc-bank-membership"; attribute :>> sourceKey="rc-store"; attribute :>> authority="VM root-domain service"; attribute :>> targetContract="Publish initialized payload/root_count under admitted registration; no partial span scan"; attribute :>> observed="alloc_rc_roots initializes cells before publishing count; scan owns closed gate"; attribute :>> closure="Foreign raw address lifetime and direct/indirect writes not closed by setter checks alone"; }
part writerFamily3:WriterFamily { attribute :>> key="marker-conversion"; attribute :>> sourceKey="marker-reload"; attribute :>> authority="Generated SFUN plan + NativeReturnSegment"; attribute :>> targetContract="Borrow pins registered slot; park access before collecting converter; reload actual slot after GC"; attribute :>> observed="Marker allocates vector then reloads *proc_root; bank persists through sfun argument and call paths"; attribute :>> closure="No blocking GC wait on a borrow held by that same conversion; exceptions must return acquired borrow once"; }
part writerFamily4:WriterFamily { attribute :>> key="rc-teardown"; attribute :>> sourceKey="pin-not-writer"; attribute :>> authority="VM resource/retirement authority"; attribute :>> targetContract="Close new borrows and writers; finish GC independently; await borrows for storage destruction only"; attribute :>> observed="prepare_rc_cleanup and cleanup_rc reject nonzero rc_root_borrows_"; attribute :>> closure="Source shows rejection/fatal behavior, not an implemented asynchronous retirement or transferable owner"; }
part writerFamily5:WriterFamily { attribute :>> key="retained-startup-request"; attribute :>> sourceKey="vm-retained"; attribute :>> authority="VM request/context setup authority"; attribute :>> targetContract="Retain VM startup/resize roots past failed or removed execution origin; generation-bound handoff"; attribute :>> observed="VM scans resize request thunk slots; ___run uses rooted startup thunk then clears marker/startup on return"; attribute :>> closure="Full request writers, all cleanup exceptions and old descriptor lifetime remain open"; }
part source17:SourceRow { attribute :>> key="frame-role"; attribute :>> path="vendor/gambit/include/_gambit/module_generation.h.in"; attribute :>> needle="cursor.excluded_slot = frame->link+1;"; attribute :>> limit="Structural link is deliberately excluded from ordinary root cursor; its traversal must remain a distinct consumer"; }
part source18:SourceRow { attribute :>> key="cursor-borrow"; attribute :>> path="vendor/gambit/include/_gambit/module_generation.h.in"; attribute :>> needle="It never outlives the descriptor's"; attribute :>> limit="Current cursor borrows descriptor/module, is nonallocating and does not cross a safepoint; resumable compilation is a new obligation"; }
part source19:SourceRow { attribute :>> key="descriptor-decode"; attribute :>> path="vendor/gambit/include/_gambit/module_generation.h.in"; attribute :>> needle="frame.fs = internal ? ___RETI_CFS_TO_FS(frame.stored_fs) : frame.stored_fs;"; attribute :>> limit="IFD/OFD and internal RETI coordinates must decode under exact ABI/module lifetime; no portable integer cast substitutes"; }
part law14:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_enumeration.qnt"; attribute :>> sourceKey="actual-slots"; attribute :>> key="program-coverage"; attribute :>> predicate="outputCoverage"; attribute :>> kernel="completeProgramCoversDeclaredFamilies"; attribute :>> law="A complete root program composes fixed/frame/dynamic families and separate control traversal"; attribute :>> proofLimit="Declared-family completeness is assumed, not discovered; RootOp semantics has no physical ABI parser"; attribute :>> refinement="Prove every actual root belongs to declared families then each program opcode covers its physical slots"; }
part law15:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_enumeration.qnt"; attribute :>> sourceKey="frame-role"; attribute :>> key="control-exclusion"; attribute :>> predicate="roleSafe"; attribute :>> kernel="ordinaryExclusionRequiresControlCoverage"; attribute :>> law="Ordinary frame link exclusion is valid only if a separate control consumer covers live structural links"; attribute :>> proofLimit="Handled control relation remains a premise; ordinary marking does not imply valid continuation link mutation"; attribute :>> refinement="Compose RETI/OFD decode, frame coordinate map, captured-chain traversal and control-role update"; }
part law16:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_enumeration.qnt"; attribute :>> sourceKey="rc-store"; attribute :>> key="program-currentness"; attribute :>> predicate="currentCredential"; attribute :>> kernel="layoutEqualityIsNotDynamicMembership"; attribute :>> law="Unchanged static layout does not certify unchanged dynamic RC membership"; attribute :>> proofLimit="Simple counterexample is not a native versioning or memory-order implementation"; attribute :>> refinement="Bind private output to code/ABI and frozen dynamic membership epoch; invalidate after any relevant change"; }
part law17:OwnershipLaw { attribute :>> kernelPath="dev/refactoring/modern-c/models/lean/RuntimeOwnership.lean"; ref part :>> domain=domain1; ref part :>> seam=GambitRuntimeComposition::blueprintInterface1; attribute :>> modelPath="dev/refactoring/modern-c/models/quint/root_enumeration.qnt"; attribute :>> sourceKey="cursor-borrow"; attribute :>> key="physical-program-refinement"; attribute :>> predicate="immutableCut"; attribute :>> kernel="declaredFamiliesNeedConcreteCoverage"; attribute :>> law="Program publication depends on actual-to-declared inventory and declared-to-emitted coverage"; attribute :>> proofLimit="No full source simulation, weak-memory proof or complete writer closure"; attribute :>> refinement="Retain descriptor plus backing domains; close writers and prohibit unsupported cursor suspension before publish"; }
part def EnumerationOp { attribute key:String; attribute sourceKey:String; attribute authority:String; attribute operand:String; attribute rights:String; attribute reuse:String; attribute invalidation:String; }
part enumerationOp0:EnumerationOp { attribute :>> key="fixed-range"; attribute :>> sourceKey="gvm-writeback"; attribute :>> authority="Scheme semantic plan + runtime fixed-service declaration"; attribute :>> operand="target-profile register/saved/cache/startup/entry slot spans"; attribute :>> rights="enumerate actual rooted range; no target-dependent type reinterpretation"; attribute :>> reuse="static recipe reusable with exact layout/ABI; fresh backing and grant each invocation"; attribute :>> invalidation="Layout or effect/writer coverage change; runtime snapshot still required"; }
part enumerationOp1:EnumerationOp { attribute :>> key="frame-roots"; attribute :>> sourceKey="descriptor-decode"; attribute :>> authority="FrameSpec generator + module/layout authority"; attribute :>> operand="IFD/OFD, RETI mode, GC bitmap runs and frame coordinates"; attribute :>> rights="ordinary roots excluding structural link; descriptor lease held"; attribute :>> reuse="reuse decoder/recipe; do not cache a borrowed cursor across safepoints"; attribute :>> invalidation="Descriptor/code/ABI or frame graph change; malformed/truncated layout refused"; }
part enumerationOp2:EnumerationOp { attribute :>> key="dynamic-domain"; attribute :>> sourceKey="rc-store"; attribute :>> authority="VM root-domain service"; attribute :>> operand="closed RC chain, initialized root_count, retained VM slots and generation"; attribute :>> rights="enumerate current admitted slots; ownership survives logical origin exit"; attribute :>> reuse="reuse service code; bind each membership cut independently"; attribute :>> invalidation="Registration/removal/membership generation, active writer or unknown store invalidates cut"; }
part enumerationOp3:EnumerationOp { attribute :>> key="control-chain"; attribute :>> sourceKey="frame-role"; attribute :>> authority="Scheme continuation semantics + native control adapter"; attribute :>> operand="structural link, stack break, captured chain and return interpretation"; attribute :>> rights="separate traversal/repair; not an ordinary value span"; attribute :>> reuse="reuse traversal code with retained layout/code and fresh graph origin"; attribute :>> invalidation="Control graph/link/return descriptor lifetime or unsupported reentry"; }
part enumerationHistory:GambitAssuranceRouting::ModelNeed { ref part :>> owner=GambitRuntimeAssurance::roots.component; attribute :>> obligationId="OWNERSHIP-ENUMERATION"; attribute :>> kind="interleaving"; attribute :>> subjectPath="dev/refactoring/modern-c/models/quint/root_enumeration.qnt"; attribute :>> subjectScope="Subordinate enumeration program: role coverage, private prefix, ABI/module lease and dynamic cut; source and semantic refinement open"; attribute :>> premise="Actual inventory completeness and root/control ABI relation remain explicit unproved source premises"; }
part def RootEnumerationProgram { ref part semantic:GambitRuntimeComposition::BlueprintModule; ref part roots:GambitRuntimeComposition::BlueprintModule; ref part collector:GambitRuntimeComposition::BlueprintModule; ref part history:GambitAssuranceRouting::ModelNeed; }
part program:RootEnumerationProgram { ref part :>> semantic=GambitRuntimeComposition::blueprintModule0; ref part :>> roots=GambitRuntimeComposition::blueprintModule3; ref part :>> collector=GambitRuntimeComposition::blueprintModule4; ref part :>> history=enumerationHistory; }
part source20:SourceRow { attribute :>> key="bitmap-build"; attribute :>> path="vendor/gambit/gsc/_t-c-3.scm"; attribute :>> needle="(define (targ-build-gc-map slots live?)"; attribute :>> limit="Semantic zero-based vars order and live predicate produce nonnegative bitmap; actual liveness and aliases remain unproved"; }
part source21:SourceRow { attribute :>> key="bitmap-emit"; attribute :>> path="vendor/gambit/gsc/_t-c-1.scm"; attribute :>> needle="(targ-frame-spec-chunks info)"; attribute :>> limit="Out-of-line frame emission uses validated spec chunks, converted U32 and grouped two per source macro"; }
part source22:SourceRow { attribute :>> key="reti-vars"; attribute :>> path="vendor/gambit/gsc/_t-c-2.scm"; attribute :>> needle="(generate cfs vars gc-map)"; attribute :>> limit="Internal vars append saved registers and return word; ordering/alignment must refine physical frame fields"; }
part source23:SourceRow { attribute :>> key="bitmap-pack"; attribute :>> path="vendor/gambit/include/_gambit/module_generation.h.in"; attribute :>> needle="#define ___GCMAP2(a,b),___CAST"; attribute :>> limit="32-bit target emits words separately; 64-bit target packs unsigned low/high halves; C promotions and object bounds not proved by Nat algebra"; }
part source24:SourceRow { attribute :>> key="frame-spec-bounds"; attribute :>> path="vendor/gambit/gsc/_t-c-3.scm"; attribute :>> needle="(vector 'frame-spec kind fs actual-fs link gc-map out-of-line?)"; attribute :>> limit="Stored vs actual fs and link/map bounds validated; a Scheme vector is not intrinsically immutable or a module-lifetime proof"; }
part law18:OwnershipLaw { ref part :>> domain=domain1; ref part :>> seam=GambitRuntimeComposition::blueprintInterface2; attribute :>> kernelPath="dev/refactoring/modern-c/models/lean/FrameBitmapComposition.lean"; attribute :>> modelPath="dev/refactoring/modern-c/models/quint/frame_roots.qnt"; attribute :>> sourceKey="bitmap-pack"; attribute :>> key="bitmap-native-word"; attribute :>> predicate="packingLaw"; attribute :>> kernel="wordBitCorrespondence"; attribute :>> law="Each target-word bit corresponds to its mathematical source bitmap index"; attribute :>> proofLimit="Natural number proof plus pair32Packing; no C cast/shift UB or full emitter execution proof"; attribute :>> refinement="Compose little-endian source chunks, native word representation and one-based slot index"; }
part law19:OwnershipLaw { ref part :>> domain=domain1; ref part :>> seam=GambitRuntimeComposition::blueprintInterface2; attribute :>> kernelPath="dev/refactoring/modern-c/models/lean/FrameBitmapComposition.lean"; attribute :>> modelPath="dev/refactoring/modern-c/models/quint/frame_roots.qnt"; attribute :>> sourceKey="frame-role"; attribute :>> key="bitmap-control-partition"; attribute :>> predicate="controlPartition"; attribute :>> kernel="ordinaryAndControlPartition"; attribute :>> law="Live bitmap slots split into ordinary and structural control roles"; attribute :>> proofLimit="Bitmap root status alone does not prove valid return/link traversal or exact cursor-run grouping"; attribute :>> refinement="Bind bitmap index ordering, excluded link+1 and separate physical control consumer"; }
part law20:OwnershipLaw { ref part :>> domain=domain1; ref part :>> seam=GambitRuntimeComposition::blueprintInterface2; attribute :>> kernelPath="dev/refactoring/modern-c/models/lean/FrameBitmapComposition.lean"; attribute :>> modelPath="dev/refactoring/modern-c/models/quint/frame_contract.qnt"; attribute :>> sourceKey="reti-vars"; attribute :>> key="reti-layout-formula"; attribute :>> predicate="safe"; attribute :>> kernel="retiFiveRegisterFormula"; attribute :>> law="Stored internal frame size expands to the saved register/return region under matching target constants"; attribute :>> proofLimit="Five registers/alignment4/reserve3 are explicit formula assumptions, not arbitrary configured runtime admission"; attribute :>> refinement="Bind actual target register count and alignment plus all saved-slot emitters and consumers"; }
part law21:OwnershipLaw { ref part :>> domain=domain1; ref part :>> seam=GambitRuntimeComposition::blueprintInterface2; attribute :>> kernelPath="dev/refactoring/modern-c/models/lean/FrameBitmapComposition.lean"; attribute :>> modelPath="dev/refactoring/modern-c/models/quint/frame_roots.qnt"; attribute :>> sourceKey="frame-runs"; attribute :>> key="bitmap-physical-span"; attribute :>> predicate="safe"; attribute :>> kernel="physicalRunCoverage"; attribute :>> law="Reversed physical frame coordinates are covered by ascending mark_array span"; attribute :>> proofLimit="Interval arithmetic reuses FutureCoordinates; no C provenance, allocation bounds or complete run simulation"; attribute :>> refinement="Prove every live ordinary slot belongs to emitted disjoint runs then map those runs to actual addresses"; }
part def BitmapStage { attribute key:String; attribute sourceKey:String; attribute operand:String; attribute result:String; attribute obligation:String; }
part bitmapStage0:BitmapStage { attribute :>> key="semantic-map"; attribute :>> sourceKey="bitmap-build"; attribute :>> operand="ordered vars plus live predicate"; attribute :>> result="zero-based bitmap"; attribute :>> obligation="Source liveness/capture and vars physical ordering; includes root/return-role distinction"; }
part bitmapStage1:BitmapStage { attribute :>> key="frame-validation"; attribute :>> sourceKey="frame-spec-bounds"; attribute :>> operand="kind/stored/link/map"; attribute :>> result="actual fs plus inline/outline choice"; attribute :>> obligation="Plan immutability and all writers; validation bounds are not a sealed-vector theorem"; }
part bitmapStage2:BitmapStage { attribute :>> key="emitted-words"; attribute :>> sourceKey="bitmap-emit"; attribute :>> operand="nonnegative bitmap split into 32-bit chunks"; attribute :>> result="GCMAP0/1/2 source groups with exact last group"; attribute :>> obligation="C literal widths, odd final chunk, target width and emitted OFD table bounds"; }
part bitmapStage3:BitmapStage { attribute :>> key="target-pack-query"; attribute :>> sourceKey="bitmap-pack"; attribute :>> operand="32-bit chunks in native words"; attribute :>> result="one-based slot test from first word plus tail excluding first"; attribute :>> obligation="Nat wordBitCorrespondence/pair32Packing; native shift/cast and memory lifetime separate"; }
part bitmapStage4:BitmapStage { attribute :>> key="frame-control"; attribute :>> sourceKey="reti-vars"; attribute :>> operand="RETI stored fs and saved/return vars"; attribute :>> result="actual frame, bitmap and excluded link coordinate"; attribute :>> obligation="Configuration identity, saved slots, RETI actual RA and normal frame coordinate proof"; }
part bitmapStage5:BitmapStage { attribute :>> key="physical-runs"; attribute :>> sourceKey="frame-runs"; attribute :>> operand="ordinary cursor first/past and frame base"; attribute :>> result="ascending mark_array range plus separate link handling"; attribute :>> obligation="Complete run simulation, pointer provenance, module leases and captured-chain mutation"; }
part law22:OwnershipLaw { ref part :>> domain=domain1; ref part :>> seam=GambitRuntimeComposition::blueprintInterface2; attribute :>> kernelPath="dev/refactoring/modern-c/models/lean/FrameCursorRefinement.lean"; attribute :>> modelPath="dev/refactoring/modern-c/models/quint/frame_roots.qnt"; attribute :>> sourceKey="frame-runs"; attribute :>> key="cursor-run-conservation"; attribute :>> predicate="runCoverage"; attribute :>> kernel="actualStepPreserves"; attribute :>> law="Conditional exact extracted next-step preservation of the abstract prefix/run invariant"; attribute :>> proofLimit="Needs ProjectionDomain, actual pre-state coverage/current invariants and current plus advanced word-guard fidelity; not full QNT invariant induction"; attribute :>> refinement="Word-state invariant and C23 native refinement remain separate source obligations"; }
part law23:OwnershipLaw { ref part :>> domain=domain1; ref part :>> seam=GambitRuntimeComposition::blueprintInterface2; attribute :>> kernelPath="dev/refactoring/modern-c/models/lean/FrameCursorRefinement.lean"; attribute :>> modelPath="dev/refactoring/modern-c/models/quint/frame_roots.qnt"; attribute :>> sourceKey="frame-role"; attribute :>> key="cursor-run-boundary"; attribute :>> predicate="runCoverage"; attribute :>> kernel="actualStepSimulation"; attribute :>> law="Actual typed-IR runStep branches refine six Moves, with DONE stuttering erased"; attribute :>> proofLimit="Conditional on ProjectionDomain, declared mode/layout and both word observations; parser/emitter and nonnegative-power interpretation remain trusted"; attribute :>> refinement="Word-state invariant and C23 native refinement remain separate source obligations"; }
part law24:OwnershipLaw { ref part :>> domain=domain1; ref part :>> seam=GambitRuntimeComposition::blueprintInterface2; attribute :>> kernelPath="dev/refactoring/modern-c/models/lean/FrameCursorRefinement.lean"; attribute :>> modelPath="dev/refactoring/modern-c/models/quint/frame_roots.qnt"; attribute :>> sourceKey="cursor-borrow"; attribute :>> key="cursor-progress"; attribute :>> predicate="runSafe"; attribute :>> kernel="stepIdentity"; attribute :>> law="Extracted next step preserves fs, bitmap, excluded role and legal mode range"; attribute :>> proofLimit="Universal structural property for legal pre-state mode; does not prove word reload arithmetic or whole GC progress"; attribute :>> refinement="Word-state invariant and C23 native refinement remain separate source obligations"; }
part law25:OwnershipLaw { ref part :>> domain=domain1; ref part :>> seam=GambitRuntimeComposition::blueprintInterface2; attribute :>> kernelPath="dev/refactoring/modern-c/models/lean/FrameCursorRefinement.lean"; attribute :>> modelPath="dev/refactoring/modern-c/models/quint/frame_roots.qnt"; attribute :>> sourceKey="actual-slots"; attribute :>> key="cursor-pending-delivery"; attribute :>> predicate="runCoverage"; attribute :>> kernel="coverageReflects"; attribute :>> law="Actual extracted coverage and current-slot/end-position guards imply the Lean Safe invariant"; attribute :>> proofLimit="Uses Int-to-Nat and extensional slot membership; does not infer arbitrary C pointers or complete source liveness"; attribute :>> refinement="Word-state invariant and C23 native refinement remain separate source obligations"; }
part def CursorStep { attribute key:String; attribute condition:String; attribute update:String; attribute projection:String; attribute obligation:String; }
part cursorStep0:CursorStep { attribute :>> key="skip"; attribute :>> condition="slot<=fs and zero-bit or excluded link"; attribute :>> update="advance slot; shift or load next bitmap word"; attribute :>> projection="SKIP microstep, delivered prefix unchanged"; attribute :>> obligation="Skipped position must be ineligible; native table remains pinned"; }
part cursorStep1:CursorStep { attribute :>> key="start-run"; attribute :>> condition="slot<=fs and live non-link bit"; attribute :>> update="save first=slot; enter do/while body"; attribute :>> projection="COLLECT microstep starts nonempty interval"; attribute :>> obligation="No raw address interpretation or link-role change"; }
part cursorStep2:CursorStep { attribute :>> key="advance-run"; attribute :>> condition="run body then remaining-slot/live/non-link test"; attribute :>> update="advance exactly once; reload only if new slot within fs and first in word"; attribute :>> projection="COLLECT continues or PENDING past=slot"; attribute :>> obligation="Need unsigned-word correspondence and no final-word overread"; }
part cursorStep3:CursorStep { attribute :>> key="return-range"; attribute :>> condition="first<past and all interval slots ordinary-live"; attribute :>> update="caller receives first/past; cursor already points at stop boundary"; attribute :>> projection="PENDING retains private returned range"; attribute :>> obligation="Returning does not imply mark_array called or descendants drained"; }
part cursorStep4:CursorStep { attribute :>> key="deliver-resume"; attribute :>> condition="caller mark_frame invokes mark_array for this exact span"; attribute :>> update="acknowledge delivery then next cursor call or retain on interrupted consumer"; attribute :>> projection="PENDING -> SKIP; END only with no uncovered run"; attribute :>> obligation="Full scan/initialization work and phase finish still require separate work closure"; }
part edge9:EdgeRow { attribute :>> fromNode="control"; attribute :>> toNode="ordinary cursor"; attribute :>> contract="eligible bitmap roles exclude structural link"; }
part edge10:EdgeRow { attribute :>> fromNode="ordinary cursor"; attribute :>> toNode="pending returned range"; attribute :>> contract="first/past plus cursor progress; descriptor borrowed"; }
part edge11:EdgeRow { attribute :>> fromNode="pending returned range"; attribute :>> toNode="collector"; attribute :>> contract="caller delivers exact mark_array span"; }
part edge12:EdgeRow { attribute :>> fromNode="collector"; attribute :>> toNode="roots"; attribute :>> contract="root visit does not discharge scan descendants or frame/code last users"; }

part def MathematicalScope { attribute kind:String; attribute key:String; attribute lawKey:String; attribute kernelPath:String; attribute kernel:String; attribute claim:String; attribute limit:String; }
part law26:OwnershipLaw { ref part :>> domain=domain1; ref part :>> seam=GambitRuntimeComposition::blueprintInterface2; attribute :>> key="cursor-step-induction"; attribute :>> predicate="runSafe"; attribute :>> kernel="preserves"; attribute :>> law="Every enabled abstract microstep preserves prefix and private-run custody"; attribute :>> proofLimit="Complete abstract invariant induction; root eligibility supplied as an immutable predicate"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope0:MathematicalScope { attribute :>> kind="abstract-total"; attribute :>> key="cursor-step-induction"; attribute :>> lawKey="cursor-step-induction"; attribute :>> kernelPath="dev/refactoring/modern-c/models/lean/FrameCursorClosure.lean"; attribute :>> kernel="preserves"; attribute :>> claim="Every enabled abstract microstep preserves prefix and private-run custody"; attribute :>> limit="Complete abstract invariant induction; root eligibility supplied as an immutable predicate"; }
part law27:OwnershipLaw { ref part :>> domain=domain1; ref part :>> seam=GambitRuntimeComposition::blueprintInterface2; attribute :>> key="cursor-exact-completion"; attribute :>> predicate="runCoverage"; attribute :>> kernel="completedExactly"; attribute :>> law="Any completed path delivers exactly all eligible one-based slots within fs"; attribute :>> proofLimit="Universal abstract path theorem; delivery is an abstract acknowledgment, not descendant work completion"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope1:MathematicalScope { attribute :>> kind="abstract-total"; attribute :>> key="cursor-exact-completion"; attribute :>> lawKey="cursor-exact-completion"; attribute :>> kernelPath="dev/refactoring/modern-c/models/lean/FrameCursorClosure.lean"; attribute :>> kernel="completedExactly"; attribute :>> claim="Any completed path delivers exactly all eligible one-based slots within fs"; attribute :>> limit="Universal abstract path theorem; delivery is an abstract acknowledgment, not descendant work completion"; }
part law28:OwnershipLaw { ref part :>> domain=domain1; ref part :>> seam=GambitRuntimeComposition::blueprintInterface2; attribute :>> key="cursor-fresh-delivery"; attribute :>> predicate="runCoverage"; attribute :>> kernel="pendingRangeIsFresh"; attribute :>> law="Every pending interval is fresh relative to previously delivered positions"; attribute :>> proofLimit="Prefix invariant excludes duplicate delivery; raw object values and aliases are not used as slot identity"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope2:MathematicalScope { attribute :>> kind="abstract-total"; attribute :>> key="cursor-fresh-delivery"; attribute :>> lawKey="cursor-fresh-delivery"; attribute :>> kernelPath="dev/refactoring/modern-c/models/lean/FrameCursorClosure.lean"; attribute :>> kernel="pendingRangeIsFresh"; attribute :>> claim="Every pending interval is fresh relative to previously delivered positions"; attribute :>> limit="Prefix invariant excludes duplicate delivery; raw object values and aliases are not used as slot identity"; }
part law29:OwnershipLaw { ref part :>> domain=domain1; ref part :>> seam=GambitRuntimeComposition::blueprintInterface2; attribute :>> key="cursor-finite-completion"; attribute :>> predicate="runSafe"; attribute :>> kernel="finiteClosure"; attribute :>> law="Every safe abstract state admits a finite path to DONE"; attribute :>> proofLimit="Strict natural rank decreases on every enabled transition; scheduler service remains an external condition"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope3:MathematicalScope { attribute :>> kind="abstract-total"; attribute :>> key="cursor-finite-completion"; attribute :>> lawKey="cursor-finite-completion"; attribute :>> kernelPath="dev/refactoring/modern-c/models/lean/FrameCursorClosure.lean"; attribute :>> kernel="finiteClosure"; attribute :>> claim="Every safe abstract state admits a finite path to DONE"; attribute :>> limit="Strict natural rank decreases on every enabled transition; scheduler service remains an external condition"; }
part law30:OwnershipLaw { ref part :>> domain=domain1; ref part :>> seam=GambitRuntimeComposition::blueprintInterface2; attribute :>> key="cursor-total-correctness"; attribute :>> predicate="runCoverage"; attribute :>> kernel="totalCorrect"; attribute :>> law="For arbitrary finite fs and eligibility there exists exact completed delivery"; attribute :>> proofLimit="Combines initialization, step preservation and finite completion; no C or parsed QNT extraction"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope4:MathematicalScope { attribute :>> kind="abstract-total"; attribute :>> key="cursor-total-correctness"; attribute :>> lawKey="cursor-total-correctness"; attribute :>> kernelPath="dev/refactoring/modern-c/models/lean/FrameCursorClosure.lean"; attribute :>> kernel="totalCorrect"; attribute :>> claim="For arbitrary finite fs and eligibility there exists exact completed delivery"; attribute :>> limit="Combines initialization, step preservation and finite completion; no C or parsed QNT extraction"; }
part law31:OwnershipLaw { ref part :>> domain=domain1; ref part :>> seam=GambitRuntimeComposition::blueprintInterface2; attribute :>> key="cursor-microstep-budget"; attribute :>> predicate="runSafe"; attribute :>> kernel="initialBudget"; attribute :>> law="Any executed abstract path from initial has at most 3*fs+2 microsteps"; attribute :>> proofLimit="Logical transition budget only; no native instruction, latency or total GC bound"; attribute :>> refinement="Prove guard eligibility, native advance and caller acknowledgment simulation; retain sourceRefinementNeed"; attribute :>> sourceKey="frame-runs"; attribute :>> modelPath="dev/refactoring/modern-c/models/quint/frame_roots.qnt"; attribute :>> kernelPath="dev/refactoring/modern-c/models/lean/FrameCursorClosure.lean"; }
part mathScope5:MathematicalScope { attribute :>> kind="abstract-total"; attribute :>> key="cursor-microstep-budget"; attribute :>> lawKey="cursor-microstep-budget"; attribute :>> kernelPath="dev/refactoring/modern-c/models/lean/FrameCursorClosure.lean"; attribute :>> kernel="initialBudget"; attribute :>> claim="Any executed abstract path from initial has at most 3*fs+2 microsteps"; attribute :>> limit="Logical transition budget only; no native instruction, latency or total GC bound"; }
part edge13:EdgeRow { attribute :>> fromNode="ordinary cursor"; attribute :>> toNode="abstract step induction"; attribute :>> contract="guard fidelity premise remains open"; }
part edge14:EdgeRow { attribute :>> fromNode="abstract step induction"; attribute :>> toNode="exact finite delivery"; attribute :>> contract="Lean preservation, freshness and rank"; }
part edge15:EdgeRow { attribute :>> fromNode="exact finite delivery"; attribute :>> toNode="native cursor admission"; attribute :>> contract="requires source guards, pointers, word representation and caller lease"; }

part mathScope6:MathematicalScope { attribute :>> kind="conditional-refinement"; attribute :>> key="cursor-run-conservation"; attribute :>> lawKey="cursor-run-conservation"; attribute :>> kernelPath="dev/refactoring/modern-c/models/lean/FrameCursorRefinement.lean"; attribute :>> kernel="actualStepPreserves"; attribute :>> claim="Conditional exact extracted next-step preservation of the abstract prefix/run invariant"; attribute :>> limit="Needs ProjectionDomain, actual pre-state coverage/current invariants and current plus advanced word-guard fidelity; not full QNT invariant induction"; }

part mathScope7:MathematicalScope { attribute :>> kind="conditional-refinement"; attribute :>> key="cursor-run-boundary"; attribute :>> lawKey="cursor-run-boundary"; attribute :>> kernelPath="dev/refactoring/modern-c/models/lean/FrameCursorRefinement.lean"; attribute :>> kernel="actualStepSimulation"; attribute :>> claim="Actual typed-IR runStep branches refine six Moves, with DONE stuttering erased"; attribute :>> limit="Conditional on ProjectionDomain, declared mode/layout and both word observations; parser/emitter and nonnegative-power interpretation remain trusted"; }

part mathScope8:MathematicalScope { attribute :>> kind="extracted-structural"; attribute :>> key="cursor-progress"; attribute :>> lawKey="cursor-progress"; attribute :>> kernelPath="dev/refactoring/modern-c/models/lean/FrameCursorRefinement.lean"; attribute :>> kernel="stepIdentity"; attribute :>> claim="Extracted next step preserves fs, bitmap, excluded role and legal mode range"; attribute :>> limit="Universal structural property for legal pre-state mode; does not prove word reload arithmetic or whole GC progress"; }

part mathScope9:MathematicalScope { attribute :>> kind="conditional-refinement"; attribute :>> key="cursor-pending-delivery"; attribute :>> lawKey="cursor-pending-delivery"; attribute :>> kernelPath="dev/refactoring/modern-c/models/lean/FrameCursorRefinement.lean"; attribute :>> kernel="coverageReflects"; attribute :>> claim="Actual extracted coverage and current-slot/end-position guards imply the Lean Safe invariant"; attribute :>> limit="Uses Int-to-Nat and extensional slot membership; does not infer arbitrary C pointers or complete source liveness"; }

part edge16:EdgeRow { attribute :>> fromNode="QNT typed cursor slice"; attribute :>> toNode="extracted Lean Int state"; attribute :>> contract="checked binding IDs and expression projection; trusted emitter"; }

part edge17:EdgeRow { attribute :>> fromNode="extracted Lean Int state"; attribute :>> toNode="abstract step induction"; attribute :>> contract="coverage reflection and conditional step simulation"; }

part edge18:EdgeRow { attribute :>> fromNode="word state fidelity"; attribute :>> toNode="extracted Lean Int state"; attribute :>> contract="proved supported-width word invariant; native table qualification remains open"; }

part law32:OwnershipLaw { ref part :>> domain=domain1; ref part :>> seam=GambitRuntimeComposition::blueprintInterface2; attribute :>> key="cursor-source-total"; attribute :>> predicate="runCoverage"; attribute :>> kernel="sourceTotalCorrectAll"; attribute :>> law="Actual extracted startRun/runStep family reaches DONE within 3*fs+2 steps with exact delivered membership over all integer slots"; attribute :>> proofLimit="Width4/32/64 and natural frame/bitmap/exclusion parameters; relative to trusted typed-IR projection and built-ins; no whole GC or native C qualification"; attribute :>> refinement="Native C must supply actual valid table/backing, integer bounds, root roles and caller/work simulation"; attribute :>> sourceKey="frame-runs"; attribute :>> modelPath="dev/refactoring/modern-c/models/quint/frame_roots.qnt"; attribute :>> kernelPath="dev/refactoring/modern-c/models/lean/FrameCursorWords.lean"; }
part mathScope10:MathematicalScope { attribute :>> kind="extracted-total"; attribute :>> key="cursor-source-total"; attribute :>> lawKey="cursor-source-total"; attribute :>> kernelPath="dev/refactoring/modern-c/models/lean/FrameCursorWords.lean"; attribute :>> kernel="sourceTotalCorrectAll"; attribute :>> claim="Actual extracted startRun/runStep family reaches DONE within 3*fs+2 steps with exact delivered membership over all integer slots"; attribute :>> limit="Width4/32/64 and natural frame/bitmap/exclusion parameters; relative to trusted typed-IR projection and built-ins; no whole GC or native C qualification"; }
part edge19:EdgeRow { attribute :>> fromNode="extracted startRun"; attribute :>> toNode="word state fidelity"; attribute :>> contract="entryShape and preserved shift/refill coordinates"; }
part edge20:EdgeRow { attribute :>> fromNode="word state fidelity"; attribute :>> toNode="supported cursor family"; attribute :>> contract="sourceTotalCorrectAll; exact Int membership and bounded completion"; }

part law33:OwnershipLaw { ref part :>> domain=domain1; ref part :>> seam=GambitRuntimeComposition::blueprintInterface2; attribute :>> key="native-word-arithmetic"; attribute :>> predicate="nativeWordContract"; attribute :>> kernel="boundaryMask"; attribute :>> law="Finite unsigned word shifts and low-bit/boundary masks agree with arithmetic windows for native widths 32/64"; attribute :>> proofLimit="C signed-to-unsigned type interpretation and effective configured widths remain premises; no C AST extraction"; attribute :>> refinement="Qualify generated descriptor view, native type ABI, lifetime and caller/work composition separately"; attribute :>> sourceKey="cursor-native"; attribute :>> modelPath="dev/refactoring/modern-c/models/quint/frame_contract.qnt"; attribute :>> kernelPath="dev/refactoring/modern-c/models/lean/FrameCursorNativeBounds.lean"; }
part mathScope11:MathematicalScope { attribute :>> kind="c-facing-arithmetic"; attribute :>> key="native-word-arithmetic"; attribute :>> lawKey="native-word-arithmetic"; attribute :>> kernelPath="dev/refactoring/modern-c/models/lean/FrameCursorNativeBounds.lean"; attribute :>> kernel="boundaryMask"; attribute :>> claim="Finite unsigned word shifts and low-bit/boundary masks agree with arithmetic windows for native widths 32/64"; attribute :>> limit="C signed-to-unsigned type interpretation and effective configured widths remain premises; no C AST extraction"; }
part law34:OwnershipLaw { ref part :>> domain=domain1; ref part :>> seam=GambitRuntimeComposition::blueprintInterface2; attribute :>> key="native-tail-view"; attribute :>> predicate="nativeTailContract"; attribute :>> kernel="tailReadBound"; attribute :>> law="Every enabled tail load reads below its logical descriptor tail length and postincrement remains at most one-past"; attribute :>> proofLimit="A containing OFD allocation bound does not imply the current descriptor view bound or its lifetime"; attribute :>> refinement="Qualify generated descriptor view, native type ABI, lifetime and caller/work composition separately"; attribute :>> sourceKey="cursor-native"; attribute :>> modelPath="dev/refactoring/modern-c/models/quint/frame_contract.qnt"; attribute :>> kernelPath="dev/refactoring/modern-c/models/lean/FrameCursorNativeBounds.lean"; }
part mathScope12:MathematicalScope { attribute :>> kind="c-facing-arithmetic"; attribute :>> key="native-tail-view"; attribute :>> lawKey="native-tail-view"; attribute :>> kernelPath="dev/refactoring/modern-c/models/lean/FrameCursorNativeBounds.lean"; attribute :>> kernel="tailReadBound"; attribute :>> claim="Every enabled tail load reads below its logical descriptor tail length and postincrement remains at most one-past"; attribute :>> limit="A containing OFD allocation bound does not imply the current descriptor view bound or its lifetime"; }
part law35:OwnershipLaw { ref part :>> domain=domain1; ref part :>> seam=GambitRuntimeComposition::blueprintInterface2; attribute :>> key="native-run-span"; attribute :>> predicate="nativeSpanContract"; attribute :>> kernel="reversedSlotIdentity"; attribute :>> law="Each delivered slot in a nonempty run maps to the reversed contiguous element span consumed by mark_array"; attribute :>> proofLimit="Requires one live allocation generation, fs <= fp <= allocation length and valid writable root slots; not C pointer provenance"; attribute :>> refinement="Qualify generated descriptor view, native type ABI, lifetime and caller/work composition separately"; attribute :>> sourceKey="frame-runs"; attribute :>> modelPath="dev/refactoring/modern-c/models/quint/frame_contract.qnt"; attribute :>> kernelPath="dev/refactoring/modern-c/models/lean/FrameCursorNativeBounds.lean"; }
part mathScope13:MathematicalScope { attribute :>> kind="c-facing-arithmetic"; attribute :>> key="native-run-span"; attribute :>> lawKey="native-run-span"; attribute :>> kernelPath="dev/refactoring/modern-c/models/lean/FrameCursorNativeBounds.lean"; attribute :>> kernel="reversedSlotIdentity"; attribute :>> claim="Each delivered slot in a nonempty run maps to the reversed contiguous element span consumed by mark_array"; attribute :>> limit="Requires one live allocation generation, fs <= fp <= allocation length and valid writable root slots; not C pointer provenance"; }
part law36:OwnershipLaw { ref part :>> domain=domain1; ref part :>> seam=GambitRuntimeComposition::blueprintInterface2; attribute :>> key="native-capacity-profile"; attribute :>> predicate="nativeCapacity"; attribute :>> kernel="bitmapCapacity"; attribute :>> law="Actual RETI sizes under the five-register profile fit signed counters and 513/257 total bitmap words"; attribute :>> proofLimit="Stored size under 16384, alignment4 and extra9 are profile premises; this does not qualify arbitrary configurations"; attribute :>> refinement="Qualify generated descriptor view, native type ABI, lifetime and caller/work composition separately"; attribute :>> sourceKey="frame-emitter"; attribute :>> modelPath="dev/refactoring/modern-c/models/quint/frame_contract.qnt"; attribute :>> kernelPath="dev/refactoring/modern-c/models/lean/FrameCursorNativeBounds.lean"; }
part mathScope14:MathematicalScope { attribute :>> kind="c-facing-arithmetic"; attribute :>> key="native-capacity-profile"; attribute :>> lawKey="native-capacity-profile"; attribute :>> kernelPath="dev/refactoring/modern-c/models/lean/FrameCursorNativeBounds.lean"; attribute :>> kernel="bitmapCapacity"; attribute :>> claim="Actual RETI sizes under the five-register profile fit signed counters and 513/257 total bitmap words"; attribute :>> limit="Stored size under 16384, alignment4 and extra9 are profile premises; this does not qualify arbitrary configurations"; }
part source25:SourceRow { attribute :>> key="cursor-native"; attribute :>> path="vendor/gambit/include/_gambit/module_generation.h.in"; attribute :>> needle="cursor->bits >>= 1;"; attribute :>> limit="Source statement inventory; mathematical finite-word model does not verify the C compiler or ABI"; }
part source26:SourceRow { attribute :>> key="frame-emitter"; attribute :>> path="vendor/gambit/gsc/_t-c-3.scm"; attribute :>> needle="(define (targ-make-frame-spec"; attribute :>> limit="Stored and actual sizes, chunk producer and validation; compiler execution and closed alias census are separate"; }
part source27:SourceRow { attribute :>> key="frame-consumer-lock"; attribute :>> path="vendor/gambit/lib/_mem/object-scanning.inc"; attribute :>> needle="words != descriptor.fs+___FRAME_EXTRA_SLOTS"; attribute :>> limit="sFRAME consumer checks payload length under acquire_frame_access; lock does not by itself prove module lifetime"; }
part edge21:EdgeRow { attribute :>> fromNode="native"; attribute :>> toNode="descriptor-view"; attribute :>> contract="qualify 32/64-bit arithmetic and logical tail view separately from containing allocation"; }
part edge22:EdgeRow { attribute :>> fromNode="descriptor-view"; attribute :>> toNode="collector"; attribute :>> contract="same live frame generation and writable reversed run; descendant work still owed"; }
// Required view supplied by Scheme-owned FrameSpec/setup, not a new runtime
// allocation or a claim that current native descriptors carry these fields.
part def NativeFrameView {
 attribute allocationId:String; attribute generation:Integer;
 attribute descriptorIdentity:String; attribute abiFingerprint:String;
 attribute actualSlots:Integer; attribute wordBits:Integer;
 attribute tailBaseElement:Integer; attribute tailWordCount:Integer;
 attribute frameBaseElement:Integer; attribute frameAllocationWords:Integer;
 attribute admission:String; attribute lifetimeLimit:String;
}
part nativeFrameView:NativeFrameView {
 attribute :>> admission="Qualified producer view, native width 32/64, logical and physical bounds, same live generation";
 attribute :>> lifetimeLimit="Synchronous borrowed scope only; suspension, callback escape and worker transfer need separate retention proof";
}
}
