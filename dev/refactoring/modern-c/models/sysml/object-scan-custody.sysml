package GambitObjectScanCustody { private import ScalarValues::*;
part def Source { attribute key:String; attribute path:String; attribute needle:String; attribute obligation:String; }
part source0:Source { attribute :>> key="packed-state"; attribute :>> path="vendor/gambit/lib/mem.c"; attribute :>> needle="int shift = 2*(pos % (___WORD_WIDTH/2));"; attribute :>> obligation="Per-object coordinate maps to two bits; distinct objects share atomic word"; }
part source1:Source { attribute :>> key="atomic-observe"; attribute :>> path="vendor/gambit/lib/mem.c"; attribute :>> needle="___WORD old = ___COMPARE_AND_SWAP_WORD(cell,0,0);"; attribute :>> obligation="One initial CAS observation per transition call, including duplicate returns"; }
part source2:Source { attribute :>> key="masked-cas"; attribute :>> path="vendor/gambit/lib/mem.c"; attribute :>> needle="(cell,old,(old & ~mask) |"; attribute :>> obligation="CAS failure retries from observed entire packed word; adjacent bits preserved"; }
part source3:Source { attribute :>> key="ready"; attribute :>> path="vendor/gambit/lib/mem.c"; attribute :>> needle="change_object_scan_state(work,header,GC_SCAN_UNPUBLISHED,GC_SCAN_READY)"; attribute :>> obligation="READY publication follows payload writes; does not settle Tail"; }
part source4:Source { attribute :>> key="ordinary-publish"; attribute :>> path="vendor/gambit/lib/mem.c"; attribute :>> needle="publish_object_scan (work, copy_header);"; attribute :>> obligation="Ordinary copy completion precedes READY; frame caller separately enumerated"; }
part source5:Source { attribute :>> key="copy-tail"; attribute :>> path="vendor/gambit/lib/mem.c"; attribute :>> needle="if (cell != 0) goto again;"; attribute :>> obligation="First field remains copier owned after object readiness and possible chunk publication"; }
part source6:Source { attribute :>> key="scan-own"; attribute :>> path="vendor/gambit/lib/mem.c"; attribute :>> needle="(work,body-1,GC_SCAN_READY,GC_SCAN_OWNED);"; attribute :>> obligation="First successful state transition authorizes graph-field scan"; }
part source7:Source { attribute :>> key="duplicate"; attribute :>> path="vendor/gambit/lib/mem.c"; attribute :>> needle="return words; /* no field mutation; the first owner carries debt */"; attribute :>> obligation="Duplicate returns no object ownership and cannot discharge first scanner"; }
part source8:Source { attribute :>> key="done"; attribute :>> path="vendor/gambit/lib/mem.c"; attribute :>> needle="change_object_scan_state(work,body-1,GC_SCAN_OWNED,GC_SCAN_DONE)"; attribute :>> obligation="DONE follows subtype field scanner; derived chunks may remain"; }
part source9:Source { attribute :>> key="generic-pair"; attribute :>> path="vendor/gambit/lib/mem.c"; attribute :>> needle="#define scan_and_advance(ptr, head) scan_no_fast_path(ptr, head)"; attribute :>> obligation="Both pair and generic consumers pass the object authorization"; }
part source10:Source { attribute :>> key="tail-exclusion"; attribute :>> path="vendor/gambit/lib/mem.c"; attribute :>> needle="mark_array (work, body+1, words-1);"; attribute :>> obligation="Ordinary movable low-subtype scan excludes copier-owned first field"; }
part source11:Source { attribute :>> key="chunk-publish"; attribute :>> path="vendor/gambit/lib/mem.c"; attribute :>> needle="heap_chunks_to_scan_tail = new_tail;"; attribute :>> obligation="FIFO content/link and tail visibility under lock and barriers"; }
part source12:Source { attribute :>> key="chunk-dequeue"; attribute :>> path="vendor/gambit/lib/mem.c"; attribute :>> needle="scan_complete_heap_chunk (work, ptr+1);"; attribute :>> obligation="Queue head transfer precedes synchronous scan; active carrier retains call stack"; }
part source13:Source { attribute :>> key="last-idle"; attribute :>> path="vendor/gambit/lib/mem.c"; attribute :>> needle="if (--(*workers_count) == 0)"; attribute :>> obligation="Only last decrement decides phase termination; no object-DONE shortcut"; }
part source14:Source { attribute :>> key="reset"; attribute :>> path="vendor/gambit/lib/mem.c"; attribute :>> needle="memset (ms->base + ___MSECTION_SIZE, 0,"; attribute :>> obligation="One round reset requires previous readers and owners drained"; }
part source15:Source { attribute :>> key="trailer"; attribute :>> path="vendor/gambit/include/gambit.h.in"; attribute :>> needle="#define ___msection_scan_words(n)"; attribute :>> obligation="Two bits per destination word allocated for half-section"; }
part source16:Source { attribute :>> key="sync-branch"; attribute :>> path="vendor/gambit/include/gambit.h.in"; attribute :>> needle="__sync_val_compare_and_swap(p,oldval,newval)"; attribute :>> obligation="GCC legacy builtin branch; effective Darwin selection not certified"; }
part source17:Source { attribute :>> key="frame-link-write"; attribute :>> path="vendor/gambit/lib/mem.c"; attribute :>> needle="ptr = &___FP_STK(alloc,link+1);"; attribute :>> obligation="Next iteration can update previous ready frame link; publishability/interference needs proof"; }
part def Contract { attribute fromNode:String; attribute toNode:String; attribute custody:String; attribute c11:String; attribute premise:String; }
part contract0:Contract { attribute :>> fromNode="initialize"; attribute :>> toNode="READY"; attribute :>> custody="payload publication"; attribute :>> c11="release READY / acquire successful claim"; attribute :>> premise="Payload stores before readiness; forwarding alone insufficient"; }
part contract1:Contract { attribute :>> fromNode="READY"; attribute :>> toNode="OWNED"; attribute :>> custody="one object scan owner"; attribute :>> c11="atomic whole-word masked CAS"; attribute :>> premise="Queue task ownership is not object scan authority"; }
part contract2:Contract { attribute :>> fromNode="OWNED"; attribute :>> toNode="duplicate-return"; attribute :>> custody="retain first call frame"; attribute :>> c11="no ownership clear on mismatch"; attribute :>> premise="An OWNED loser may return while winner and descendants remain active"; }
part contract3:Contract { attribute :>> fromNode="OWNED"; attribute :>> toNode="DONE"; attribute :>> custody="own subtype field footprint"; attribute :>> c11="release completion only after field accesses"; attribute :>> premise="DONE excludes copier Tail and unscanned descendants"; }
part contract4:Contract { attribute :>> fromNode="DONE"; attribute :>> toNode="local-drain"; attribute :>> custody="retain derived work"; attribute :>> c11="active carrier remains until local queues/frontiers settle"; attribute :>> premise="DONE is not an idle or reclamation receipt"; }
part contract5:Contract { attribute :>> fromNode="local-drain"; attribute :>> toNode="idle"; attribute :>> custody="local no-debt condition"; attribute :>> c11="all last uses before mutex-protected decrement"; attribute :>> premise="All real producers must be roster-covered"; }
part contract6:Contract { attribute :>> fromNode="idle"; attribute :>> toNode="phase-terminal"; attribute :>> custody="zero active with closed input"; attribute :>> c11="one termination synchronization domain"; attribute :>> premise="Weak round and cleanup are distinct"; }
part contract7:Contract { attribute :>> fromNode="copier-Tail"; attribute :>> toNode="local-drain"; attribute :>> custody="separate first-field ownership"; attribute :>> c11="scanner and Tail footprints disjoint or synchronized"; attribute :>> premise="Frame link fixups remain an unresolved non-Tail writer"; }
part contract8:Contract { attribute :>> fromNode="reset-cut"; attribute :>> toNode="initialize"; attribute :>> custody="new round identity"; attribute :>> c11="quiescence before plain memset; no late stale task"; attribute :>> premise="Single-epoch model does not prove reset/ABA exclusion"; }
part def Obligation { attribute key:String; attribute status:String; attribute scope:String; }
part obligation0:Obligation { attribute :>> key="finite-custody"; attribute :>> status="proved-in-model"; attribute :>> scope="Twenty projected atomic actions preserve Safe; induction covers arbitrary finite action histories"; }
part obligation1:Obligation { attribute :>> key="duplicates"; attribute :>> status="proved-in-model"; attribute :>> scope="One object two occurrences; loser leaves first owner and child debt unchanged"; }
part obligation2:Obligation { attribute :>> key="terminal-zero"; attribute :>> status="proved-in-model"; attribute :>> scope="Closed input plus zero active implies DONE and no copier Tail or child debt under modeled custody"; }
part obligation3:Obligation { attribute :>> key="projection"; attribute :>> status="conditional-checked"; attribute :>> scope="Actual typed IR guards updates invariant initial and step roster projected; JSON parser/emitter trusted"; }
part obligation4:Obligation { attribute :>> key="real-task-roster"; attribute :>> status="open"; attribute :>> scope="All private frontiers chunks synchronous frame stacks and derived producers; arbitrary task counts not refined"; }
part obligation5:Obligation { attribute :>> key="frame-post-ready-write"; attribute :>> status="open"; attribute :>> scope="Previous captured-frame link may be fixed after READY; legal concurrent queue visibility not proved or ruled out"; }
part obligation6:Obligation { attribute :>> key="c11-source"; attribute :>> status="open"; attribute :>> scope="Effective config atomic storage lockless prechecks and reset lifetime need source-to-C11 simulation"; }
part obligation7:Obligation { attribute :>> key="epoch-and-progress"; attribute :>> status="open"; attribute :>> scope="Packed-state reuse late tasks fault/exception paths and lost-wakeup/fairness outside single-round model"; }
part def Gain { attribute key:String; attribute avoided:String; attribute added:String; attribute condition:String; }
part gain0:Gain { attribute :>> key="duplicate fields"; attribute :>> avoided="At most D redundant field scans for D duplicate occurrences"; attribute :>> added="D additional state lookups and one observation CAS call each absent interference"; attribute :>> condition="Savings only after actual duplicate source/footprint qualification; no throughput claim"; }
part gain1:Gain { attribute :>> key="unique object cost"; attribute :>> avoided="One authorized field scan per object"; attribute :>> added="Three state transitions; six CAS API calls plus three section lookups absent retries"; attribute :>> condition="Compare equally correct structural task uniqueness; object bitmap is not automatically necessary"; }
part gain2:Gain { attribute :>> key="scan metadata"; attribute :>> avoided="No object header or frame coordinate expansion"; attribute :>> added="ceil(ceil(n/2)/(B/2)) words per section plus round clearing; two-bit trailer"; attribute :>> condition="For aligned even sections and B=64: 1/64 full payload bytes; relative active half 1/32"; }
part gain3:Gain { attribute :>> key="counter fusion"; attribute :>> avoided="Avoid a second independent publisher counter"; attribute :>> added="Retain copier owner call frame child work and final idle coverage"; attribute :>> condition="Every source producer synchronous and covered; no new physical-worker failure tolerance"; }
part gain4:Gain { attribute :>> key="modern C choice"; attribute :>> avoided="Explicit ownership shared across pair/generic consumers"; attribute :>> added="C11 atomics generation reset footprint and native proof remain"; attribute :>> condition="No Zig-specific saving established; code-generation language does not prove GC closure"; }
part def Binding { attribute actionName:String; attribute lemma:String; attribute scope:String; }
part binding0:Binding { attribute :>> actionName="forward"; attribute :>> lemma="forwardPreserves"; attribute :>> scope="Projected full guard and update; native source simulation open"; }
part binding1:Binding { attribute :>> actionName="initializeCopy"; attribute :>> lemma="initializeCopyPreserves"; attribute :>> scope="Projected full guard and update; native source simulation open"; }
part binding2:Binding { attribute :>> actionName="publishReady"; attribute :>> lemma="publishReadyPreserves"; attribute :>> scope="Projected full guard and update; native source simulation open"; }
part binding3:Binding { attribute :>> actionName="publishBatch"; attribute :>> lemma="publishBatchPreserves"; attribute :>> scope="Projected full guard and update; native source simulation open"; }
part binding4:Binding { attribute :>> actionName="duplicateTask"; attribute :>> lemma="duplicateTaskPreserves"; attribute :>> scope="Projected full guard and update; native source simulation open"; }
part binding5:Binding { attribute :>> actionName="closeInputs"; attribute :>> lemma="closeInputsPreserves"; attribute :>> scope="Projected full guard and update; native source simulation open"; }
part binding6:Binding { attribute :>> actionName="finishTail"; attribute :>> lemma="finishTailPreserves"; attribute :>> scope="Projected full guard and update; native source simulation open"; }
part binding7:Binding { attribute :>> actionName="claim0"; attribute :>> lemma="claim0Preserves"; attribute :>> scope="Projected full guard and update; native source simulation open"; }
part binding8:Binding { attribute :>> actionName="claim1"; attribute :>> lemma="claim1Preserves"; attribute :>> scope="Projected full guard and update; native source simulation open"; }
part binding9:Binding { attribute :>> actionName="own0"; attribute :>> lemma="own0Preserves"; attribute :>> scope="Projected full guard and update; native source simulation open"; }
part binding10:Binding { attribute :>> actionName="own1"; attribute :>> lemma="own1Preserves"; attribute :>> scope="Projected full guard and update; native source simulation open"; }
part binding11:Binding { attribute :>> actionName="skip0"; attribute :>> lemma="skip0Preserves"; attribute :>> scope="Projected full guard and update; native source simulation open"; }
part binding12:Binding { attribute :>> actionName="skip1"; attribute :>> lemma="skip1Preserves"; attribute :>> scope="Projected full guard and update; native source simulation open"; }
part binding13:Binding { attribute :>> actionName="done0"; attribute :>> lemma="done0Preserves"; attribute :>> scope="Projected full guard and update; native source simulation open"; }
part binding14:Binding { attribute :>> actionName="done1"; attribute :>> lemma="done1Preserves"; attribute :>> scope="Projected full guard and update; native source simulation open"; }
part binding15:Binding { attribute :>> actionName="drain0"; attribute :>> lemma="drain0Preserves"; attribute :>> scope="Projected full guard and update; native source simulation open"; }
part binding16:Binding { attribute :>> actionName="drain1"; attribute :>> lemma="drain1Preserves"; attribute :>> scope="Projected full guard and update; native source simulation open"; }
part binding17:Binding { attribute :>> actionName="idle0"; attribute :>> lemma="idle0Preserves"; attribute :>> scope="Projected full guard and update; native source simulation open"; }
part binding18:Binding { attribute :>> actionName="idle1"; attribute :>> lemma="idle1Preserves"; attribute :>> scope="Projected full guard and update; native source simulation open"; }
part binding19:Binding { attribute :>> actionName="terminate"; attribute :>> lemma="terminatePreserves"; attribute :>> scope="Projected full guard and update; native source simulation open"; }
part def Composition { attribute key:String; attribute lemma:String; attribute scope:String; }
part composition0:Composition { attribute :>> key="induction"; attribute :>> lemma="reachableSafe"; attribute :>> scope="Reachability closure for entire projected step roster"; }
part composition1:Composition { attribute :>> key="final-cut"; attribute :>> lemma="finalZeroImpliesNoDebt"; attribute :>> scope="No omniscient pending-work guard in terminate"; }
part composition2:Composition { attribute :>> key="done-boundary"; attribute :>> lemma="doneNotGlobalClosure"; attribute :>> scope="Counterexample to treating DONE as whole closure"; }
part history:GambitAssuranceRouting::ModelNeed { ref part :>> owner=GambitBuildAssurance::planner.component; attribute :>> obligationId="OSC-history"; attribute :>> kind="interleaving"; attribute :>> subjectPath="dev/refactoring/modern-c/models/quint/object_scan_custody.qnt"; attribute :>> subjectScope="One object two tasks two workers one scan phase within a GC round and child debt"; attribute :>> premise="Formal architecture research; no runtime qualification"; }
part induction:GambitAssuranceRouting::ModelNeed { ref part :>> owner=GambitBuildAssurance::planner.component; attribute :>> obligationId="OSC-induction"; attribute :>> kind="induction"; attribute :>> subjectPath="dev/refactoring/modern-c/models/lean/ObjectScanCustody.lean"; attribute :>> subjectScope="All twenty projected steps invariant preservation and reachable-state induction"; attribute :>> premise="Formal architecture research; no runtime qualification"; }
part projection:GambitAssuranceRouting::ModelNeed { ref part :>> owner=GambitBuildAssurance::planner.component; attribute :>> obligationId="OSC-projection"; attribute :>> kind="restricted-projection"; attribute :>> subjectPath="dev/refactoring/modern-c/models/lean/ObjectScanAst.lean"; attribute :>> subjectScope="Actual typed IR scalar subset; trusted parser and emitter"; attribute :>> premise="Formal architecture research; no runtime qualification"; }
part source:GambitAssuranceRouting::ModelNeed { ref part :>> owner=GambitBuildAssurance::planner.component; attribute :>> obligationId="OSC-source"; attribute :>> kind="source-refinement"; attribute :>> subjectPath="dev/refactoring/modern-c/object-scan-custody-design.org"; attribute :>> subjectScope="Source task and field-footprint refinement unresolved"; attribute :>> premise="Formal architecture research; no runtime qualification"; }
part platform:GambitAssuranceRouting::ModelNeed { ref part :>> owner=GambitBuildAssurance::planner.component; attribute :>> obligationId="OSC-platform"; attribute :>> kind="c11-refinement"; attribute :>> subjectPath="dev/refactoring/modern-c/object-scan-custody-design.org"; attribute :>> subjectScope="Effective C11 atomics and reset/drain unresolved"; attribute :>> premise="Formal architecture research; no runtime qualification"; }
part def Seam { ref part producer:GambitRuntimeComposition::BlueprintModule; ref part consumer:GambitRuntimeComposition::BlueprintModule; attribute contract:String; attribute modelNeed:String; }
part seam0:Seam { ref part :>> producer=GambitRuntimeComposition::blueprintModule3; ref part :>> consumer=GambitRuntimeComposition::blueprintModule4; attribute :>> contract="frozen roots produce copying work"; attribute :>> modelNeed="OSC-source"; }
part seam1:Seam { ref part :>> producer=GambitRuntimeComposition::blueprintModule4; ref part :>> consumer=GambitRuntimeComposition::blueprintModule4; attribute :>> contract="copy/chunk/object/Tail custody"; attribute :>> modelNeed="OSC-history"; }
part seam2:Seam { ref part :>> producer=GambitRuntimeComposition::blueprintModule4; ref part :>> consumer=GambitRuntimeComposition::blueprintModule5; attribute :>> contract="phase idle and closed producer roster"; attribute :>> modelNeed="OSC-induction"; }
part seam3:Seam { ref part :>> producer=GambitRuntimeComposition::blueprintModule4; ref part :>> consumer=GambitRuntimeComposition::blueprintModule1; attribute :>> contract="atomic packed storage and reset"; attribute :>> modelNeed="OSC-platform"; }

part source18:Source { attribute :>> key="weak-phase-entry"; attribute :>> path="vendor/gambit/lib/mem.c"; attribute :>> needle="traverse_weak_refs = 1;"; attribute :>> obligation="Object DONE persists into weak processing; prove later phase field obligations use explicit weak consumers before treating attempts as duplicates"; }
part obligation8:Obligation { attribute :>> key="phase-footprint"; attribute :>> status="open"; attribute :>> scope="Strong and weak rounds share object scan states; later-phase required work must be discharged by process_wills and other specialized consumers before DONE suppression is equivalent"; }

part contract9:Contract { attribute :>> fromNode="READY"; attribute :>> toNode="chunk-queued"; attribute :>> custody="initialized chunk publication"; attribute :>> c11="release visibility before queue read"; attribute :>> premise="READY alone does not transfer queue custody"; }
part contract10:Contract { attribute :>> fromNode="chunk-queued"; attribute :>> toNode="chunk-claimed"; attribute :>> custody="dequeue transfers task custody"; attribute :>> c11="FIFO lock then active scan frame"; attribute :>> premise="Chunk may contain several object identities"; }
part contract11:Contract { attribute :>> fromNode="chunk-claimed"; attribute :>> toNode="OWNED"; attribute :>> custody="claim object authority"; attribute :>> c11="acquire successful object CAS"; attribute :>> premise="Queue and object identities are independent"; }
part contract12:Contract { attribute :>> fromNode="initialize"; attribute :>> toNode="copier-Tail"; attribute :>> custody="reserve first field"; attribute :>> c11="footprint disjointness or synchronization"; attribute :>> premise="Tail can remain after READY and DONE"; }
part contract13:Contract { attribute :>> fromNode="duplicate-return"; attribute :>> toNode="local-drain"; attribute :>> custody="settle occurrence only"; attribute :>> c11="original owner remains counted"; attribute :>> premise="No release of original object frame or child debt"; }

part gain5:Gain { attribute :>> key="typed atomic observation"; attribute :>> avoided="Replace six CAS API calls per unique object with three loads plus three transition CAS on no-retry path"; attribute :>> added="Explicit atomic storage and observation success/failure ordering; retries remain"; attribute :>> condition="Proposed modern C service only; global legacy CAS macro replacement is inadmissible"; }
part gain6:Gain { attribute :>> key="validated scan coordinates"; attribute :>> avoided="Potentially remove repeated 3U+D section lookups"; attribute :>> added="Section epoch header bounds trailer mapping and queue-transfer validation"; attribute :>> condition="Allocator and chunk producer issue coordinates; stale coordinate refusal required"; }
}
