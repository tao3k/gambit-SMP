package GambitImageMembershipEnrollment { private import ScalarValues::*;
part def SourceRow { attribute key:String; attribute path:String; attribute needle:String; attribute obligation:String; }
part source0:SourceRow { attribute :>> key="linker-exec"; attribute :>> path="vendor/gambit/lib/setup.c"; attribute :>> needle="mol = linker (___GSTATE);"; attribute :>> obligation="Reservation must precede executing linker"; }
part source1:SourceRow { attribute :>> key="linker-rewrite"; attribute :>> path="vendor/gambit/lib/setup.c"; attribute :>> needle="p->mol = linker_to_mod_or_lnk"; attribute :>> obligation="Link table resolved in place; not immutable discovery"; }
part source2:SourceRow { attribute :>> key="ordered-traverse"; attribute :>> path="vendor/gambit/lib/setup.c"; attribute :>> needle="e = for_each_module (ctx, p->mol, proc);"; attribute :>> obligation="Distinct ownership set must not deduplicate ordered initialization effects"; }
part source3:SourceRow { attribute :>> key="setup-atomic-todo"; attribute :>> path="vendor/gambit/lib/setup.c"; attribute :>> needle="TODO: make this phase atomic for when there are multiple VMs?"; attribute :>> obligation="Current setup lacks image owner gate"; }
part source4:SourceRow { attribute :>> key="positive-count"; attribute :>> path="vendor/gambit/lib/setup.c"; attribute :>> needle="ctx->module_count++;"; attribute :>> obligation="Count restricted by lblcount branch"; }
part source5:SourceRow { attribute :>> key="positive-descriptors"; attribute :>> path="vendor/gambit/lib/setup.c"; attribute :>> needle="if (module->lblcount > 0)"; attribute :>> obligation="Returned descriptor array is not complete native membership"; }
part source6:SourceRow { attribute :>> key="permanent"; attribute :>> path="vendor/gambit/lib/setup.c"; attribute :>> needle="NULL, /* allocate as permanent object */"; attribute :>> obligation="Current wrapper has process storage lifetime"; }
part source7:SourceRow { attribute :>> key="raw-store"; attribute :>> path="vendor/gambit/lib/setup.c"; attribute :>> needle="___CAST(void*,module),"; attribute :>> obligation="Raw module pointer escapes"; }
part source8:SourceRow { attribute :>> key="field-store"; attribute :>> path="vendor/gambit/lib/setup.c"; attribute :>> needle="___VECTORELEM(descr, ___MODULE_DESCR_MODULE_STRUCT) = module_scmobj;"; attribute :>> obligation="Facade migration must cover legacy field reader"; }
part source9:SourceRow { attribute :>> key="program-alias"; attribute :>> path="vendor/gambit/lib/setup.c"; attribute :>> needle="___VECTORELEM(___VECTORELEM(ctx->program_descr, 0), ctx->module_count) = descr;"; attribute :>> obligation="Same descriptor referenced by permanent program array"; }
part source10:SourceRow { attribute :>> key="setup-outside"; attribute :>> path="vendor/gambit/lib/setup.c"; attribute :>> needle="return module->setup_mod ();"; attribute :>> obligation="Zero-label ABI branch still executes setup hook; legal generated witness OPEN"; }
part source11:SourceRow { attribute :>> key="setup-sentinel"; attribute :>> path="vendor/gambit/lib/setup.c"; attribute :>> needle="mol->linkfile.version = -1;"; attribute :>> obligation="Setup result and loaded sentinel do not prove no partial effects"; }
part source12:SourceRow { attribute :>> key="bootstrap"; attribute :>> path="vendor/gambit/lib/setup.c"; attribute :>> needle="___GSTATE->program_descr = err;"; attribute :>> obligation="Process owner needed before VM initialization"; }
part source13:SourceRow { attribute :>> key="global-alias"; attribute :>> path="vendor/gambit/lib/_kernel.scm"; attribute :>> needle="___RESULT = ___GSTATE->program_descr;"; attribute :>> obligation="Program descriptor exposed by reference"; }
part source14:SourceRow { attribute :>> key="init-raw"; attribute :>> path="vendor/gambit/lib/_kernel.scm"; attribute :>> needle="___CAST(___module_struct*,___FOREIGN_PTR_FIELD(___ARG1))->init_mod"; attribute :>> obligation="Actual reader blindly interprets raw pointer"; }
part source15:SourceRow { attribute :>> key="remove-cell"; attribute :>> path="vendor/gambit/lib/_kernel.scm"; attribute :>> needle="(and x (##set-car! x #f))"; attribute :>> obligation="Removing registry cell cannot erase descriptor aliases"; }
part source16:SourceRow { attribute :>> key="register-todo"; attribute :>> path="vendor/gambit/lib/_kernel.scm"; attribute :>> needle="TODO: make manipulation of ##registered-modules atomic"; attribute :>> obligation="Concurrent enrollment not presently atomic"; }
part source17:SourceRow { attribute :>> key="supply-alias"; attribute :>> path="vendor/gambit/lib/_kernel.scm"; attribute :>> needle="(##register-module-descr! module-ref module-descr)"; attribute :>> obligation="Multiple supply names share descriptor identity"; }
part source18:SourceRow { attribute :>> key="field-setter"; attribute :>> path="vendor/gambit/lib/_kernel#.scm"; attribute :>> needle="(##define-macro (macro-module-descr-module-struct-set!"; attribute :>> obligation="Mutable vector accessor exists; bounded inventory is not alias closure"; }
part source19:SourceRow { attribute :>> key="module-callback"; attribute :>> path="vendor/gambit/lib/_module.scm"; attribute :>> needle="(macro-module-module-descr mod)"; attribute :>> obligation="Callback/lookup consumers preserve descriptor identity"; }
part source20:SourceRow { attribute :>> key="vm-publish"; attribute :>> path="vendor/gambit/lib/mem.c"; attribute :>> needle="tail->next = ___vms;"; attribute :>> obligation="VM topology publication precedes remaining initialization"; }
part source21:SourceRow { attribute :>> key="vm-glos"; attribute :>> path="vendor/gambit/lib/mem.c"; attribute :>> needle="___vms->glos = ___CAST(___SCMOBJ*,___ALLOC_MEM(n * sizeof (___SCMOBJ)));"; attribute :>> obligation="Later globals allocation; list presence is not READY"; }
part source22:SourceRow { attribute :>> key="vm-unlink"; attribute :>> path="vendor/gambit/lib/mem.c"; attribute :>> needle="prev->next = next;"; attribute :>> obligation="VM unlink not proof of native detachment"; }
part source23:SourceRow { attribute :>> key="vm-lock"; attribute :>> path="vendor/gambit/lib/mem.c"; attribute :>> needle="It is assumed that ___GSTATE->vm_list_mut is currently locked"; attribute :>> obligation="Topology synchronization distinct from image gate"; }
part source24:SourceRow { attribute :>> key="labels"; attribute :>> path="vendor/gambit/include/gambit.h.in"; attribute :>> needle="___label_struct *lbltbl; int lblcount;"; attribute :>> obligation="Native image membership includes labels and hosts"; }
part source25:SourceRow { attribute :>> key="ofd"; attribute :>> path="vendor/gambit/include/gambit.h.in"; attribute :>> needle="___WORD *ofdtbl; int ofd_length;"; attribute :>> obligation="Relocated frame metadata needs independent ownership mapping"; }
part source26:SourceRow { attribute :>> key="label-copy"; attribute :>> path="vendor/gambit/lib/setup.c"; attribute :>> needle="module->lbltbl = new_lbltbl;"; attribute :>> obligation="Addresses can move outside image range"; }
part source27:SourceRow { attribute :>> key="foreign-release"; attribute :>> path="vendor/gambit/lib/c_intf.c"; attribute :>> needle="___FOREIGN_RELEASE_FN_FIELD(r) = ___CAST(___SCMOBJ,release_fn);"; attribute :>> obligation="Native callback address can outlive ordinary module registry"; }
part source28:SourceRow { attribute :>> key="c-closure"; attribute :>> path="vendor/gambit/lib/os_dyn.c"; attribute :>> needle="___set_data_rc (c_closure, proc);"; attribute :>> obligation="Scheme root alone omits native converter ownership"; }
part source29:SourceRow { attribute :>> key="load-publish"; attribute :>> path="vendor/gambit/lib/os_dyn.c"; attribute :>> needle="p->next = ___dyn_mod.dl_list;"; attribute :>> obligation="Loader handle published before setup success"; }
part source30:SourceRow { attribute :>> key="linker-emit"; attribute :>> path="vendor/gambit/gsc/_t-c-1.scm"; attribute :>> needle="BEGIN_OLD_LNK"; attribute :>> obligation="Generated linker classification can supply explicit sidecar"; }
part source31:SourceRow { attribute :>> key="unload"; attribute :>> path="vendor/gambit/lib/os_dyn.c"; attribute :>> needle="dlclose (p->descr);"; attribute :>> obligation="Known OS-reference release does not prove unmapped memory"; }
part def InventoryRow { attribute key:String; attribute path:String; attribute pattern:String; attribute count:String; attribute scope:String; }
part inventory0:InventoryRow { attribute :>> key="module-struct-setter"; attribute :>> path="vendor/gambit/lib/_kernel#.scm"; attribute :>> pattern="\\(##define-macro \\(macro-module-descr-module-struct-set!"; attribute :>> count="1"; attribute :>> scope="Exact lexical scope only; arbitrary vector/FFI aliases and preprocessing closure OPEN"; }
part inventory1:InventoryRow { attribute :>> key="named-setter-kernel"; attribute :>> path="vendor/gambit/lib/_kernel.scm"; attribute :>> pattern="macro-module-descr-module-struct-set!"; attribute :>> count="0"; attribute :>> scope="Exact lexical scope only; arbitrary vector/FFI aliases and preprocessing closure OPEN"; }
part inventory2:InventoryRow { attribute :>> key="init-raw-reader"; attribute :>> path="vendor/gambit/lib/_kernel.scm"; attribute :>> pattern="___CAST\\(___module_struct\\*,___FOREIGN_PTR_FIELD\\(___ARG1\\)\\)->init_mod"; attribute :>> count="1"; attribute :>> scope="Exact lexical scope only; arbitrary vector/FFI aliases and preprocessing closure OPEN"; }
part inventory3:InventoryRow { attribute :>> key="vm-tail-insert"; attribute :>> path="vendor/gambit/lib/mem.c"; attribute :>> pattern="tail->next = ___vms;"; attribute :>> count="1"; attribute :>> scope="Exact lexical scope only; arbitrary vector/FFI aliases and preprocessing closure OPEN"; }
part inventory4:InventoryRow { attribute :>> key="registry-todo"; attribute :>> path="vendor/gambit/lib/_kernel.scm"; attribute :>> pattern="TODO: make manipulation of ##registered-modules atomic"; attribute :>> count="1"; attribute :>> scope="Exact lexical scope only; arbitrary vector/FFI aliases and preprocessing closure OPEN"; }
part inventory5:InventoryRow { attribute :>> key="descriptor-field-store"; attribute :>> path="vendor/gambit/lib/setup.c"; attribute :>> pattern="___VECTORELEM\\(descr, ___MODULE_DESCR_MODULE_STRUCT\\) = module_scmobj;"; attribute :>> count="1"; attribute :>> scope="Exact lexical scope only; arbitrary vector/FFI aliases and preprocessing closure OPEN"; }
part def ConsumerRow { attribute key:String; attribute callers:String; attribute custody:String; attribute gap:String; }
part consumer0:ConsumerRow { attribute :>> key="native-members"; attribute :>> callers="linker_to_mod_or_lnk -> for_each_module -> setup_mod"; attribute :>> custody="Complete ownership set AND ordered effect plan"; attribute :>> gap="Zero-label ABI branch must be represented; no legal generated witness yet"; }
part consumer1:ConsumerRow { attribute :>> key="descriptor-alias"; attribute :>> callers="collect_moddescrs -> program_descr -> registry supply names"; attribute :>> custody="Same descriptor identity and permanent foreign wrapper"; attribute :>> gap="Untracked raw aliases pin legacy image; field overwrite insufficient"; }
part consumer2:ConsumerRow { attribute :>> key="vm-reservation"; attribute :>> callers="setup_mem_vmstate -> glos allocation -> setup_pstate"; attribute :>> custody="Stable RESERVED record before executable publication"; attribute :>> gap="VM topology is not ready owner roster"; }
part consumer3:ConsumerRow { attribute :>> key="bootstrap-owner"; attribute :>> callers="setup_modules -> GSTATE program_descr -> setup_vmstate"; attribute :>> custody="Process/bootstrap ownership independent of VM count"; attribute :>> gap="No current per-image record"; }
part consumer4:ConsumerRow { attribute :>> key="exit-owner"; attribute :>> callers="cleanup_vmstate -> cleanup_mem_vmstate -> vm unlink"; attribute :>> custody="Persistent tombstone until all native leases detached"; attribute :>> gap="Failure or unknown outcome retains debt"; }
part consumer5:ConsumerRow { attribute :>> key="maintenance-ffi"; attribute :>> callers="frame/OFD scanners and foreign release/converter"; attribute :>> custody="Native code data and moved metadata ownership"; attribute :>> gap="Prior global-unload inventory imported; full native alias closure OPEN"; }
part def ClaimRow { attribute key:String; attribute mechanism:String; attribute condition:String; attribute result:String; attribute gap:String; }
part claim0:ClaimRow { attribute :>> key="membership"; attribute :>> mechanism="Separate deduplicated ownership set and ordered linker effect plan"; attribute :>> condition="Producer ModuleSpec and qualified loader adapter cover every member/dependency"; attribute :>> result="Descriptor subset cannot silently omit native setup members"; attribute :>> gap="Linker invocation can have effects; complete native image mapping OPEN"; }
part claim1:ClaimRow { attribute :>> key="reservation"; attribute :>> mechanism="Reserve owner ticket before ready publication under same close authority"; attribute :>> condition="Stable ImageId VM incarnation epoch and non-overflow key"; attribute :>> result="Close includes pending VM initialization"; attribute :>> gap="Current VM list has no such enrollment"; }
part claim2:ClaimRow { attribute :>> key="late-commit"; attribute :>> mechanism="Preclose reservation may settle after close without reopening public entry"; attribute :>> condition="Existing accepted debt retained until known commit/abort"; attribute :>> result="Initialization completion is distinct from fresh enrollment"; attribute :>> gap="Unknown side effects retain tombstone"; }
part claim3:ClaimRow { attribute :>> key="migration"; attribute :>> mechanism="Interned owned handle replaces raw descriptor access on migrated route"; attribute :>> condition="Every old field reader writer exporter and captured alias accounted"; attribute :>> result="Owned facade cannot erase legacy raw escape"; attribute :>> gap="Permanent or untracked alias prevents unload"; }
part claim4:ClaimRow { attribute :>> key="coverage"; attribute :>> mechanism="Explicit quotient maps all native owners to represented slots"; attribute :>> condition="Every owner included; slot receipt implies detachment of all mapped owners"; attribute :>> result="Finite model safety composes with previous AllDetached predicate"; attribute :>> gap="Coverage and arbitrary owner-product refinement OPEN"; }
part claim5:ClaimRow { attribute :>> key="retirement"; attribute :>> mechanism="Current-epoch receipt only after close and known quiescence"; attribute :>> condition="Native observer and external callback drain included"; attribute :>> result="VM unlink and duplicate acknowledgments cannot authorize unload"; attribute :>> gap="C11/source and platform qualification OPEN"; }
part def MemoryRow { attribute key:String; attribute publication:String; attribute consumer:String; attribute gap:String; }
part memory0:MemoryRow { attribute :>> key="reserve-close"; attribute :>> publication="One mutex or proven atomic ledger linearizes reserve versus close"; attribute :>> consumer="Preclose tickets included; late reserve denied before payload access"; attribute :>> gap="No independent list snapshot plus gate check"; }
part memory1:MemoryRow { attribute :>> key="init-publish"; attribute :>> publication="Private initialization then release commit of stable owner record"; attribute :>> consumer="Acquire validates ImageId incarnation epoch and READY or closing-settlement state"; attribute :>> gap="Do not hold topology/image mutex through linker callbacks GC or waits"; }
part memory2:MemoryRow { attribute :>> key="borrow-close"; attribute :>> publication="Reserve borrow under same authority before reading module pointer"; attribute :>> consumer="Return last use before release decrement; acquire receipt sees drain"; attribute :>> gap="Raw accessor bypass and counter overflow must deny qualification"; }
part memory3:MemoryRow { attribute :>> key="receipt-retire"; attribute :>> publication="Release publish keyed receipt after alias/root/native detachment"; attribute :>> consumer="Acquire aggregator checks immutable membership and owner digest"; attribute :>> gap="VM storage may die; control record and receipts cannot reside in image"; }
part memory4:MemoryRow { attribute :>> key="unknown"; attribute :>> publication="No speculative decrement on unknown setup/abort/delivery"; attribute :>> consumer="Stable tombstone retains dependencies and provisional handle"; attribute :>> gap="C11 weak-memory refinement not supplied by sequential QNT"; }
part def GainRow { attribute key:String; attribute avoided:String; attribute added:String; attribute condition:String; }
part gain0:GainRow { attribute :>> key="completeness"; attribute :>> avoided="Avoid full-VM rescans on each repeated receipt; cache sealed membership"; attribute :>> added="O(M+E) member/effect metadata and O(V+P) stable owner ledger"; attribute :>> condition="M members E initialization edges V owners P pending; closure must be complete"; }
part gain1:GainRow { attribute :>> key="parallel"; attribute :>> avoided="Separate VM topology lock from callbacks and image lifetime control"; attribute :>> added="Short authority operations per accepted enrollment/borrow"; attribute :>> condition="Parallel benefit conditional on lock contention and absence of untracked native aliases"; }
part gain2:GainRow { attribute :>> key="incremental"; attribute :>> avoided="Keep old/new generated module generations concurrently without global restart"; attribute :>> added="Generation-keyed handles and ABI dependency invalidation"; attribute :>> condition="Artifact replacement is not permission to free old captured frames"; }
part gain3:GainRow { attribute :>> key="permanent"; attribute :>> avoided="Qualified handles permit eventual per-image release instead of whole-process retention"; attribute :>> added="One stable handle per identity plus observer drain metadata"; attribute :>> condition="Reclaimable bytes ZERO while any untracked permanent/raw alias remains"; }
part gain4:GainRow { attribute :>> key="duplicate"; attribute :>> avoided="Idempotent keyed receipt avoids duplicate completion accounting"; attribute :>> added="O(V) receipt keys or equivalent compressed set"; attribute :>> condition="One owner receipt cannot stand for another without proven coverage"; }
part gain5:GainRow { attribute :>> key="language"; attribute :>> avoided="Same modern C ownership ABI shared by GC FFI and module service"; attribute :>> added="Explicit generated adapters and source refinement"; attribute :>> condition="No runtime speedup or incremental Zig advantage established"; }
part def ContractRow { attribute fromNode:String; attribute toNode:String; attribute custody:String; }
part contract0:ContractRow { attribute :>> fromNode="loader-reservation"; attribute :>> toNode="resolved-linker-graph"; attribute :>> custody="Own provisional native handle before executing mutating linker"; }
part contract1:ContractRow { attribute :>> fromNode="resolved-linker-graph"; attribute :>> toNode="ownership-membership"; attribute :>> custody="All native modules including zero-label ABI branch and dependencies"; }
part contract2:ContractRow { attribute :>> fromNode="resolved-linker-graph"; attribute :>> toNode="ordered-initialization"; attribute :>> custody="Preserve edge flags order duplicate effects; not ownership dedup"; }
part contract3:ContractRow { attribute :>> fromNode="ownership-membership"; attribute :>> toNode="sealed-image-manifest"; attribute :>> custody="Qualified ModuleSpec mapping; immutable close digest"; }
part contract4:ContractRow { attribute :>> fromNode="process-bootstrap-owner"; attribute :>> toNode="owner-reservation"; attribute :>> custody="Module setup precedes VM ready; bootstrap not omitted"; }
part contract5:ContractRow { attribute :>> fromNode="VM-topology"; attribute :>> toNode="owner-reservation"; attribute :>> custody="Presence is not READY; reserve stable incarnation ticket"; }
part contract6:ContractRow { attribute :>> fromNode="owner-reservation"; attribute :>> toNode="private-initialization"; attribute :>> custody="Accepted ticket retains debt through callbacks and failures"; }
part contract7:ContractRow { attribute :>> fromNode="private-initialization"; attribute :>> toNode="published-owner"; attribute :>> custody="Open commit or preclose settlement; no fresh postclose access"; }
part contract8:ContractRow { attribute :>> fromNode="private-initialization"; attribute :>> toNode="unknown-tombstone"; attribute :>> custody="Unknown side effects preserve provisional ownership"; }
part contract9:ContractRow { attribute :>> fromNode="legacy-permanent-raw"; attribute :>> toNode="retained-image"; attribute :>> custody="New facade cannot revoke escaped raw pointers"; }
part contract10:ContractRow { attribute :>> fromNode="sealed-image-manifest"; attribute :>> toNode="close-authority"; attribute :>> custody="Freeze accepted and pending owners under same gate"; }
part contract11:ContractRow { attribute :>> fromNode="published-owner"; attribute :>> toNode="local-detachment"; attribute :>> custody="Close borrows then drain roots frames FFI and derived work"; }
part contract12:ContractRow { attribute :>> fromNode="VM-exit"; attribute :>> toNode="local-detachment"; attribute :>> custody="Unlink not receipt; external stable record survives"; }
part contract13:ContractRow { attribute :>> fromNode="local-detachment"; attribute :>> toNode="current-keyed-receipts"; attribute :>> custody="Image generation VM incarnation close epoch scope match"; }
part contract14:ContractRow { attribute :>> fromNode="current-keyed-receipts"; attribute :>> toNode="global-unload-permission"; attribute :>> custody="All required owners no pending unknown raw escape or observers"; }
part contract15:ContractRow { attribute :>> fromNode="unknown-tombstone"; attribute :>> toNode="retained-image"; attribute :>> custody="Known recovery evidence required; no blind retry or debt erase"; }
part def BindingRow { attribute actionName:String; attribute lemma:String; attribute scope:String; }
part binding0:BindingRow { attribute :>> actionName="image_membership_enrollment.enumerateHelper"; attribute :>> lemma="ImageEnrollment.enumerateHelperPreserves"; attribute :>> scope="Extracted typed IR step; source realization and C11 remain OPEN"; }
part binding1:BindingRow { attribute :>> actionName="image_membership_enrollment.sealMembers"; attribute :>> lemma="ImageEnrollment.sealMembersPreserves"; attribute :>> scope="Extracted typed IR step; source realization and C11 remain OPEN"; }
part binding2:BindingRow { attribute :>> actionName="image_membership_enrollment.prepareOwned"; attribute :>> lemma="ImageEnrollment.prepareOwnedPreserves"; attribute :>> scope="Extracted typed IR step; source realization and C11 remain OPEN"; }
part binding3:BindingRow { attribute :>> actionName="image_membership_enrollment.exposeRaw"; attribute :>> lemma="ImageEnrollment.exposeRawPreserves"; attribute :>> scope="Extracted typed IR step; source realization and C11 remain OPEN"; }
part binding4:BindingRow { attribute :>> actionName="image_membership_enrollment.reserveOwner"; attribute :>> lemma="ImageEnrollment.reserveOwnerPreserves"; attribute :>> scope="Extracted typed IR step; source realization and C11 remain OPEN"; }
part binding5:BindingRow { attribute :>> actionName="image_membership_enrollment.commitOpen"; attribute :>> lemma="ImageEnrollment.commitOpenPreserves"; attribute :>> scope="Extracted typed IR step; source realization and C11 remain OPEN"; }
part binding6:BindingRow { attribute :>> actionName="image_membership_enrollment.closeGlobal"; attribute :>> lemma="ImageEnrollment.closeGlobalPreserves"; attribute :>> scope="Extracted typed IR step; source realization and C11 remain OPEN"; }
part binding7:BindingRow { attribute :>> actionName="image_membership_enrollment.commitClosing"; attribute :>> lemma="ImageEnrollment.commitClosingPreserves"; attribute :>> scope="Extracted typed IR step; source realization and C11 remain OPEN"; }
part binding8:BindingRow { attribute :>> actionName="image_membership_enrollment.abortReserved"; attribute :>> lemma="ImageEnrollment.abortReservedPreserves"; attribute :>> scope="Extracted typed IR step; source realization and C11 remain OPEN"; }
part binding9:BindingRow { attribute :>> actionName="image_membership_enrollment.unknownOwner"; attribute :>> lemma="ImageEnrollment.unknownOwnerPreserves"; attribute :>> scope="Extracted typed IR step; source realization and C11 remain OPEN"; }
part binding10:BindingRow { attribute :>> actionName="image_membership_enrollment.close0"; attribute :>> lemma="ImageEnrollment.close0Preserves"; attribute :>> scope="Extracted typed IR step; source realization and C11 remain OPEN"; }
part binding11:BindingRow { attribute :>> actionName="image_membership_enrollment.close1"; attribute :>> lemma="ImageEnrollment.close1Preserves"; attribute :>> scope="Extracted typed IR step; source realization and C11 remain OPEN"; }
part binding12:BindingRow { attribute :>> actionName="image_membership_enrollment.return0"; attribute :>> lemma="ImageEnrollment.return0Preserves"; attribute :>> scope="Extracted typed IR step; source realization and C11 remain OPEN"; }
part binding13:BindingRow { attribute :>> actionName="image_membership_enrollment.return1"; attribute :>> lemma="ImageEnrollment.return1Preserves"; attribute :>> scope="Extracted typed IR step; source realization and C11 remain OPEN"; }
part binding14:BindingRow { attribute :>> actionName="image_membership_enrollment.exitKnown"; attribute :>> lemma="ImageEnrollment.exitKnownPreserves"; attribute :>> scope="Extracted typed IR step; source realization and C11 remain OPEN"; }
part binding15:BindingRow { attribute :>> actionName="image_membership_enrollment.reuseBeforeClose"; attribute :>> lemma="ImageEnrollment.reuseBeforeClosePreserves"; attribute :>> scope="Extracted typed IR step; source realization and C11 remain OPEN"; }
part binding16:BindingRow { attribute :>> actionName="image_membership_enrollment.issue0"; attribute :>> lemma="ImageEnrollment.issue0Preserves"; attribute :>> scope="Extracted typed IR step; source realization and C11 remain OPEN"; }
part binding17:BindingRow { attribute :>> actionName="image_membership_enrollment.issue1"; attribute :>> lemma="ImageEnrollment.issue1Preserves"; attribute :>> scope="Extracted typed IR step; source realization and C11 remain OPEN"; }
part binding18:BindingRow { attribute :>> actionName="image_membership_enrollment.observe"; attribute :>> lemma="ImageEnrollment.observePreserves"; attribute :>> scope="Extracted typed IR step; source realization and C11 remain OPEN"; }
part binding19:BindingRow { attribute :>> actionName="image_membership_enrollment.retireObserver"; attribute :>> lemma="ImageEnrollment.retireObserverPreserves"; attribute :>> scope="Extracted typed IR step; source realization and C11 remain OPEN"; }
part binding20:BindingRow { attribute :>> actionName="image_membership_enrollment.borrow0"; attribute :>> lemma="ImageEnrollment.borrow0Preserves"; attribute :>> scope="Extracted typed IR step; source realization and C11 remain OPEN"; }
part binding21:BindingRow { attribute :>> actionName="image_membership_enrollment.borrow1"; attribute :>> lemma="ImageEnrollment.borrow1Preserves"; attribute :>> scope="Extracted typed IR step; source realization and C11 remain OPEN"; }
part binding22:BindingRow { attribute :>> actionName="image_membership_enrollment.rejectLate"; attribute :>> lemma="ImageEnrollment.rejectLatePreserves"; attribute :>> scope="Extracted typed IR step; source realization and C11 remain OPEN"; }
part binding23:BindingRow { attribute :>> actionName="image_membership_enrollment.rejectStale"; attribute :>> lemma="ImageEnrollment.rejectStalePreserves"; attribute :>> scope="Extracted typed IR step; source realization and C11 remain OPEN"; }
part binding24:BindingRow { attribute :>> actionName="image_membership_enrollment.unknownExternal"; attribute :>> lemma="ImageEnrollment.unknownExternalPreserves"; attribute :>> scope="Extracted typed IR step; source realization and C11 remain OPEN"; }
part binding25:BindingRow { attribute :>> actionName="image_membership_enrollment.permit"; attribute :>> lemma="ImageEnrollment.permitPreserves"; attribute :>> scope="Extracted typed IR step; source realization and C11 remain OPEN"; }
part binding26:BindingRow { attribute :>> actionName="image_membership_enrollment.invalidateMembership"; attribute :>> lemma="ImageEnrollment.invalidateMembershipPreserves"; attribute :>> scope="Extracted typed IR step; source realization and C11 remain OPEN"; }
part def ProofRow { attribute key:String; attribute lemma:String; }
part proof0:ProofRow { attribute :>> key="all-step"; attribute :>> lemma="ImageEnrollment.stepPreserves"; }
part proof1:ProofRow { attribute :>> key="reachable"; attribute :>> lemma="ImageEnrollment.reachableSafe"; }
part proof2:ProofRow { attribute :>> key="receipts"; attribute :>> lemma="ImageEnrollment.permitOwnerReceipts"; }
part proof3:ProofRow { attribute :>> key="preclose-ticket"; attribute :>> lemma="ImageEnrollment.closeCapturesReservedOwner"; }
part proof4:ProofRow { attribute :>> key="raw-not-erased"; attribute :>> lemma="ImageEnrollment.facadeDoesNotEraseRawAlias"; }
part proof5:ProofRow { attribute :>> key="required-owners"; attribute :>> lemma="ImageEnrollmentComposition.permitCoversRequiredOwners"; }
part proof6:ProofRow { attribute :>> key="native-coverage"; attribute :>> lemma="ImageEnrollmentComposition.actualOwnerCoverage"; }
part proof7:ProofRow { attribute :>> key="raw-block"; attribute :>> lemma="ImageEnrollmentComposition.legacyRawBlocksPermit"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse6; attribute :>> contract="complete-member-manifest"; attribute :>> actionName="image_membership_enrollment.sealMembers"; attribute :>> lemma="ImageEnrollment.sealMembersPreserves"; }
part seam1:SeamRow { ref part :>> producer=GambitAssuranceRelations::modelUse4; ref part :>> consumer=GambitAssuranceRelations::modelUse6; attribute :>> contract="preclose-owner-reservation"; attribute :>> actionName="image_membership_enrollment.reserveOwner"; attribute :>> lemma="ImageEnrollment.closeCapturesReservedOwner"; }
part seam2:SeamRow { ref part :>> producer=GambitAssuranceRelations::modelUse5; ref part :>> consumer=GambitAssuranceRelations::modelUse6; attribute :>> contract="legacy-alias-detachment"; attribute :>> actionName="image_membership_enrollment.prepareOwned"; attribute :>> lemma="ImageEnrollment.facadeDoesNotEraseRawAlias"; }
part seam3:SeamRow { ref part :>> producer=GambitAssuranceRelations::modelUse3; ref part :>> consumer=GambitAssuranceRelations::modelUse6; attribute :>> contract="root-and-native-detachment"; attribute :>> actionName="image_membership_enrollment.permit"; attribute :>> lemma="ImageEnrollmentComposition.actualOwnerCoverage"; }
part history:GambitAssuranceRouting::ModelNeed { ref part :>> owner=GambitAssuranceRelations::modelUse6; attribute :>> obligationId="IE-history"; attribute :>> kind="interleaving"; attribute :>> subjectPath="dev/refactoring/modern-c/models/quint/image_membership_enrollment.qnt"; attribute :>> subjectScope="Optional owner reservation close settlement raw escape and incarnation histories"; attribute :>> premise="Conditional research; no native unload acceptance"; }
part induction:GambitAssuranceRouting::ModelNeed { ref part :>> owner=GambitAssuranceRelations::modelUse6; attribute :>> obligationId="IE-induction"; attribute :>> kind="induction"; attribute :>> subjectPath="dev/refactoring/modern-c/models/lean/ImageEnrollment.lean"; attribute :>> subjectScope="All extracted atomic steps; sequential abstract ledger only"; attribute :>> premise="Conditional research; no native unload acceptance"; }
part composition:GambitAssuranceRouting::ModelNeed { ref part :>> owner=GambitAssuranceRelations::modelUse6; attribute :>> obligationId="IE-composition"; attribute :>> kind="induction"; attribute :>> subjectPath="dev/refactoring/modern-c/models/lean/ImageEnrollmentComposition.lean"; attribute :>> subjectScope="Required owners imply preceding AllDetached under explicit native coverage premise"; attribute :>> premise="Conditional research; no native unload acceptance"; }
part projection:GambitAssuranceRouting::ModelNeed { ref part :>> owner=GambitAssuranceRelations::modelUse6; attribute :>> obligationId="IE-projection"; attribute :>> kind="restricted-projection"; attribute :>> subjectPath="dev/refactoring/modern-c/models/lean/ImageEnrollmentAst.lean"; attribute :>> subjectScope="Typed JSON binding IDs field kinds and full action roster"; attribute :>> premise="Conditional research; no native unload acceptance"; }
part source:GambitAssuranceRouting::ModelNeed { ref part :>> owner=GambitAssuranceRelations::modelUse6; attribute :>> obligationId="IE-source"; attribute :>> kind="source-refinement"; attribute :>> subjectPath="dev/refactoring/modern-c/image-membership-enrollment-design.org"; attribute :>> subjectScope="Complete native members permanent raw alias closure and all owner mapping OPEN"; attribute :>> premise="Conditional research; no native unload acceptance"; }
part platform:GambitAssuranceRouting::ModelNeed { ref part :>> owner=GambitAssuranceRelations::modelUse6; attribute :>> obligationId="IE-platform"; attribute :>> kind="native-memory-order"; attribute :>> subjectPath="dev/refactoring/modern-c/image-membership-enrollment-design.org"; attribute :>> subjectScope="C11 gate lifetime teardown and effective build-profile refinement OPEN"; attribute :>> premise="Conditional research; no native unload acceptance"; }

part def MemberRow { attribute key:String; attribute fields:String; attribute producer:String; attribute lifetime:String; attribute migration:String; }
part member0:MemberRow { attribute :>> key="module-header"; attribute :>> fields="version kind sizeof_module/global/VM/processor_struct name flags"; attribute :>> producer="generated module initializer and setup fixup"; attribute :>> lifetime="ABI and profile scope; name bytes may be image storage"; attribute :>> migration="Copy value metadata only with stable identity and source/profile digest"; }
part member1:MemberRow { attribute :>> key="globals"; attribute :>> fields="glotbl glocount supcount glo_names"; attribute :>> producer="generated resources -> setup fixup -> VM globals"; attribute :>> lifetime="Global bindings may contain procedures/native image-dependent objects"; attribute :>> migration="Map global binding roots and per-VM references; name table ownership explicit"; }
part member2:MemberRow { attribute :>> key="symbols-keys"; attribute :>> fields="symtbl symcount sym_names keytbl keycount key_names"; attribute :>> producer="generated resources -> interning/setup"; attribute :>> lifetime="Interned identities differ from original string/table allocation ownership"; attribute :>> migration="Do not assume interning detaches table or other image references"; }
part member3:MemberRow { attribute :>> key="entry-labels"; attribute :>> fields="lp lbltbl lblcount"; attribute :>> producer="generated hosts and setup label relocation"; attribute :>> lifetime="Executable host plus relocated labels used by call/return"; attribute :>> migration="Lease code separately from relocated metadata; zero labels do not erase setup hook"; }
part member4:MemberRow { attribute :>> key="frame-metadata"; attribute :>> fields="ofdtbl ofd_length"; attribute :>> producer="generated FrameSpec/OFD and setup relocation"; attribute :>> lifetime="GC continuation and restoration retain metadata dependencies"; attribute :>> migration="Bind PointId/FrameSpec generation and scanner/maintenance leases"; }
part member5:MemberRow { attribute :>> key="heap-tables"; attribute :>> fields="cnstbl cnscount subtbl subcount"; attribute :>> producer="generated constants/subtyped objects -> setup fixup"; attribute :>> lifetime="Objects or tables may retain procedure/native addresses"; attribute :>> migration="Trace semantic roots and physical allocation owners separately"; }
part member6:MemberRow { attribute :>> key="hooks-descriptor"; attribute :>> fields="setup_mod init_mod script_line next moddescr"; attribute :>> producer="generated native hooks -> setup -> program/registry consumers"; attribute :>> lifetime="Executable callbacks raw module wrapper descriptor aliases and chain links"; attribute :>> migration="Preserve ordered effects; replace raw reader with owned identity only on qualified route"; }
part member7:MemberRow { attribute :>> key="linkfile"; attribute :>> fields="version kind name sym_list key_list linkertbl mol flags"; attribute :>> producer="generated old/new linker tables -> mutating resolution"; attribute :>> lifetime="Linker graph and ordered edge effects may outlive discovery"; attribute :>> migration="Deduplicate ownership membership without deduplicating initialization semantics"; }
part member8:MemberRow { attribute :>> key="external-dependencies"; attribute :>> fields="exported callbacks converter release_fn platform dependency images"; attribute :>> producer="native FFI installation loader and cleanup adapters"; attribute :>> lifetime="Native registries can retain code independently of Scheme roots"; attribute :>> migration="Require explicit dependency/export owner mapping; absence is not derivable from module fields"; }

part source32:SourceRow { attribute :>> key="globals-fields"; attribute :>> path="vendor/gambit/include/gambit.h.in"; attribute :>> needle="___FAKEWORD *glotbl; int glocount; int supcount;"; attribute :>> obligation="Member inventory is field-complete for module/linkfile shape; native dependency closure still OPEN"; }
part source33:SourceRow { attribute :>> key="symbols-fields"; attribute :>> path="vendor/gambit/include/gambit.h.in"; attribute :>> needle="___FAKEWORD *symtbl; int symcount;"; attribute :>> obligation="Member inventory is field-complete for module/linkfile shape; native dependency closure still OPEN"; }
part source34:SourceRow { attribute :>> key="constant-fields"; attribute :>> path="vendor/gambit/include/gambit.h.in"; attribute :>> needle="___WORD *cnstbl; int cnscount;"; attribute :>> obligation="Member inventory is field-complete for module/linkfile shape; native dependency closure still OPEN"; }
part source35:SourceRow { attribute :>> key="subtyped-fields"; attribute :>> path="vendor/gambit/include/gambit.h.in"; attribute :>> needle="___FAKEWORD *subtbl; int subcount;"; attribute :>> obligation="Member inventory is field-complete for module/linkfile shape; native dependency closure still OPEN"; }
part source36:SourceRow { attribute :>> key="linkfile-fields"; attribute :>> path="vendor/gambit/include/gambit.h.in"; attribute :>> needle="___linkinfo *linkertbl;"; attribute :>> obligation="Member inventory is field-complete for module/linkfile shape; native dependency closure still OPEN"; }

part contract16:ContractRow { attribute :>> fromNode="close-authority"; attribute :>> toNode="local-detachment"; attribute :>> custody="No fresh public entry; accepted preclose debt must settle"; }
part contract17:ContractRow { attribute :>> fromNode="close-authority"; attribute :>> toNode="global-unload-permission"; attribute :>> custody="Closed immutable membership and owner manifest are mandatory guards"; }
}
