package GambitSubmissionUnits {
  private import ScalarValues::*;
  attribute scope:String="Enforce complete integration submission in the existing RevisionSubmission and shared ASCENT policy; support corrections have zero architecture progress and exact non-runtime paths. This mechanism does not implement runtime lifecycle result3.";
  attribute stage:String="Close complete historical model/reference source ownership and retain actual binding-read cost attribution. Runtime remains bd0991ed; this support unit adds0 progress and independent SMP stays1/12.";
  attribute formalDuty:String="Native SysML owns submission kinds, four results and their predecessor obligations. ASCENT combines unit coverage with all five gates. Python checks actual Git paths and exact durable receipt identities. Existing QNT temporal and Lean arithmetic duties are unchanged; no duplicate proof added. Raw Git and the truth of reviewed receipts remain explicit external boundaries.";
  attribute graph:String="sysml -> projection -> custody -> unit; unit -> ascent; gates -> ascent; ascent -> commit; unit -> complete; unit -> support; complete -> one_result; support -> zero_progress; raw_git -> external_boundary;";
  part submission:GambitCommitGates::SubmissionUnit {
    attribute :>> testModules="tests/test_evidence_views.py;tests/test_model_binding.py;tests/test_branch_evidence.py;tests/test_product_materialization.py;tests/test_revision_inventory.py;tests/test_revision_comment_policy.py";
    attribute :>> kind="support"; attribute :>> result=""; attribute :>> progressDelta=0;
    attribute :>> supportPaths="dev/modeling/models/sysml/commit-gates.sysml;dev/refactoring/modern-c/branch-checklist.org;dev/refactoring/modern-c/delivery-plan.org;dev/refactoring/modern-c/diagrams/post-delivery.d2;dev/refactoring/modern-c/index.org;dev/refactoring/modern-c/models/sysml/pending-cuts.sysml;dev/refactoring/modern-c/models/sysml/submission-units.sysml;dev/refactoring/modern-c/post-delivery.org;evidence/research/retained/modern-c/post-delivery/ascent-planning.json;evidence/research/retained/modern-c/post-delivery/binding-read-attribution.json;evidence/research/retained/modern-c/post-delivery/ci-observation.json;evidence/research/retained/modern-c/post-delivery/current-model-binding.json;evidence/research/retained/modern-c/post-delivery/evidence-query.json;evidence/research/retained/modern-c/post-delivery/historical-reference-transition.json;evidence/research/retained/modern-c/post-delivery/history-closure-prior.json;evidence/research/retained/modern-c/post-delivery/history-closure.json;evidence/research/retained/modern-c/post-delivery/model-observation.json;evidence/research/retained/modern-c/post-delivery/pending-inventory.json;evidence/research/retained/modern-c/post-delivery/performance-observation.json;evidence/research/retained/modern-c/post-delivery/qualification.json;evidence/research/retained/modern-c/post-delivery/source-review.json;evidence/research/retained/modern-c/post-delivery/submission/review.json;evidence/research/retained/modern-c/post-delivery/submission/validation.json;evidence/scenarios/modern-c/request-product.view.json;pyproject.toml;src/gambit_smp/branch_evidence.py;src/gambit_smp/evidence_views.py;src/gambit_smp/model_binding.py;src/gambit_smp/product_materialization.py;src/gambit_smp/revision_inventory.py;src/gambit_smp/source_identity.py;tests/fixtures/historical-view-pointers.json;tests/historical_view.py;tests/test_branch_evidence.py;tests/test_evidence_views.py;tests/test_model_binding.py;tests/test_product_materialization.py;tests/test_revision_comment_policy.py;tests/test_revision_inventory.py;uv.lock";
  }
  part def Need { ref part gate:GambitCommitGates::Gate; attribute id:String; attribute method:String; attribute artifact:String; attribute scope:String; }
  part tests:Need { ref part :>> gate=GambitCommitGates::tests; attribute :>> id="UNIT-TESTS"; attribute :>> method="native"; attribute :>> artifact="evidence/research/retained/modern-c/post-delivery/submission/validation.json"; attribute :>> scope="All six declared source/test consumers run63 tests with no failures/errors/skips; twelve unchanged published source controls are preserved. Current216-field native SDK/CLI and recorded-case/refusal checks bind the whole source epoch. No additional runtime C is admitted."; }
  part learning:Need { ref part :>> gate=GambitCommitGates::learning; attribute :>> id="UNIT-LEARNING"; attribute :>> method="source-analysis"; attribute :>> artifact="dev/refactoring/modern-c/post-delivery.org"; attribute :>> scope="Learn from the mixed-epoch failure: current files cannot redefine historical proof premises. Shared typed reconstruction and strict recorded-case consumers replace cached expression and mutable-path authority; actual hot-path counts expose a remaining C ownership-placement cost."; }
  part process:Need { ref part :>> gate=GambitCommitGates::process; attribute :>> id="UNIT-PROCESS"; attribute :>> method="source-analysis"; attribute :>> artifact="dev/refactoring/modern-c/post-delivery.org"; attribute :>> scope="Close the historical source binding and current/frozen consumer contract as one support REV. Keep the full92-path runtime review queue and twelve-family native plan distinct; add0 architecture progress and keep SMP1/12."; }
  part models:Need { ref part :>> gate=GambitCommitGates::models; attribute :>> id="UNIT-MODELS"; attribute :>> method="source-refinement"; attribute :>> artifact="evidence/research/retained/modern-c/post-delivery/submission/review.json"; attribute :>> scope="Real SysML projects the programme obligation closure, not a Python duplicate list. ASCENT must reject missing unit, missing current/predecessor/component evidence, stale identities and support promotion."; }
  part questions:Need { ref part :>> gate=GambitCommitGates::questions; attribute :>> id="UNIT-QUESTIONS"; attribute :>> method="source-analysis"; attribute :>> artifact="dev/refactoring/modern-c/post-delivery.org"; attribute :>> scope="Which exact source epoch supports each claim? Why do missing families and gates still refuse? Which TLS/page work is proven and which percentage attribution remains open? What complete C binding-read activation retires repeated proof while preserving roots and multi-shot control?"; }
}
