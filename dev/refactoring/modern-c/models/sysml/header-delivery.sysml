package GambitHeaderDelivery {
  private import ScalarValues::*;
  attribute scope:String="Complete lossless header organization: source, generation, installation, every direct template consumer; no runtime semantics or SMP progress.";
  attribute stage:String="header-organization";
  attribute formalDuty:String="OpenSysML owns the source partition and five-gate scope; ASCENT joins exact source/profile/evidence. Byte equality is representation refinement, not a concurrent algorithm or a new algebraic law; QNT and Lean add no duplicate proof.";
  part submission:GambitCommitGates::SubmissionUnit {
    attribute :>> kind="organization";
    attribute :>> result="header-organization";
    attribute :>> progressDelta=0;
    attribute :>> supportPaths="";
  }
  part def Need { ref part gate:GambitCommitGates::Gate; attribute id:String; attribute method:String; attribute artifact:String; attribute scope:String; }
  part bytes:Need { ref part :>> gate=GambitCommitGates::tests; attribute :>> id="H-BYTES"; attribute :>> method="native"; attribute :>> artifact="evidence/research/retained/modern-c/header-organization/native.json"; attribute :>> scope="All ordered payloads reconstruct the published baseline exactly; the manifest contains no payload."; }
  part configuration:Need { ref part :>> gate=GambitCommitGates::tests; attribute :>> id="H-CONFIG"; attribute :>> method="native"; attribute :>> artifact="evidence/research/retained/modern-c/header-organization/native.json"; attribute :>> scope="Existing configure/config.status and Make publish byte-identical public headers with the original profile."; }
  part consumers:Need { ref part :>> gate=GambitCommitGates::tests; attribute :>> id="H-CONSUMERS"; attribute :>> method="native"; attribute :>> artifact="evidence/research/retained/modern-c/header-organization/native.json"; attribute :>> scope="Installed public header, original frame contract and real map multi-shot continuation/GC consumers."; }
  part dependencies:Need { ref part :>> gate=GambitCommitGates::tests; attribute :>> id="H-DEPENDENCIES"; attribute :>> method="native"; attribute :>> artifact="evidence/research/retained/modern-c/header-organization/native.json"; attribute :>> scope="Every module is a Make prerequisite and distribution input; no-change and changed-fragment paths are distinguished."; }
  part templateConsumers:Need { ref part :>> gate=GambitCommitGates::tests; attribute :>> id="H-TEMPLATE-CONSUMERS"; attribute :>> method="native"; attribute :>> artifact="evidence/research/retained/modern-c/header-organization/native.json"; attribute :>> scope="Register/version writers, raw configure probe and all Windows renderers use the canonical partition."; }
  part learning:Need { ref part :>> gate=GambitCommitGates::learning; attribute :>> id="H-LESSON"; attribute :>> method="source-analysis"; attribute :>> artifact="dev/refactoring/modern-c/header-delivery.org"; attribute :>> scope="One source authority, explicit ownership; no runtime acceleration claim."; }
  part processNeed:Need { ref part :>> gate=GambitCommitGates::process; attribute :>> id="H-PROCESS"; attribute :>> method="source-analysis"; attribute :>> artifact="dev/refactoring/modern-c/header-delivery.org"; attribute :>> scope="Independent structural delivery; preserve unrelated Changes and separate SMP progress."; }
  part models:Need { ref part :>> gate=GambitCommitGates::models; attribute :>> id="H-MODELS"; attribute :>> method="native"; attribute :>> artifact="evidence/research/retained/modern-c/header-organization/native.json"; attribute :>> scope="Native OpenSysML SDK projection drives ASCENT, including stale/missing/wrong-source controls."; }
  part questions:Need { ref part :>> gate=GambitCommitGates::questions; attribute :>> id="H-QUESTIONS"; attribute :>> method="source-analysis"; attribute :>> artifact="dev/refactoring/modern-c/header-delivery.org"; attribute :>> scope="C portability, frames, tail calls and multi-shot continuations retain identical representation; list counterexamples and costs."; }
}
