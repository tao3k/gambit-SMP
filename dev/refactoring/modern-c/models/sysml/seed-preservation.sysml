package GambitSeedPreservation {
 private import ScalarValues::*;
 attribute scope:String="Completed seed output custody, not a new builder. Only a successful declared seed consuming the same configured-source ancestry may retire its old snapshots after independent completed preservation. Old-descriptor current-byte checks stay strict.";
 attribute stage:String="Support correction of observed CI STALE; no runtime/integration increment. Architecture3/4 and SMP1/12 unchanged; hosted build and macOS pair remain separate.";
 attribute formalDuty:String="Existing models/build/incremental_build.qnt owns scheduling and models/build/IncrementalBuild.lean owns conditional input algebra. Neither proves filesystem/hash/host behavior; this cut supplies source refinement and real filesystem counterexamples without duplicating models.";
 attribute existingOwner:String="dev/refactoring/modern-c/models/sysml/bootstrap-artifact-custody.sysml#retained";
 attribute sourceProducer:String="src/gambit_smp/bootstrap_artifacts.py#freeze";
 attribute sourceConsumer:String="src/gambit_smp/recipes.py#preserved_successor";
 attribute snapshotRule:String="Historical source snapshot RETAINED only with verified old custody, successful seed declared-input ancestry, completed record bound to saved identity, both current full identities equal, disjoint paths and no same-file leaf aliases";
 attribute borrowRule:String="RETAINED does not satisfy old current-byte artifact consumption; missing, failed, unknown, modified or aliased transfer remains refused";
 attribute diagram:String="direction: right\ninput: Declared configured source\nbuild: Same owned workspace after seed build\nsaved: Preserved completed seed\nproof: Input ancestry + receipt + full identities + independent inodes\npast: Earlier snapshot retained\nreuse: Old descriptor reuse rejected\nready: Saved runtime available\nrefuse: Missing or changed proof rejected\ninput -> build: admitted mutation\nbuild -> saved: existing freeze\nbuild -> proof\nsaved -> proof\nproof -> past: verified\npast -> reuse: no current-byte authority\nsaved -> ready: current identity checked\nproof -> refuse: unknown or mismatch\n";
 part def Need { attribute id:String; ref part gate:GambitCommitGates::Gate; attribute method:String; attribute artifact:String; attribute scope:String; }
 part tests:Need { attribute :>> id="SEED-TESTS"; ref part :>> gate=GambitCommitGates::tests; attribute :>> method="native"; attribute :>> artifact="evidence/research/retained/modern-c/ci-handoff/receipt.json"; attribute :>> scope="Observed seed lifecycle refinement only; no old failed run or whole runtime/CI admission"; }
 part learning:Need { attribute :>> id="SEED-LEARNING"; ref part :>> gate=GambitCommitGates::learning; attribute :>> method="source-refinement"; attribute :>> artifact="evidence/research/retained/modern-c/ci-handoff/receipt.json"; attribute :>> scope="Observed seed lifecycle refinement only; no old failed run or whole runtime/CI admission"; }
 part process:Need { attribute :>> id="SEED-PROCESS"; ref part :>> gate=GambitCommitGates::process; attribute :>> method="source-refinement"; attribute :>> artifact="evidence/research/retained/modern-c/ci-handoff/receipt.json"; attribute :>> scope="Observed seed lifecycle refinement only; no old failed run or whole runtime/CI admission"; }
 part models:Need { attribute :>> id="SEED-MODELS"; ref part :>> gate=GambitCommitGates::models; attribute :>> method="source-refinement"; attribute :>> artifact="evidence/research/retained/modern-c/ci-handoff/receipt.json"; attribute :>> scope="Observed seed lifecycle refinement only; no old failed run or whole runtime/CI admission"; }
 part questions:Need { attribute :>> id="SEED-QUESTIONS"; ref part :>> gate=GambitCommitGates::questions; attribute :>> method="source-refinement"; attribute :>> artifact="evidence/research/retained/modern-c/ci-handoff/receipt.json"; attribute :>> scope="Observed seed lifecycle refinement only; no old failed run or whole runtime/CI admission"; }
 part submission:GambitCommitGates::SubmissionUnit { attribute :>> kind="support"; attribute :>> result=""; attribute :>> progressDelta=0; attribute :>> supportPaths="src/gambit_smp/recipes.py;src/gambit_smp/bootstrap_artifacts.py;tests/test_bootstrap_artifacts.py;dev/refactoring/modern-c/models/sysml/seed-preservation.sysml;dev/refactoring/modern-c/seed-preservation.org;dev/refactoring/modern-c/branch-checklist.org;dev/refactoring/modern-c/diagrams/seed-preservation.d2;dev/refactoring/modern-c/diagrams/seed-preservation.svg;evidence/research/retained/modern-c/ci-handoff/receipt.json;evidence/research/retained/modern-c/ci-handoff/root-cause.json"; attribute :>> testModules="tests/test_bootstrap_artifacts.py"; }
}
