package GambitFrameSealStartRetire { private import ScalarValues::*;
part def SourceRow { attribute key:String; attribute path:String; attribute needle:String; attribute obligation:String; }
part source0:SourceRow { attribute :>> key="constructor"; attribute :>> path="vendor/gambit/gsc/_t-c-3.scm"; attribute :>> needle="(vector 'frame-spec kind fs actual-fs link gc-map out-of-line?)"; attribute :>> obligation="Fresh mutable vector; validation is not alias closure"; }
part source1:SourceRow { attribute :>> key="validation"; attribute :>> path="vendor/gambit/gsc/_t-c-3.scm"; attribute :>> needle="(< gc-map (expt 2 actual-fs))"; attribute :>> obligation="Revalidate exact kind size effective layout link and gc-map under frozen ABI"; }
part source2:SourceRow { attribute :>> key="chunks"; attribute :>> path="vendor/gambit/gsc/_t-c-3.scm"; attribute :>> needle="(targ-frame-spec-chunks spec)"; attribute :>> obligation="Emitter-time chunk generation also needs stable view"; }
part source3:SourceRow { attribute :>> key="return-wrappers"; attribute :>> path="vendor/gambit/gsc/_t-c-2.scm"; attribute :>> needle="(targ-make-frame-spec 'internal fs link gc-map)"; attribute :>> obligation="Three wrappers create normal task internal specs"; }
part source4:SourceRow { attribute :>> key="replace-class"; attribute :>> path="vendor/gambit/gsc/_t-c-2.scm"; attribute :>> needle="(vector-set! lbl-struct 2 class)"; attribute :>> obligation="Class and info writes are a logical pair, not atomic publish"; }
part source5:SourceRow { attribute :>> key="replace-payload"; attribute :>> path="vendor/gambit/gsc/_t-c-2.scm"; attribute :>> needle="(vector-set! lbl-struct 3 info)"; attribute :>> obligation="Replaces FrameSpec reference rather than mutating its scalar fields"; }
part source6:SourceRow { attribute :>> key="code-alias"; attribute :>> path="vendor/gambit/gsc/_t-c-2.scm"; attribute :>> needle="(targ-emit (cons 'label x))"; attribute :>> obligation="Code stream holds same canonical label as registry"; }
part source7:SourceRow { attribute :>> key="table-alias"; attribute :>> path="vendor/gambit/gsc/_t-c-2.scm"; attribute :>> needle="(queue-put! targ-proc-lbl-tbl (cons n y))"; attribute :>> obligation="Canonical label identity returned on repeated lookup"; }
part source8:SourceRow { attribute :>> key="order-alias"; attribute :>> path="vendor/gambit/gsc/_t-c-2.scm"; attribute :>> needle="(queue-put! targ-proc-lbl-tbl-ord lbl-struct)"; attribute :>> obligation="Ordered queue preserves label alias"; }
part source9:SourceRow { attribute :>> key="plan-alias"; attribute :>> path="vendor/gambit/gsc/_t-c-2.scm"; attribute :>> needle="(reverse val-lbls)"; attribute :>> obligation="Reversing list copies spine not label records"; }
part source10:SourceRow { attribute :>> key="plan-publish"; attribute :>> path="vendor/gambit/gsc/_t-c-2.scm"; attribute :>> needle="(set-car! p"; attribute :>> obligation="Procedure plan installed after scans but before goto numbering ends"; }
part source11:SourceRow { attribute :>> key="number-cell"; attribute :>> path="vendor/gambit/gsc/_t-c-2.scm"; attribute :>> needle="(targ-cell-set! (targ-lbl-num x) i)"; attribute :>> obligation="Seal must wait for loop3 goto numbering too"; }
part source12:SourceRow { attribute :>> key="ifd-reader"; attribute :>> path="vendor/gambit/gsc/_t-c-1.scm"; attribute :>> needle="(targ-frame-spec-stored-fs info)"; attribute :>> obligation="Descriptor pass reads mutable payload"; }
part source13:SourceRow { attribute :>> key="ofd-reader"; attribute :>> path="vendor/gambit/gsc/_t-c-1.scm"; attribute :>> needle="(targ-frame-spec-chunks info)"; attribute :>> obligation="OFD body pass must match count and IFD pass"; }
part source14:SourceRow { attribute :>> key="ofd-count"; attribute :>> path="vendor/gambit/gsc/_t-c-1.scm"; attribute :>> needle="(define (targ-get-ofd-count objs)"; attribute :>> obligation="Separate count traversal can disagree after mutation"; }
part source15:SourceRow { attribute :>> key="source-write"; attribute :>> path="vendor/gambit/lib/setup.c"; attribute :>> needle="source->thunk = thunk;"; attribute :>> obligation="Publish before any allocation callback safe point; reentry refused"; }
part source16:SourceRow { attribute :>> key="source-queue"; attribute :>> path="vendor/gambit/lib/setup.c"; attribute :>> needle="___RESIZE_SOURCE_WRITING, ___RESIZE_SOURCE_QUEUED"; attribute :>> obligation="Root publication precedes token enqueue"; }
part source17:SourceRow { attribute :>> key="token-check"; attribute :>> path="vendor/gambit/lib/setup.c"; attribute :>> needle="source->serial != token / ___MAX_PROCESSORS"; attribute :>> obligation="Serial and origin bind selected request"; }
part source18:SourceRow { attribute :>> key="reload"; attribute :>> path="vendor/gambit/lib/setup.c"; attribute :>> needle="(___ps, source->thunk, sop_ptr->arg[1]);"; attribute :>> obligation="Selected operation reloads GC-updated source slot"; }
part source19:SourceRow { attribute :>> key="ledger-publish"; attribute :>> path="vendor/gambit/lib/setup.c"; attribute :>> needle="r->thunk = thunk;"; attribute :>> obligation="Old participant barrier precedes possible GC"; }
part source20:SourceRow { attribute :>> key="ledger-clear"; attribute :>> path="vendor/gambit/lib/setup.c"; attribute :>> needle="r->thunk = ___FAL;"; attribute :>> obligation="Clear only outside retained phase; successor contexts can still own roots"; }
part source21:SourceRow { attribute :>> key="source-ack"; attribute :>> path="vendor/gambit/lib/setup.c"; attribute :>> needle="source->thunk = ___FAL;"; attribute :>> obligation="Only CONSUMED CAS winner clears then publishes IDLE"; }
part source22:SourceRow { attribute :>> key="source-unknown"; attribute :>> path="vendor/gambit/lib/setup.c"; attribute :>> needle="___RESIZE_SOURCE_QUEUED, ___RESIZE_SOURCE_RETAINED"; attribute :>> obligation="Unknown keeps thunk serial and exclusion of slot reuse"; }
part source23:SourceRow { attribute :>> key="root-scan"; attribute :>> path="vendor/gambit/lib/mem.c"; attribute :>> needle="mark_array (work, &___vms->resize_requests[i].thunk, 1);"; attribute :>> obligation="All MAX_PROCESSORS slots including retained absent origins"; }
part source24:SourceRow { attribute :>> key="ledger-scan"; attribute :>> path="vendor/gambit/lib/mem.c"; attribute :>> needle="mark_array (work, &___vms->resize.thunk, 1);"; attribute :>> obligation="Deduplicate transitive objects across ledger source and context aliases"; }
part source25:SourceRow { attribute :>> key="retire-guard"; attribute :>> path="vendor/gambit/lib/mem.c"; attribute :>> needle="No C stack or"; attribute :>> obligation="Current shrink refuses nonidle origin slot"; }
part source26:SourceRow { attribute :>> key="cleanup-guard"; attribute :>> path="vendor/gambit/lib/setup.c"; attribute :>> needle="return; /* source-root ownership outlives an interrupted C activation */"; attribute :>> obligation="Cleanup refusal is custody not a drain/liveness proof"; }
part source27:SourceRow { attribute :>> key="setup-root"; attribute :>> path="vendor/gambit/lib/setup.c"; attribute :>> needle="___vms->resize_requests[i].thunk = ___FAL;"; attribute :>> obligation="Exclusive pre-borrow setup; not an in-round writer"; }
part source28:SourceRow { attribute :>> key="serial"; attribute :>> path="vendor/gambit/include/gambit.h.in"; attribute :>> needle="___resize_request_root resize_requests[___MAX_PROCESSORS];"; attribute :>> obligation="VM-owned stable storage; generation/serial overflow must refuse reuse"; }
part source29:SourceRow { attribute :>> key="cas-family"; attribute :>> path="vendor/gambit/include/gambit.h.in"; attribute :>> needle="__sync_val_compare_and_swap(p,oldval,newval)"; attribute :>> obligation="Multiple macro backends; volatile alone establishes no C11 happens-before"; }
part source30:SourceRow { attribute :>> key="startup-publish"; attribute :>> path="vendor/gambit/lib/setup.c"; attribute :>> needle="ps->context->startup_thunk = r->thunk;"; attribute :>> obligation="Successor context keeps exact thunk before native start"; }
part source31:SourceRow { attribute :>> key="startup-scan"; attribute :>> path="vendor/gambit/lib/mem.c"; attribute :>> needle="mark_array (work, &context->startup_thunk, 1);"; attribute :>> obligation="Context root scanning must remain until successful downstream detach"; }
part source32:SourceRow { attribute :>> key="target-registry"; attribute :>> path="vendor/gambit/gsc/_back.scm"; attribute :>> needle="(define targets-alist"; attribute :>> obligation="Registry holds mutable target vectors and executable provider hooks"; }
part source33:SourceRow { attribute :>> key="target-replace"; attribute :>> path="vendor/gambit/gsc/_back.scm"; attribute :>> needle="(set-cdr! x targ)"; attribute :>> obligation="Provider replacement writer; not a FrameSpec field mutation"; }
part source34:SourceRow { attribute :>> key="target-hooks"; attribute :>> path="vendor/gambit/gsc/_back.scm"; attribute :>> needle="(set! target.dump"; attribute :>> obligation="Selected global hook aliases mutable target table"; }
part source35:SourceRow { attribute :>> key="frontend-cleanup"; attribute :>> path="vendor/gambit/gsc/_front.scm"; attribute :>> needle="(target-unselect!)"; attribute :>> obligation="Sequential cleanup is not a multi-shot dynamic guard"; }
part source36:SourceRow { attribute :>> key="backend-entry"; attribute :>> path="vendor/gambit/gsc/_front.scm"; attribute :>> needle="(target.dump"; attribute :>> obligation="Real handoff from module procs c-intf descriptor to target"; }
part source37:SourceRow { attribute :>> key="error-capture"; attribute :>> path="vendor/gambit/gsc/_utils.scm"; attribute :>> needle="(set! throw-to-exception-handler cont)"; attribute :>> obligation="Actual compiler continuation captured in mutable global"; }
part source38:SourceRow { attribute :>> key="error-return"; attribute :>> path="vendor/gambit/gsc/_utils.scm"; attribute :>> needle="(set! throw-to-exception-handler old-exception-handler)"; attribute :>> obligation="Restore only after proc returns through this lexical path"; }
part source39:SourceRow { attribute :>> key="error-abort"; attribute :>> path="vendor/gambit/gsc/_utils.scm"; attribute :>> needle="(throw-to-exception-handler #f)"; attribute :>> obligation="Real nonlocal compiler abort path"; }
part source40:SourceRow { attribute :>> key="macro-callback"; attribute :>> path="vendor/gambit/gsc/_ptree1.scm"; attribute :>> needle="(expander source)"; attribute :>> obligation="Actual arbitrary Scheme callback; normally before frame emission"; }
part source41:SourceRow { attribute :>> key="macro-eval"; attribute :>> path="vendor/gambit/gsc/_ptree1.scm"; attribute :>> needle="(scheme-global-eval (source->expression proc)"; attribute :>> obligation="Macro expander constructed by runtime evaluation"; }
part source42:SourceRow { attribute :>> key="ffi-builder"; attribute :>> path="vendor/gambit/gsc/_ptree2.scm"; attribute :>> needle="(define (build-c-lambda"; attribute :>> obligation="Generates native call code; not evidence it executes during the same compilation"; }
part source43:SourceRow { attribute :>> key="ffi-scmobj-result"; attribute :>> path="vendor/gambit/gsc/_ptree2.scm"; attribute :>> needle="\"BEGIN_CFUN_SCMOBJ(\""; attribute :>> obligation="Direct Scheme-object result mode needs separate native borrow contract"; }
part source44:SourceRow { attribute :>> key="ffi-c-interface"; attribute :>> path="vendor/gambit/gsc/_t-c-1.scm"; attribute :>> needle="(c-intf-procs-set! c-intf '())"; attribute :>> obligation="Backend consumes and clears mutable FFI interface container"; }
part source45:SourceRow { attribute :>> key="port-global"; attribute :>> path="vendor/gambit/gsc/_t-c-1.scm"; attribute :>> needle="(set! targ-port (open-output-file-preserving-case filename))"; attribute :>> obligation="Mutable output and line state belongs to emission session"; }
part source46:SourceRow { attribute :>> key="port-write"; attribute :>> path="vendor/gambit/gsc/_t-c-1.scm"; attribute :>> needle="(display x targ-port)"; attribute :>> obligation="Potential callback/reentry boundary not a proved capturing port witness"; }
part source47:SourceRow { attribute :>> key="marker-entry"; attribute :>> path="vendor/gambit/include/gambit.h.in"; attribute :>> needle="#define ___BEGIN_SFUN_SCMOBJ(proc)"; attribute :>> obligation="Native Scheme callback wrapper allocates marker and calls Scheme"; }
part source48:SourceRow { attribute :>> key="still-release"; attribute :>> path="vendor/gambit/lib/mem.c"; attribute :>> needle="___still_obj_refcount_dec (obj);"; attribute :>> obligation="Release_scmobj refcount is not an old-code unload lease"; }
part source49:SourceRow { attribute :>> key="loader-failed-load"; attribute :>> path="vendor/gambit/lib/os_dyn.c"; attribute :>> needle="dlclose (p->descr);"; attribute :>> obligation="Failed-load cleanup distinct from retirement of a published module"; }
part source50:SourceRow { attribute :>> key="loader-cleanup"; attribute :>> path="vendor/gambit/lib/os_dyn.c"; attribute :>> needle="___HIDDEN void cleanup_dynamic_load"; attribute :>> obligation="Global dynamic-load list cleanup, not per-generation descriptor retirement"; }
part source51:SourceRow { attribute :>> key="loader-entry"; attribute :>> path="vendor/gambit/lib/os_dyn.c"; attribute :>> needle="void ___cleanup_dyn_module"; attribute :>> obligation="Global cleanup wrapper does not supply captured-frame detachment receipt"; }
part source52:SourceRow { attribute :>> key="loader-cleanup-callers"; attribute :>> path="vendor/gambit/lib/os_setup.c"; attribute :>> needle="___cleanup_dyn_module ();"; attribute :>> obligation="Two direct callers: setup failure unwind and global cleanup_os; not per-generation GC retire"; }
part source53:SourceRow { attribute :>> key="global-loader-owner"; attribute :>> path="vendor/gambit/lib/os_dyn.c"; attribute :>> needle="___dyn_module ___dyn_mod ="; attribute :>> obligation="Process-global loader owner requires all-VM and native detachment before unload"; }
part def InventoryRow { attribute key:String; attribute path:String; attribute pattern:String; attribute count:String; attribute scope:String; }
part inventory0:InventoryRow { attribute :>> key="typed-return-constructors"; attribute :>> path="vendor/gambit/gsc/_t-c-2.scm"; attribute :>> pattern="\\(targ-make-frame-spec '(?:normal|task|internal)"; attribute :>> count="3"; attribute :>> scope="Bounded lexical snapshot only; aliases unsafe FFI and external extensions not excluded"; }
part inventory1:InventoryRow { attribute :>> key="label-payload-stores"; attribute :>> path="vendor/gambit/gsc/_t-c-2.scm"; attribute :>> pattern="\\(vector-set! lbl-struct [23] "; attribute :>> count="2"; attribute :>> scope="Bounded lexical snapshot only; aliases unsafe FFI and external extensions not excluded"; }
part inventory2:InventoryRow { attribute :>> key="handler-global-stores"; attribute :>> path="vendor/gambit/gsc/_utils.scm"; attribute :>> pattern="\\(set! throw-to-exception-handler "; attribute :>> count="2"; attribute :>> scope="Bounded lexical snapshot only; aliases unsafe FFI and external extensions not excluded"; }
part inventory3:InventoryRow { attribute :>> key="c-intf-drains"; attribute :>> path="vendor/gambit/gsc/_t-c-1.scm"; attribute :>> pattern="\\(c-intf-(?:decls|procs|inits|objs)-set! c-intf '\\(\\)\\)"; attribute :>> count="4"; attribute :>> scope="Bounded lexical snapshot only; aliases unsafe FFI and external extensions not excluded"; }
part inventory4:InventoryRow { attribute :>> key="native-wrapper-builder"; attribute :>> path="vendor/gambit/gsc/_ptree2.scm"; attribute :>> pattern="\\(define \\(build-c-lambda "; attribute :>> count="1"; attribute :>> scope="Bounded lexical snapshot only; aliases unsafe FFI and external extensions not excluded"; }
part inventory5:InventoryRow { attribute :>> key="native-unload-sites"; attribute :>> path="vendor/gambit/lib/os_dyn.c"; attribute :>> pattern="\\bdlclose \\(p->descr\\);"; attribute :>> count="2"; attribute :>> scope="Bounded lexical snapshot only; aliases unsafe FFI and external extensions not excluded"; }
part inventory6:InventoryRow { attribute :>> key="native-cleanup-callers"; attribute :>> path="vendor/gambit/lib/os_setup.c"; attribute :>> pattern="___cleanup_dyn_module \\(\\);"; attribute :>> count="2"; attribute :>> scope="Bounded lexical snapshot only; aliases unsafe FFI and external extensions not excluded"; }
part inventory7:InventoryRow { attribute :>> key="direct-named-spec-setters"; attribute :>> path="vendor/gambit/gsc/_t-c-3.scm"; attribute :>> pattern="\\(vector-set! spec "; attribute :>> count="0"; attribute :>> scope="Bounded lexical snapshot only; aliases unsafe FFI and external extensions not excluded"; }
part def AliasRow { attribute key:String; attribute writer:String; attribute custody:String; attribute gap:String; }
part alias0:AliasRow { attribute :>> key="constructors"; attribute :>> writer="Three normal/task/internal wrappers"; attribute :>> custody="Fresh seven-field vector; exact scalar checks"; attribute :>> gap="Bounded direct writers inventoried; arbitrary Scheme vector access is outside proof"; }
part alias1:AliasRow { attribute :>> key="payload-replacement"; attribute :>> writer="targ-add-label"; attribute :>> custody="Class/info pair mutates canonical label record"; attribute :>> gap="Pair must be private or owner-excluded across both stores"; }
part alias2:AliasRow { attribute :>> key="containers"; attribute :>> writer="label table ordered queue code val-lbls"; attribute :>> custody="Shared label vector and number cell identities"; attribute :>> gap="Copy all mutable paths with relocation map; list reverse alone insufficient"; }
part alias3:AliasRow { attribute :>> key="numbering"; attribute :>> writer="targ-scan-procedure loop2 and loop3"; attribute :>> custody="Set-car plan install precedes final goto numbering"; attribute :>> gap="Seal only after complete procedure scan and module queue drain"; }
part alias4:AliasRow { attribute :>> key="target-profile"; attribute :>> writer="target-add target-select begin!"; attribute :>> custody="Registry vector hooks selected globals register/layout parameters"; attribute :>> gap="Version and isolate entire target/provider environment"; }
part alias5:AliasRow { attribute :>> key="interface"; attribute :>> writer="targ-dump c-intf-* setters"; attribute :>> custody="Four destructive drains of interface payload"; attribute :>> gap="Own c-intf and c-decls queue; declarations are emitted data, not executed callbacks"; }
part alias6:AliasRow { attribute :>> key="ports"; attribute :>> writer="targ-port info-port source-location state"; attribute :>> custody="Output calls and mutable line state"; attribute :>> gap="Private output transaction; no concrete captured-output callback witness claimed"; }
part alias7:AliasRow { attribute :>> key="compiler-continuation"; attribute :>> writer="with-exception-handling compiler-abort"; attribute :>> custody="Saved continuation and old handler global"; attribute :>> gap="A captured compiler continuation is not a durable once-only owner token"; }
part alias8:AliasRow { attribute :>> key="macro-continuation"; attribute :>> writer="scheme-global-eval macro-expand"; attribute :>> custody="Arbitrary expander code can capture execution"; attribute :>> gap="Normally precedes FrameSpec creation; later resumption can reexecute pipeline; alias access unresolved"; }
part alias9:AliasRow { attribute :>> key="native-boundary"; attribute :>> writer="c-lambda c-define scheme-object SFUN"; attribute :>> custody="Raw Scheme object and callbacks are ABI capabilities"; attribute :>> gap="No direct FrameSpec -> FFI argument found; untracked raw export cannot be certified"; }
part alias10:AliasRow { attribute :>> key="runtime-descriptor"; attribute :>> writer="frame return point closure module handle"; attribute :>> custody="Code/OFD aliases survive source-slot ACK"; attribute :>> gap="Detach objects code readers maintenance native and pending roots independently"; }
part alias11:AliasRow { attribute :>> key="scope-retirement"; attribute :>> writer="global loader cleanup list"; attribute :>> custody="dlclose and list free are global cleanup actions"; attribute :>> gap="Not an existing hot-reload or per-module GC reclamation protocol"; }
part def ClaimRow { attribute key:String; attribute mechanism:String; attribute condition:String; attribute result:String; attribute gap:String; }
part claim0:ClaimRow { attribute :>> key="closure"; attribute :>> mechanism="A registered writer/capability domain bounds the trusted closure"; attribute :>> condition="Entire compiler globals cells targets hooks and output state owned"; attribute :>> result="Restricted private seal can be specified; full unrestricted Scheme closure remains OPEN"; attribute :>> gap="No universal alias theorem from lexical absence"; }
part claim1:ClaimRow { attribute :>> key="continuation"; attribute :>> mechanism="Suspend retains construction identity; resume rechecks live owner"; attribute :>> condition="Generation and phase unchanged; published views never reopen"; attribute :>> result="Stale resume denied in model; legitimate pure fork needs a separate private session"; attribute :>> gap="Rejecting arbitrary legacy resumption is a service restriction, not full semantic equivalence"; }
part claim2:ClaimRow { attribute :>> key="ffi"; attribute :>> mechanism="Immutable native view or copied bytes behind registered lease"; attribute :>> condition="No raw mutable vector or untracked C storage escapes"; attribute :>> result="Read-only borrow can be pinned; unknown outcome blocks retire"; attribute :>> gap="FFI ABI compatibility does not confer immutability or descriptor liveness"; }
part claim3:ClaimRow { attribute :>> key="start-revoke"; attribute :>> mechanism="Single generation/phase authority arbitrates competing CAS"; attribute :>> condition="Payload/descriptor already rooted and stable control record remains live"; attribute :>> result="Revoke first blocks start; start first preserves copy grant until finish"; attribute :>> gap="C11 weak-memory translation and actual stable guard integration remain OPEN"; }
part claim4:ClaimRow { attribute :>> key="retire"; attribute :>> mechanism="Close new admissions then settle all old users"; attribute :>> condition="No active copy issued plan native root frame maintenance or observer debt"; attribute :>> result="Finite model rejects premature release and keeps unknown debt"; attribute :>> gap="Arbitrary multi-shot aliases native raw pointers and global shutdown ordering unclosed"; }
part claim5:ClaimRow { attribute :>> key="global-unload"; attribute :>> mechanism="Local VM detachment feeds process-global module owner"; attribute :>> condition="Other VM native and loader owners all detached and global admission closed"; attribute :>> result="Local reclaimed model state alone does not authorize dlclose"; attribute :>> gap="Actual all-VM descriptor ownership inventory and C11 composition OPEN"; }
part def MemoryRow { attribute key:String; attribute publication:String; attribute consumer:String; attribute gap:String; }
part memory0:MemoryRow { attribute :>> key="publish"; attribute :>> publication="Ordinary immutable payload writes before release ISSUED publication"; attribute :>> consumer="Successful acquire/acq_rel starter observes exact generation; control storage stable"; attribute :>> gap="No proof of current macro backend or concrete Scheme root adapter"; }
part memory1:MemoryRow { attribute :>> key="CAS"; attribute :>> publication="ISSUED -> STARTED and ISSUED -> REVOKED compete on same atomic object"; attribute :>> consumer="Strong acq_rel success; acquire failure; revalidate expected whole generation/phase"; attribute :>> gap="A load/fence pair or two unrelated flags do not linearize both decisions"; }
part memory2:MemoryRow { attribute :>> key="credit"; attribute :>> publication="Close admissions and credit reservation serialize under same authority"; attribute :>> consumer="Credit return acq_rel; acquire final drain check; unknown guard stays retained"; attribute :>> gap="Per-user exact-once and physical counter encoding remain C11 refinement obligations"; }
part memory3:MemoryRow { attribute :>> key="ABA"; attribute :>> publication="Generation exhaustion refuses reuse; stable VM control outlives readers"; attribute :>> consumer="Observer lease acquired before dereferencing descriptor payload"; attribute :>> gap="Acquire alone does not keep freed memory alive; no unqualified hazard-pointer implementation"; }
part memory4:MemoryRow { attribute :>> key="GC"; attribute :>> publication="Rooted handles survive safepoints; scanner owns relocation writes"; attribute :>> consumer="Reload movable values after GC; immutable semantic data is not immovable address"; attribute :>> gap="Native/raw object alias inventory not complete"; }
part def GainRow { attribute key:String; attribute avoided:String; attribute added:String; attribute condition:String; }
part gain0:GainRow { attribute :>> key="compiler-seal"; attribute :>> avoided="Avoid repeated validation/count/profile interpretation"; attribute :>> added="O(F) private plan copying and identity table; required C/IFD/OFD emission remains"; attribute :>> condition="Saving > copy+validation+invalidation; no measured speedup"; }
part gain1:GainRow { attribute :>> key="start-revoke"; attribute :>> avoided="One linearization authority eliminates split check/start window"; attribute :>> added="At least one state RMW per start/revoke; retries and shared cache-line contention"; attribute :>> condition="Net benefit is safe independent workers and tighter plans; lock-free throughput not established"; }
part gain2:GainRow { attribute :>> key="descriptor-retire"; attribute :>> avoided="Enable future per-generation reclaim after exact detachment"; attribute :>> added="Typed credits for frames roots native maintenance observers; retained memory on unknown"; attribute :>> condition="Positive memory benefit only if reclaimed code exceeds lease+summary retention costs"; }
part gain3:GainRow { attribute :>> key="continuation"; attribute :>> avoided="Private immutable snapshots may support parallel independent compilation sessions"; attribute :>> added="Session fork/rebuild and private output transaction for restored computations"; attribute :>> condition="No reuse benefit when arbitrary effects force isolated execution"; }
part gain4:GainRow { attribute :>> key="GC-budget"; attribute :>> avoided="Old roots and module producer summaries remain in certified union"; attribute :>> added="Pending resize roots still scan all slots and can retain larger live graphs"; attribute :>> condition="No reduction in copying from dropping root slots; delta uses unique source union"; }
part gain5:GainRow { attribute :>> key="language"; attribute :>> avoided="All specified operations fit generated modern C plus Scheme semantics"; attribute :>> added="Atomic ABI root wrappers and generation guards require maintenance"; attribute :>> condition="No additional Zig benefit established by this study"; }
part def ContractRow { attribute fromNode:String; attribute toNode:String; attribute custody:String; }
part contract0:ContractRow { attribute :>> fromNode="compiler-writer-closure"; attribute :>> toNode="private-plan-seal"; attribute :>> custody="Own labels cells target c-intf and output"; }
part contract1:ContractRow { attribute :>> fromNode="captured-compiler-continuation"; attribute :>> toNode="session-reentry-guard"; attribute :>> custody="Resume only same live construction or fork privately"; }
part contract2:ContractRow { attribute :>> fromNode="native-capabilities"; attribute :>> toNode="session-reentry-guard"; attribute :>> custody="Untracked raw escape blocks seal admission"; }
part contract3:ContractRow { attribute :>> fromNode="private-plan-seal"; attribute :>> toNode="issued-authority"; attribute :>> custody="Root payload and exact ABI before release publication"; }
part contract4:ContractRow { attribute :>> fromNode="issued-authority"; attribute :>> toNode="start-CAS"; attribute :>> custody="Same generation phase and stable owner identity"; }
part contract5:ContractRow { attribute :>> fromNode="issued-authority"; attribute :>> toNode="revoke-CAS"; attribute :>> custody="Same atomic authority competing with start"; }
part contract6:ContractRow { attribute :>> fromNode="start-CAS"; attribute :>> toNode="copy-credit"; attribute :>> custody="Winner retains descriptors roots and capacity"; }
part contract7:ContractRow { attribute :>> fromNode="revoke-CAS"; attribute :>> toNode="observer-drain"; attribute :>> custody="Stale observer cannot start or dereference freed payload"; }
part contract8:ContractRow { attribute :>> fromNode="copy-credit"; attribute :>> toNode="closed-admission"; attribute :>> custody="Finish guard settles known outcome only"; }
part contract9:ContractRow { attribute :>> fromNode="frame-native-root-maintenance-users"; attribute :>> toNode="closed-admission"; attribute :>> custody="Close new users then drain all existing credits"; }
part contract10:ContractRow { attribute :>> fromNode="closed-admission"; attribute :>> toNode="local-detachment-receipt"; attribute :>> custody="No issued or copy work and no user observer or unknown debt"; }
part contract11:ContractRow { attribute :>> fromNode="unknown-result"; attribute :>> toNode="retained-custody"; attribute :>> custody="Never infer zero from failed or missing acknowledgment"; }
part contract12:ContractRow { attribute :>> fromNode="local-detachment-receipt"; attribute :>> toNode="global-module-owner"; attribute :>> custody="Collect other VM and process native owner receipts"; }
part contract13:ContractRow { attribute :>> fromNode="global-module-owner"; attribute :>> toNode="loader-unload"; attribute :>> custody="Global admission closed and all descriptor owners detached"; }
part contract14:ContractRow { attribute :>> fromNode="session-reentry-guard"; attribute :>> toNode="private-plan-seal"; attribute :>> custody="No live mutable or escaped alias at seal"; }
part contract15:ContractRow { attribute :>> fromNode="observer-drain"; attribute :>> toNode="local-detachment-receipt"; attribute :>> custody="All protected reads admitted before close have settled"; }
part def BindingRow { attribute actionName:String; attribute lemma:String; attribute scope:String; }
part binding0:BindingRow { attribute :>> actionName="frame_seal_start_retire.capture"; attribute :>> lemma="SealStart.capturePreserves"; attribute :>> scope="Actual typed IR step preservation; concrete caller mapping open"; }
part binding1:BindingRow { attribute :>> actionName="frame_seal_start_retire.resumeLive"; attribute :>> lemma="SealStart.resumeLivePreserves"; attribute :>> scope="Actual typed IR step preservation; concrete caller mapping open"; }
part binding2:BindingRow { attribute :>> actionName="frame_seal_start_retire.resumeDenied"; attribute :>> lemma="SealStart.resumeDeniedPreserves"; attribute :>> scope="Actual typed IR step preservation; concrete caller mapping open"; }
part binding3:BindingRow { attribute :>> actionName="frame_seal_start_retire.closeWriters"; attribute :>> lemma="SealStart.closeWritersPreserves"; attribute :>> scope="Actual typed IR step preservation; concrete caller mapping open"; }
part binding4:BindingRow { attribute :>> actionName="frame_seal_start_retire.opaqueEscape"; attribute :>> lemma="SealStart.opaqueEscapePreserves"; attribute :>> scope="Actual typed IR step preservation; concrete caller mapping open"; }
part binding5:BindingRow { attribute :>> actionName="frame_seal_start_retire.seal"; attribute :>> lemma="SealStart.sealPreserves"; attribute :>> scope="Actual typed IR step preservation; concrete caller mapping open"; }
part binding6:BindingRow { attribute :>> actionName="frame_seal_start_retire.abortCandidate"; attribute :>> lemma="SealStart.abortCandidatePreserves"; attribute :>> scope="Actual typed IR step preservation; concrete caller mapping open"; }
part binding7:BindingRow { attribute :>> actionName="frame_seal_start_retire.issue"; attribute :>> lemma="SealStart.issuePreserves"; attribute :>> scope="Actual typed IR step preservation; concrete caller mapping open"; }
part binding8:BindingRow { attribute :>> actionName="frame_seal_start_retire.observe"; attribute :>> lemma="SealStart.observePreserves"; attribute :>> scope="Actual typed IR step preservation; concrete caller mapping open"; }
part binding9:BindingRow { attribute :>> actionName="frame_seal_start_retire.revoke"; attribute :>> lemma="SealStart.revokePreserves"; attribute :>> scope="Actual typed IR step preservation; concrete caller mapping open"; }
part binding10:BindingRow { attribute :>> actionName="frame_seal_start_retire.casStart"; attribute :>> lemma="SealStart.casStartPreserves"; attribute :>> scope="Actual typed IR step preservation; concrete caller mapping open"; }
part binding11:BindingRow { attribute :>> actionName="frame_seal_start_retire.casFailed"; attribute :>> lemma="SealStart.casFailedPreserves"; attribute :>> scope="Actual typed IR step preservation; concrete caller mapping open"; }
part binding12:BindingRow { attribute :>> actionName="frame_seal_start_retire.revokeTooLate"; attribute :>> lemma="SealStart.revokeTooLatePreserves"; attribute :>> scope="Actual typed IR step preservation; concrete caller mapping open"; }
part binding13:BindingRow { attribute :>> actionName="frame_seal_start_retire.finishCopy"; attribute :>> lemma="SealStart.finishCopyPreserves"; attribute :>> scope="Actual typed IR step preservation; concrete caller mapping open"; }
part binding14:BindingRow { attribute :>> actionName="frame_seal_start_retire.nativeBorrow"; attribute :>> lemma="SealStart.nativeBorrowPreserves"; attribute :>> scope="Actual typed IR step preservation; concrete caller mapping open"; }
part binding15:BindingRow { attribute :>> actionName="frame_seal_start_retire.nativeReturn"; attribute :>> lemma="SealStart.nativeReturnPreserves"; attribute :>> scope="Actual typed IR step preservation; concrete caller mapping open"; }
part binding16:BindingRow { attribute :>> actionName="frame_seal_start_retire.nativeUnknown"; attribute :>> lemma="SealStart.nativeUnknownPreserves"; attribute :>> scope="Actual typed IR step preservation; concrete caller mapping open"; }
part binding17:BindingRow { attribute :>> actionName="frame_seal_start_retire.closeAdmission"; attribute :>> lemma="SealStart.closeAdmissionPreserves"; attribute :>> scope="Actual typed IR step preservation; concrete caller mapping open"; }
part binding18:BindingRow { attribute :>> actionName="frame_seal_start_retire.dropFrame"; attribute :>> lemma="SealStart.dropFramePreserves"; attribute :>> scope="Actual typed IR step preservation; concrete caller mapping open"; }
part binding19:BindingRow { attribute :>> actionName="frame_seal_start_retire.dropRoot"; attribute :>> lemma="SealStart.dropRootPreserves"; attribute :>> scope="Actual typed IR step preservation; concrete caller mapping open"; }
part binding20:BindingRow { attribute :>> actionName="frame_seal_start_retire.beginMaintenance"; attribute :>> lemma="SealStart.beginMaintenancePreserves"; attribute :>> scope="Actual typed IR step preservation; concrete caller mapping open"; }
part binding21:BindingRow { attribute :>> actionName="frame_seal_start_retire.endMaintenance"; attribute :>> lemma="SealStart.endMaintenancePreserves"; attribute :>> scope="Actual typed IR step preservation; concrete caller mapping open"; }
part binding22:BindingRow { attribute :>> actionName="frame_seal_start_retire.reclaim"; attribute :>> lemma="SealStart.reclaimPreserves"; attribute :>> scope="Actual typed IR step preservation; concrete caller mapping open"; }
part binding23:BindingRow { attribute :>> actionName="frame_seal_start_retire.denyLateBorrow"; attribute :>> lemma="SealStart.denyLateBorrowPreserves"; attribute :>> scope="Actual typed IR step preservation; concrete caller mapping open"; }
part def ProofRow { attribute key:String; attribute lemma:String; }
part proof0:ProofRow { attribute :>> key="all-step"; attribute :>> lemma="SealStart.stepPreserves"; }
part proof1:ProofRow { attribute :>> key="reachable"; attribute :>> lemma="SealStart.reachableSafe"; }
part proof2:ProofRow { attribute :>> key="revoke-first"; attribute :>> lemma="SealStart.revokeBlocksStart"; }
part proof3:ProofRow { attribute :>> key="start-first"; attribute :>> lemma="SealStart.startBlocksRevoke"; }
part proof4:ProofRow { attribute :>> key="resume-token"; attribute :>> lemma="SealStart.sealInvalidatesSavedToken"; }
part proof5:ProofRow { attribute :>> key="retired-users"; attribute :>> lemma="SealStart.retiredHasNoUsers"; }
part proof6:ProofRow { attribute :>> key="capacity-handoff"; attribute :>> lemma="SealStartComposition.copyingKeepsConditionalBudget"; }
part proof7:ProofRow { attribute :>> key="copy-alive"; attribute :>> lemma="SealStart.copyingAlive"; }
part proof8:ProofRow { attribute :>> key="local-not-global"; attribute :>> lemma="SealStartComposition.localReceiptIsInsufficient"; }
part proof9:ProofRow { attribute :>> key="global-owners"; attribute :>> lemma="SealStartComposition.globalReleaseNeedsAllOwners"; }
part proof10:ProofRow { attribute :>> key="global-release"; attribute :>> lemma="SealStartComposition.globalReleaseFromLocalReceipt"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse3; attribute :>> contract="sealed-plan-to-start-authority"; attribute :>> actionName="frame_seal_start_retire.casStart"; attribute :>> lemma="SealStart.casStartPreserves"; }
part seam1:SeamRow { ref part :>> producer=GambitAssuranceRelations::modelUse5; ref part :>> consumer=GambitAssuranceRelations::modelUse3; attribute :>> contract="multi-shot-frame-descriptor-lease"; attribute :>> actionName="frame_seal_start_retire.reclaim"; attribute :>> lemma="SealStart.retiredHasNoUsers"; }
part seam2:SeamRow { ref part :>> producer=GambitAssuranceRelations::modelUse4; ref part :>> consumer=GambitAssuranceRelations::modelUse3; attribute :>> contract="native-borrow-unknown-retention"; attribute :>> actionName="frame_seal_start_retire.nativeUnknown"; attribute :>> lemma="SealStart.nativeUnknownPreserves"; }
part seam3:SeamRow { ref part :>> producer=GambitAssuranceRelations::modelUse3; ref part :>> consumer=GambitAssuranceRelations::modelUse6; attribute :>> contract="local-detachment-to-global-loader-release"; attribute :>> actionName="frame_seal_start_retire.reclaim"; attribute :>> lemma="SealStartComposition.globalReleaseFromLocalReceipt"; }
part history:GambitAssuranceRouting::ModelNeed { ref part :>> owner=GambitAssuranceRelations::modelUse3; attribute :>> obligationId="SR-history"; attribute :>> kind="interleaving"; attribute :>> subjectPath="dev/refactoring/modern-c/models/quint/frame_seal_start_retire.qnt"; attribute :>> subjectScope="Single authority stale observation resume and detachment histories"; attribute :>> premise="Source and atomic abstract proof do not qualify native implementation"; }
part induction:GambitAssuranceRouting::ModelNeed { ref part :>> owner=GambitAssuranceRelations::modelUse3; attribute :>> obligationId="SR-induction"; attribute :>> kind="induction"; attribute :>> subjectPath="dev/refactoring/modern-c/models/lean/SealStart.lean"; attribute :>> subjectScope="All actual typed IR steps; no C11 weak memory claim"; attribute :>> premise="Source and atomic abstract proof do not qualify native implementation"; }
part composition:GambitAssuranceRouting::ModelNeed { ref part :>> owner=GambitAssuranceRelations::modelUse3; attribute :>> obligationId="SR-composition"; attribute :>> kind="induction"; attribute :>> subjectPath="dev/refactoring/modern-c/models/lean/SealStartComposition.lean"; attribute :>> subjectScope="Conditional previous source-cover budget plus copy descriptor liveness"; attribute :>> premise="Source and atomic abstract proof do not qualify native implementation"; }
part projection:GambitAssuranceRouting::ModelNeed { ref part :>> owner=GambitAssuranceRelations::modelUse2; attribute :>> obligationId="SR-projection"; attribute :>> kind="restricted-projection"; attribute :>> subjectPath="dev/refactoring/modern-c/models/lean/SealStartAst.lean"; attribute :>> subjectScope="Bound JSON names fields and exact step roster"; attribute :>> premise="Source and atomic abstract proof do not qualify native implementation"; }
part source:GambitAssuranceRouting::ModelNeed { ref part :>> owner=GambitAssuranceRelations::modelUse4; attribute :>> obligationId="SR-source"; attribute :>> kind="source-refinement"; attribute :>> subjectPath="dev/refactoring/modern-c/frame-seal-start-retire-design.org"; attribute :>> subjectScope="Complete extension continuation FFI writer and descriptor detach closure OPEN"; attribute :>> premise="Source and atomic abstract proof do not qualify native implementation"; }
part platform:GambitAssuranceRouting::ModelNeed { ref part :>> owner=GambitAssuranceRelations::modelUse3; attribute :>> obligationId="SR-platform"; attribute :>> kind="native-memory-order"; attribute :>> subjectPath="dev/refactoring/modern-c/frame-seal-start-retire-design.org"; attribute :>> subjectScope="Real C11 control record guard rooting and weak-memory refinement OPEN"; attribute :>> premise="Source and atomic abstract proof do not qualify native implementation"; }
}
