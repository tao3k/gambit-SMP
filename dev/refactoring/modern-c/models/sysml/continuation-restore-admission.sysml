package GambitContinuationRestoreAdmission { private import ScalarValues::*;
part def SourceRow { attribute key:String; attribute path:String; attribute needle:String; attribute obligation:String; }
part source0:SourceRow { attribute :>> key="R"; attribute :>> path="vendor/gambit/lib/mem.c"; attribute :>> needle="length = (___ps->context->stack_break + ___FIRST_BREAK_FRAME_SPACE) - start;"; attribute :>> obligation="R is current contiguous active segment, not the whole captured continuation"; }
part source1:SourceRow { attribute :>> key="copy"; attribute :>> path="vendor/gambit/lib/mem.c"; attribute :>> needle="*--p2 = *--p1;"; attribute :>> obligation="Writes exactly R descending words after tospace tracing"; }
part source2:SourceRow { attribute :>> key="metadata"; attribute :>> path="vendor/gambit/lib/mem.c"; attribute :>> needle="-___FIRST_BREAK_FRAME_STACK_MSECTION,"; attribute :>> obligation="Metadata offset two must remain inside copied interval"; }
part source3:SourceRow { attribute :>> key="threshold"; attribute :>> path="vendor/gambit/lib/mem.c"; attribute :>> needle="(___ps->context->stack_start - ___ps->context->stack_limit)*2/3)"; attribute :>> obligation="Conditional pressure heuristic is not a quarter bound"; }
part source4:SourceRow { attribute :>> key="limit-break"; attribute :>> path="vendor/gambit/lib/mem.c"; attribute :>> needle="___ps->context->stack_break = alloc_stack_ptr;"; attribute :>> obligation="Setup, stack overflow and restoration produce break identity"; }
part source5:SourceRow { attribute :>> key="explicit"; attribute :>> path="vendor/gambit/lib/_kernel.scm"; attribute :>> needle="(define-prim (##gc)"; attribute :>> obligation="Explicit collection path has no preceding universal split-fit check"; }
part source6:SourceRow { attribute :>> key="gc-call"; attribute :>> path="vendor/gambit/lib/_kernel.scm"; attribute :>> needle="overflow = ___garbage_collect (___PSP 0);"; attribute :>> obligation="Several Scheme GC entry paths store roots then collect"; }
part source7:SourceRow { attribute :>> key="heap"; attribute :>> path="vendor/gambit/lib/mem.c"; attribute :>> needle="return 1; /* trigger GC */"; attribute :>> obligation="Heap pressure also collects without stack threshold normalization"; }
part source8:SourceRow { attribute :>> key="mark-local"; attribute :>> path="vendor/gambit/lib/mem.c"; attribute :>> needle="fp = context->fp;"; attribute :>> obligation="mark_continuation walks a local fp; does not truncate frozen segment"; }
part source9:SourceRow { attribute :>> key="frozen"; attribute :>> path="vendor/gambit/lib/mem.c"; attribute :>> needle="participant->phase = ___GC_ROOTS_FROZEN;"; attribute :>> obligation="Snapshot collection point before setup loop"; }
part source10:SourceRow { attribute :>> key="setup"; attribute :>> path="vendor/gambit/lib/mem.c"; attribute :>> needle="tospace_offset = fromspace_offset;"; attribute :>> obligation="Parity flip is irreversible boundary for preflight rejection"; }
part source11:SourceRow { attribute :>> key="initial-stack"; attribute :>> path="vendor/gambit/lib/mem.c"; attribute :>> needle="set_stack_msection (___ps, alloc);"; attribute :>> obligation="Reuse already assigned stack section as dedicated space"; }
part source12:SourceRow { attribute :>> key="shared-cap"; attribute :>> path="vendor/gambit/lib/mem.c"; attribute :>> needle="alloc_stack_limit = alloc_stack_ptr - (space + ___MSECTION_FUDGE);"; attribute :>> obligation="Future heap fallback shrinks stack reserve after setup"; }
part source13:SourceRow { attribute :>> key="markers"; attribute :>> path="vendor/gambit/lib/mem.c"; attribute :>> needle="work->context->mem.alloc_heap_limit_ -= 2;"; attribute :>> obligation="Heap interval includes end markers"; }
part source14:SourceRow { attribute :>> key="prepare"; attribute :>> path="vendor/gambit/lib/mem.c"; attribute :>> needle="stack_left_before_fudge = (alloc_stack_ptr - alloc_stack_limit)"; attribute :>> obligation="Restoration capacity and resumption headroom are distinct"; }
part source15:SourceRow { attribute :>> key="undo"; attribute :>> path="vendor/gambit/lib/mem.c"; attribute :>> needle="stack_msection_resume_using (___ps, alloc_stack_start, alloc_stack_ptr);"; attribute :>> obligation="Old stack restoration can rebind section provenance"; }
part source16:SourceRow { attribute :>> key="capture"; attribute :>> path="vendor/gambit/include/gambit.h.in"; attribute :>> needle="#define ___CONTINUATION_CAPTURE"; attribute :>> obligation="Capture changes current break and stores prior frames"; }
part source17:SourceRow { attribute :>> key="graft"; attribute :>> path="vendor/gambit/include/gambit.h.in"; attribute :>> needle="#define ___CONTINUATION_GRAFT_NO_WINDING"; attribute :>> obligation="Graft resets active fp to break; not universal GC pre-normalization"; }
part source18:SourceRow { attribute :>> key="thread"; attribute :>> path="vendor/gambit/include/gambit.h.in"; attribute :>> needle="#define ___THREAD_SAVE"; attribute :>> obligation="Thread suspension may insert break independently"; }
part source19:SourceRow { attribute :>> key="break-handler"; attribute :>> path="vendor/gambit/lib/_kernel.scm"; attribute :>> needle="ra1 = ___stack_overflow_undo_if_possible (___PSPNC);"; attribute :>> obligation="Resume can copy one described frame or restore prior stack"; }
part source20:SourceRow { attribute :>> key="alignment"; attribute :>> path="vendor/gambit/include/gambit.h.in"; attribute :>> needle="#define ___FRAME_ALIGN 4"; attribute :>> obligation="Default first-break rounded size four and frame alignment"; }
part source21:SourceRow { attribute :>> key="limits"; attribute :>> path="vendor/gambit/lib/mem.h"; attribute :>> needle="#define ___MSECTION_SIZE        131072"; attribute :>> obligation="Default half-section H65536; effective profile still must be bound"; }
part def ClaimRow { attribute key:String; attribute mechanism:String; attribute condition:String; attribute result:String; attribute gap:String; }
part claim0:ClaimRow { attribute :>> key="R-span"; attribute :>> mechanism="Prove B<=R<=H from same-block ordered frozen endpoints"; attribute :>> condition="All generated stack writes and break restoration preserve provenance"; attribute :>> result="Conditional symbolic theorem"; attribute :>> gap="Legal Scheme full trace and external FFI aliases remain open"; }
part claim1:ClaimRow { attribute :>> key="quarter"; attribute :>> mechanism="R<=quarter reserve is an additional property"; attribute :>> condition="No universal trimming across explicit and heap GC entries was found"; attribute :>> result="Cannot certify quarter fit for all legal Scheme from current evidence"; attribute :>> gap="No source-qualified legal-input counterexample; numerical implication refuted only"; }
part claim2:ClaimRow { attribute :>> key="policy"; attribute :>> mechanism="Check R plus execution headroom at freeze"; attribute :>> condition="Shared when it fits, otherwise preserve initial stack as dedicated"; attribute :>> result="Avoid late fatal fallback by planning before setup"; attribute :>> gap="Dedicated plan must also reserve global copy-space and pool capacity"; }
part claim3:ClaimRow { attribute :>> key="enforcement"; attribute :>> mechanism="Authorize every later heap fallback from immutable plan"; attribute :>> condition="No R or section identity change until restore completes"; attribute :>> result="A preflight observation alone is insufficient"; attribute :>> gap="Native hook and writer closure plus C11 refinement open"; }
part claim4:ClaimRow { attribute :>> key="failure"; attribute :>> mechanism="Reject or retain before parity flip"; attribute :>> condition="All old members consume same immutable outcome and acknowledge"; attribute :>> result="No coordinator-only return or new Scheme execution while frozen"; attribute :>> gap="Stable exception handoff and emergency headroom remain open"; }
part def MemoryRow { attribute key:String; attribute publication:String; attribute consumer:String; attribute gap:String; }
part memory0:MemoryRow { attribute :>> key="freeze"; attribute :>> publication="Last source pointer write happens-before owner acknowledgement"; attribute :>> consumer="Coordinator acquire observes fp/break/source section as one frozen view"; attribute :>> gap="Ordinary reads only after writer exclusion; per-field atomics insufficient"; }
part memory1:MemoryRow { attribute :>> key="plan"; attribute :>> publication="Initialize manifest and per-member reserve policy then release publish"; attribute :>> consumer="Every member acquire same generation and digest"; attribute :>> gap="Generation reuse prohibited while readers or late receipts exist"; }
part memory2:MemoryRow { attribute :>> key="fallback"; attribute :>> publication="Acquire plan or hold owning epoch before changing heap/stack limits"; attribute :>> consumer="Allowed sharing cannot shrink below committed K"; attribute :>> gap="No extra global atomic per copied word required"; }
part memory3:MemoryRow { attribute :>> key="failure"; attribute :>> publication="Publish rejected result release; acquire consumption and last-reader ack"; attribute :>> consumer="Old roots retained until all acknowledgements and result delivery"; attribute :>> gap="Unknown is retained, never timeout-forged completion"; }
part memory4:MemoryRow { attribute :>> key="restore"; attribute :>> publication="R/source identity pinned through weak completion and move_continuation"; attribute :>> consumer="Restore completion precedes authorization to resume context"; attribute :>> gap="C11 native adapter and callbacks not refined by sequential QNT"; }
part def GainRow { attribute key:String; attribute avoided:String; attribute added:String; attribute condition:String; }
part gain0:GainRow { attribute :>> key="shared"; attribute :>> avoided="Use original heap borrowing for short active segments"; attribute :>> added="O(P) length/provenance checks and plan records"; attribute :>> condition="R+headroom fits shared reserve and total heap capacity independently sufficient"; }
part gain1:GainRow { attribute :>> key="dedicated"; attribute :>> avoided="Reuse initial stack instead of allocating another section just for restore"; attribute :>> added="Forbid fallback; surrender up to current shared heap quota per protected section"; attribute :>> condition="Net benefit only if avoiding extra storage/failure outweighs lost heap capacity"; }
part gain2:GainRow { attribute :>> key="pool"; attribute :>> avoided="At most eligible stack sections contribute fallback visits"; attribute :>> added="Recompute actual N and actual eligible count"; attribute :>> condition="L<=N remains conditional; no credit for removing existing allocation lock"; }
part gain3:GainRow { attribute :>> key="reject"; attribute :>> avoided="Prevent partial parity flip for unsupported plan"; attribute :>> added="Collective latency and retained resources on unknown results"; attribute :>> condition="No speedup claim; do not map rejection directly to an allocating Scheme exception"; }
part gain4:GainRow { attribute :>> key="modern-c"; attribute :>> avoided="Explicit runtime contract replaces implicit quarter assumption"; attribute :>> added="Plan issuer, guard coverage and generation reclamation support"; attribute :>> condition="Zig is not needed to express these contracts"; }
part def ContractRow { attribute fromNode:String; attribute toNode:String; attribute custody:String; }
part contract0:ContractRow { attribute :>> fromNode="frozen-roster"; attribute :>> toNode="span-snapshot"; attribute :>> custody="Validate same live block and checked offsets; pin source"; }
part contract1:ContractRow { attribute :>> fromNode="span-snapshot"; attribute :>> toNode="shared-fit"; attribute :>> custody="Compare R plus execution headroom with reserve"; }
part contract2:ContractRow { attribute :>> fromNode="shared-fit"; attribute :>> toNode="shared-policy"; attribute :>> custody="Short segment may allow later heap fallback"; }
part contract3:ContractRow { attribute :>> fromNode="shared-fit"; attribute :>> toNode="dedicated-policy"; attribute :>> custody="Large segment keeps existing full stack section"; }
part contract4:ContractRow { attribute :>> fromNode="dedicated-policy"; attribute :>> toNode="global-capacity"; attribute :>> custody="Rebudget copy space and queue pool before acceptance"; }
part contract5:ContractRow { attribute :>> fromNode="shared-policy"; attribute :>> toNode="global-capacity"; attribute :>> custody="Bind actual N and eligible fallback identities"; }
part contract6:ContractRow { attribute :>> fromNode="global-capacity"; attribute :>> toNode="collective-decision"; attribute :>> custody="Unknown retains; known unsupported plan rejects"; }
part contract7:ContractRow { attribute :>> fromNode="collective-decision"; attribute :>> toNode="last-reader-acks"; attribute :>> custody="All members consume matching generation and outcome"; }
part contract8:ContractRow { attribute :>> fromNode="last-reader-acks"; attribute :>> toNode="setup"; attribute :>> custody="Accept only; parity flip after release"; }
part contract9:ContractRow { attribute :>> fromNode="last-reader-acks"; attribute :>> toNode="reject-delivery"; attribute :>> custody="Reject only; preserve old roots and no parity change"; }
part contract10:ContractRow { attribute :>> fromNode="setup"; attribute :>> toNode="guarded-fallback"; attribute :>> custody="Enforce plan until actual restoration"; }
part contract11:ContractRow { attribute :>> fromNode="guarded-fallback"; attribute :>> toNode="restore-and-resume"; attribute :>> custody="Copy R then validate execution headroom and publish context"; }
part def BindingRow { attribute actionName:String; attribute lemma:String; attribute scope:String; }
part binding0:BindingRow { attribute :>> actionName="continuation_restore_plan.freezeSmall"; attribute :>> lemma="ContinuationRestore.freezeSmallPreserves"; attribute :>> scope="Actual typed AST induction, not native source qualification"; }
part binding1:BindingRow { attribute :>> actionName="continuation_restore_plan.freezeLarge"; attribute :>> lemma="ContinuationRestore.freezeLargePreserves"; attribute :>> scope="Actual typed AST induction, not native source qualification"; }
part binding2:BindingRow { attribute :>> actionName="continuation_restore_plan.freezeOversize"; attribute :>> lemma="ContinuationRestore.freezeOversizePreserves"; attribute :>> scope="Actual typed AST induction, not native source qualification"; }
part binding3:BindingRow { attribute :>> actionName="continuation_restore_plan.share0"; attribute :>> lemma="ContinuationRestore.share0Preserves"; attribute :>> scope="Actual typed AST induction, not native source qualification"; }
part binding4:BindingRow { attribute :>> actionName="continuation_restore_plan.share1"; attribute :>> lemma="ContinuationRestore.share1Preserves"; attribute :>> scope="Actual typed AST induction, not native source qualification"; }
part binding5:BindingRow { attribute :>> actionName="continuation_restore_plan.dedicate0"; attribute :>> lemma="ContinuationRestore.dedicate0Preserves"; attribute :>> scope="Actual typed AST induction, not native source qualification"; }
part binding6:BindingRow { attribute :>> actionName="continuation_restore_plan.dedicate1"; attribute :>> lemma="ContinuationRestore.dedicate1Preserves"; attribute :>> scope="Actual typed AST induction, not native source qualification"; }
part binding7:BindingRow { attribute :>> actionName="continuation_restore_plan.reject0"; attribute :>> lemma="ContinuationRestore.reject0Preserves"; attribute :>> scope="Actual typed AST induction, not native source qualification"; }
part binding8:BindingRow { attribute :>> actionName="continuation_restore_plan.reject1"; attribute :>> lemma="ContinuationRestore.reject1Preserves"; attribute :>> scope="Actual typed AST induction, not native source qualification"; }
part binding9:BindingRow { attribute :>> actionName="continuation_restore_plan.sealAccept"; attribute :>> lemma="ContinuationRestore.sealAcceptPreserves"; attribute :>> scope="Actual typed AST induction, not native source qualification"; }
part binding10:BindingRow { attribute :>> actionName="continuation_restore_plan.sealReject"; attribute :>> lemma="ContinuationRestore.sealRejectPreserves"; attribute :>> scope="Actual typed AST induction, not native source qualification"; }
part binding11:BindingRow { attribute :>> actionName="continuation_restore_plan.allocationFailure"; attribute :>> lemma="ContinuationRestore.allocationFailurePreserves"; attribute :>> scope="Actual typed AST induction, not native source qualification"; }
part binding12:BindingRow { attribute :>> actionName="continuation_restore_plan.denyMutation"; attribute :>> lemma="ContinuationRestore.denyMutationPreserves"; attribute :>> scope="Actual typed AST induction, not native source qualification"; }
part binding13:BindingRow { attribute :>> actionName="continuation_restore_plan.retainUnknown"; attribute :>> lemma="ContinuationRestore.retainUnknownPreserves"; attribute :>> scope="Actual typed AST induction, not native source qualification"; }
part def ProofRow { attribute key:String; attribute lemma:String; }
part proof0:ProofRow { attribute :>> key="span"; attribute :>> lemma="RestoreAdmissionComposition.sourceSpanBound"; }
part proof1:ProofRow { attribute :>> key="quarter-control"; attribute :>> lemma="RestoreAdmissionComposition.thresholdDoesNotImplyQuarter"; }
part proof2:ProofRow { attribute :>> key="interval"; attribute :>> lemma="RestoreAdmissionComposition.actualWriteSeparation"; }
part proof3:ProofRow { attribute :>> key="resume"; attribute :>> lemma="RestoreAdmissionComposition.resumeHeadroom"; }
part proof4:ProofRow { attribute :>> key="lease-count"; attribute :>> lemma="RestoreAdmissionComposition.restrictFallbackCount"; }
part proof5:ProofRow { attribute :>> key="bounds"; attribute :>> lemma="ContinuationRestore.acceptedBounds"; }
part proof6:ProofRow { attribute :>> key="large"; attribute :>> lemma="ContinuationRestore.largeNeedsDedicated"; }
part proof7:ProofRow { attribute :>> key="frozen"; attribute :>> lemma="ContinuationRestore.frozenLengthStable"; }
part proof8:ProofRow { attribute :>> key="sealed"; attribute :>> lemma="ContinuationRestore.sealedOutcomeStable"; }
part proof9:ProofRow { attribute :>> key="product"; attribute :>> lemma="RestoreAdmissionComposition.reachableCoupled"; }
part proof10:ProofRow { attribute :>> key="setup"; attribute :>> lemma="RestoreAdmissionComposition.setupRequiresValidBounds"; }
part proof11:ProofRow { attribute :>> key="reject"; attribute :>> lemma="RestoreAdmissionComposition.rejectedPlanCannotSetup"; }
part proof12:ProofRow { attribute :>> key="non-vacuity"; attribute :>> lemma="RestoreAdmissionComposition.largeDedicatedSetupReachable"; }
part history:GambitAssuranceRouting::ModelNeed { ref part :>> owner=GambitAssuranceRelations::modelUse3; attribute :>> obligationId="CR-history"; attribute :>> kind="interleaving"; attribute :>> subjectPath="dev/refactoring/modern-c/models/quint/continuation_restore_plan.qnt"; attribute :>> subjectScope="Two-owner short long oversize OOM unknown and mutation histories"; attribute :>> premise="Research model only; source and native qualification separate"; }
part induction:GambitAssuranceRouting::ModelNeed { ref part :>> owner=GambitAssuranceRelations::modelUse3; attribute :>> obligationId="CR-induction"; attribute :>> kind="induction"; attribute :>> subjectPath="dev/refactoring/modern-c/models/lean/ContinuationRestore.lean"; attribute :>> subjectScope="All actual typed AST planner actions"; attribute :>> premise="Research model only; source and native qualification separate"; }
part composition:GambitAssuranceRouting::ModelNeed { ref part :>> owner=GambitAssuranceRelations::modelUse3; attribute :>> obligationId="CR-composition"; attribute :>> kind="induction"; attribute :>> subjectPath="dev/refactoring/modern-c/models/lean/RestoreAdmissionComposition.lean"; attribute :>> subjectScope="Actual preceding collective AST product plus conditional source-span geometry"; attribute :>> premise="Research model only; source and native qualification separate"; }
part projection:GambitAssuranceRouting::ModelNeed { ref part :>> owner=GambitAssuranceRelations::modelUse3; attribute :>> obligationId="CR-projection"; attribute :>> kind="restricted-projection"; attribute :>> subjectPath="dev/refactoring/modern-c/models/lean/ContinuationRestoreAst.lean"; attribute :>> subjectScope="Scalar typed JSON to Lean identity-preserving extraction"; attribute :>> premise="Research model only; source and native qualification separate"; }
part source:GambitAssuranceRouting::ModelNeed { ref part :>> owner=GambitAssuranceRelations::modelUse3; attribute :>> obligationId="CR-source"; attribute :>> kind="source-refinement"; attribute :>> subjectPath="dev/refactoring/modern-c/continuation-restore-admission-design.org"; attribute :>> subjectScope="Legal Scheme trace source provenance and actual all-writer plan guards remain open"; attribute :>> premise="Research model only; source and native qualification separate"; }
part platform:GambitAssuranceRouting::ModelNeed { ref part :>> owner=GambitAssuranceRelations::modelUse3; attribute :>> obligationId="CR-platform"; attribute :>> kind="native-memory-order"; attribute :>> subjectPath="dev/refactoring/modern-c/continuation-restore-admission-design.org"; attribute :>> subjectScope="C11 publication and stable guard failure delivery remain open"; attribute :>> premise="Research model only; source and native qualification separate"; }
part def Dependency { ref part prior:GambitAssuranceRouting::ModelNeed; attribute contract:String; }
part priorCollective:Dependency { ref part :>> prior=GambitDefaultLeaseAdmission::collectiveInduction; attribute :>> contract="Import exact prior collective AST and proof; gate its publication on accepted restore plan"; }
part priorLeases:Dependency { ref part :>> prior=GambitDefaultLeaseAdmission::leasesInduction; attribute :>> contract="Restrict eligible fallback set; do not invent a second allocation counter"; }
}
