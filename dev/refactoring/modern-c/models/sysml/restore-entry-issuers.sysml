package GambitRestoreEntryIssuers { private import ScalarValues::*;
part def Owner { attribute componentId:String; }
part entryOwner:Owner { attribute :>> componentId="entry"; }
part guardOwner:Owner { attribute :>> componentId="guard"; }
part rootsOwner:Owner { attribute :>> componentId="roots"; }
part def SourceRow { attribute key:String; attribute path:String; attribute needle:String; attribute obligation:String; }
part source0:SourceRow { attribute :>> key="raw-return"; attribute :>> path="vendor/gambit/gsc/tests/15-cont/ctak.scm"; attribute :>> needle="(##continuation-return-no-winding k z)"; attribute :>> obligation="Direct extended-binding invocation exists; no dynamic-wind wrapper premise"; }
part source1:SourceRow { attribute :>> key="raw-graft"; attribute :>> path="vendor/gambit/gsc/tests/15-cont/contcapgraft.scm"; attribute :>> needle="(##continuation-graft-no-winding k f0)"; attribute :>> obligation="Active zero-argument direct graft; later block-comment cases are not execution evidence"; }
part source2:SourceRow { attribute :>> key="raw-values"; attribute :>> path="vendor/gambit/gsc/tests/15-cont/contcapret.scm"; attribute :>> needle="(##continuation-return-no-winding"; attribute :>> obligation="Direct return includes values construction before transfer"; }
part source3:SourceRow { attribute :>> key="primitive"; attribute :>> path="vendor/gambit/gsc/_prims.scm"; attribute :>> needle="(\"##continuation-graft-no-winding\""; attribute :>> obligation="Primitive registry recognizes direct extended binding; not a managed issuer"; }
part source4:SourceRow { attribute :>> key="thread-schedule"; attribute :>> path="vendor/gambit/lib/_thread.scm"; attribute :>> needle="(macro-thread-restore!"; attribute :>> obligation="Local, steal and alternate-profile scheduler call sites"; }
part source5:SourceRow { attribute :>> key="thread-wrapper"; attribute :>> path="vendor/gambit/lib/_thread.scm"; attribute :>> needle="(##thread-restore! thread (lambda () (##apply proc args)))"; attribute :>> obligation="Arity packing wrapper is not automatically a new execution"; }
part source6:SourceRow { attribute :>> key="graft-wrapper"; attribute :>> path="vendor/gambit/lib/_thread.scm"; attribute :>> needle="(##continuation-graft-no-winding cont ##apply proc args)"; attribute :>> obligation="Wrapper and aux arity normalization must preserve invocation identity"; }
part source7:SourceRow { attribute :>> key="wind"; attribute :>> path="vendor/gambit/lib/_thread.scm"; attribute :>> needle="(define-prim (##continuation-unwind-wind src dst continue)"; attribute :>> obligation="Internal before/after navigation uses same primitive as direct invocation"; }
part source8:SourceRow { attribute :>> key="graft-aux"; attribute :>> path="vendor/gambit/lib/_thread.scm"; attribute :>> needle="(define-prim (##continuation-graft-aux cont proc arg1 arg2 arg3 others)"; attribute :>> obligation="Allocate args then invoke low-level graft; generator point must preserve roots"; }
part source9:SourceRow { attribute :>> key="return-aux"; attribute :>> path="vendor/gambit/lib/_thread.scm"; attribute :>> needle="(define-prim (##continuation-return-aux cont val1 val2 val3 others)"; attribute :>> obligation="Values packing and winding are parts of original invocation"; }
part source10:SourceRow { attribute :>> key="emit-graft"; attribute :>> path="vendor/gambit/gsc/_t-c-2.scm"; attribute :>> needle="(targ-jump-inline \"##continuation-graft-no-winding\""; attribute :>> obligation="Actual destructive jump emitter needs provenance; primitive name is insufficient"; }
part source11:SourceRow { attribute :>> key="emit-thread"; attribute :>> path="vendor/gambit/gsc/_t-c-2.scm"; attribute :>> needle="(targ-jump-inline \"##thread-restore!\""; attribute :>> obligation="Scheduler and direct primitive need explicit distinct intent"; }
part source12:SourceRow { attribute :>> key="sfun-generator"; attribute :>> path="vendor/gambit/gsc/_ptree2.scm"; attribute :>> needle="(define (c-make-function sfun? name param-typs result-typ make-body)"; attribute :>> obligation="BEGIN_SFUN is emitted before argument conversion; ___call is too late for bootstrap roots"; }
part source13:SourceRow { attribute :>> key="sfun-convert-order"; attribute :>> path="vendor/gambit/gsc/_ptree2.scm"; attribute :>> needle="(append (keep scmobj-typ? numbered-param-typs)"; attribute :>> obligation="SCMOBJ conversion priority does not move it ahead of BEGIN_SFUN marker allocation"; }
part source14:SourceRow { attribute :>> key="sfun-static"; attribute :>> path="vendor/gambit/gsc/_ptree2.scm"; attribute :>> needle="c-id-prefix \"MLBL(\" c-id-prefix \"C_LBL_\" proc-name"; attribute :>> obligation="Static c-define procedure label differs from dynamic closure FAL converter"; }
part source15:SourceRow { attribute :>> key="sfun-begin"; attribute :>> path="vendor/gambit/include/gambit.h"; attribute :>> needle="#define ___BEGIN_SFUN_VOID(proc)"; attribute :>> obligation="Marker allocated before argument body and ___call"; }
part source16:SourceRow { attribute :>> key="sfun-scmarg"; attribute :>> path="vendor/gambit/include/gambit.h"; attribute :>> needle="#define ___BEGIN_SFUN_ARG_SCMOBJ(i)"; attribute :>> obligation="Empty macro is not a generic root registration"; }
part source17:SourceRow { attribute :>> key="sfun-error"; attribute :>> path="vendor/gambit/include/gambit.h"; attribute :>> needle="#define ___SFUN_ERROR_VOID"; attribute :>> obligation="Conversion retry reuses host marker; not a fresh top-level host entry"; }
part source18:SourceRow { attribute :>> key="catcher"; attribute :>> path="vendor/gambit/include/gambit.h"; attribute :>> needle="#define ___END_TRY } ___ps->catcher = ___old_catcher; }"; attribute :>> obligation="Only actual outer catch/restoration can support completion"; }
part source19:SourceRow { attribute :>> key="run"; attribute :>> path="vendor/gambit/lib/setup.c"; attribute :>> needle="___make_sfun_stack_marker_from_root"; attribute :>> obligation="Managed startup has rooted endpoint; generic host guard absent in inspected path"; }
part source20:SourceRow { attribute :>> key="call"; attribute :>> path="vendor/gambit/lib/setup.c"; attribute :>> needle="stack_marker != ___ps->context->fp[___FRAME_SPACE(2)-2]"; attribute :>> obligation="Unmatched unwind propagates; cannot fabricate local exit witness"; }
part source21:SourceRow { attribute :>> key="reload"; attribute :>> path="vendor/gambit/lib/c_intf.c"; attribute :>> needle="proc_or_false = *proc_root; /* reload after allocating the marker */"; attribute :>> obligation="Known slot must remain valid and GC-updated before guard reservation"; }
part source22:SourceRow { attribute :>> key="legacy"; attribute :>> path="vendor/gambit/lib/c_intf.c"; attribute :>> needle="Legacy raw SFUN entry is not made a registered-root interface"; attribute :>> obligation="Raw local address cannot bootstrap a managed root protocol"; }
part source23:SourceRow { attribute :>> key="dynamic-source"; attribute :>> path="vendor/gambit/lib/c_intf.c"; attribute :>> needle="___VECTORELEM(stack_marker, 0) = ___data_rc (___c_closure_self ());"; attribute :>> obligation="Ambient dynamic closure read occurs after allocating marker; identity freeze required"; }
part source24:SourceRow { attribute :>> key="closure-global"; attribute :>> path="vendor/gambit/lib/os_dyn.c"; attribute :>> needle="/* TODO: c_closure_self needs to be thread local */"; attribute :>> obligation="Conditional dynamic closure path has shared ambient self; TLS alone would not solve nested identity"; }
part source25:SourceRow { attribute :>> key="closure-producer"; attribute :>> path="vendor/gambit/lib/os_dyn.c"; attribute :>> needle="___set_data_rc (c_closure, proc);"; attribute :>> obligation="Dynamic closure stores procedure in RC payload"; }
part source26:SourceRow { attribute :>> key="closure-unavailable"; attribute :>> path="vendor/gambit/lib/os_dyn.c"; attribute :>> needle="#ifndef C_CLOSURE_CODE_SIZE"; attribute :>> obligation="Unsupported architecture returns null; no claim this conditional branch runs on Darwin arm64"; }
part source27:SourceRow { attribute :>> key="tcl-producer"; attribute :>> path="vendor/gambit/examples/tcltk/tcltk.scm"; attribute :>> needle="___EXT(___set_data_rc) (cd, vect);"; attribute :>> obligation="Native callback source vector installed in RC payload"; }
part source28:SourceRow { attribute :>> key="tcl-entry"; attribute :>> path="vendor/gambit/examples/tcltk/tcltk.scm"; attribute :>> needle="char *result = tcltk_call"; attribute :>> obligation="Concrete native ingress; deletion/lifetime/scan custody must precede new guard"; }
part source29:SourceRow { attribute :>> key="rc-register"; attribute :>> path="vendor/gambit/lib/memory/rc-allocation.inc"; attribute :>> needle="if (ptr != 0) ___register_rc (___PSP ptr);"; attribute :>> obligation="Registration and payload assignment distinct; list mutation is not an arbitrary-thread pin protocol"; }
part source30:SourceRow { attribute :>> key="rc-update"; attribute :>> path="vendor/gambit/lib/memory/rc-allocation.inc"; attribute :>> needle="h->data = val;"; attribute :>> obligation="Actual payload writer must join source freeze and scan handoff"; }
part source31:SourceRow { attribute :>> key="rc-scan"; attribute :>> path="vendor/gambit/lib/memory/rc-roots.inc"; attribute :>> needle="mark_array (work, &h->data, 1);"; attribute :>> obligation="Moving GC updates RC data slot; native raw copy is not automatically reloaded"; }
part source32:SourceRow { attribute :>> key="startup-scan"; attribute :>> path="vendor/gambit/lib/memory/root-origins.inc"; attribute :>> needle="mark_array (work, &context->startup_thunk, 1);"; attribute :>> obligation="Existing context root consumer reusable after origin membership is qualified"; }
part source33:SourceRow { attribute :>> key="entry-marker-scan"; attribute :>> path="vendor/gambit/lib/memory/root-origins.inc"; attribute :>> needle="mark_array (work, &context->entry_marker, 1);"; attribute :>> obligation="Context marker scanned; no universal pre-guard carrier inferred"; }
part source34:SourceRow { attribute :>> key="c-return"; attribute :>> path="vendor/gambit/lib/_kernel.scm"; attribute :>> needle="___COVER_RETURN_TO_C_HANDLER_WRONG_PROCESSOR;"; attribute :>> obligation="Keep C return affinity distinct from ticket ownership"; }
part def IdentityRow { attribute key:String; attribute structure:String; attribute rule:String; attribute caveat:String; }
part identity0:IdentityRow { attribute :>> key="fresh"; attribute :>> structure="InvocationIntent plus external AttemptId"; attribute :>> rule="Mint once per direct admitted semantic restore"; attribute :>> caveat="Raw primitive spelling alone gives no trusted navigation proof"; }
part identity1:IdentityRow { attribute :>> key="navigation"; attribute :>> structure="Parent restore transaction plus qualified call-site role"; attribute :>> rule="Keep ticket through helper and arity packing"; attribute :>> caveat="before/after user procedure invocation may itself start a new semantic restore"; }
part identity2:IdentityRow { attribute :>> key="scheduler"; attribute :>> structure="ExecutionContextId plus existing TicketId"; attribute :>> rule="Resume same activation with carrier handoff"; attribute :>> caveat="Direct ##thread-restore! outside known scheduler remains unqualified"; }
part identity3:IdentityRow { attribute :>> key="foreign"; attribute :>> structure="HostEntryId plus child TicketId"; attribute :>> rule="Nested callback child differs from conversion OperationId"; attribute :>> caveat="Static MLBL proc does not prove Scheme arguments rooted"; }
part identity4:IdentityRow { attribute :>> key="bootstrap"; attribute :>> structure="SourceRootId plus generation plus pre-reserved carrier"; attribute :>> rule="Root transfer and GC reload before allocating guard or marker"; attribute :>> caveat="Raw C local, volatile or slot address is not a registration witness"; }
part identity5:IdentityRow { attribute :>> key="receipt"; attribute :>> structure="Full GuardId immutable across restored data"; attribute :>> rule="Dispatch exact identity regardless of ambient current"; attribute :>> caveat="Real owner signer, finite generation and reclamation still open"; }
part def IssuerRow { attribute key:String; attribute proposedIssuer:String; attribute actualSource:String; attribute status:String; attribute responsibility:String; }
part issuer0:IssuerRow { attribute :>> key="intent"; attribute :>> proposedIssuer="Scheme/GVM caller-role producer plus runtime validator"; attribute :>> actualSource="Actual wrappers, wind helpers, scheduler and direct test sources located"; attribute :>> status="Lexical census bounded; indirect callable aliases remain open"; attribute :>> responsibility="Generate an unforgeable or checked intent capability"; }
part issuer1:IssuerRow { attribute :>> key="bootstrap"; attribute :>> proposedIssuer="Current source-root and execution-context owner"; attribute :>> actualSource="Context roots and RC scan consumers located; generic entry carrier absent"; attribute :>> status="Required refactoring"; attribute :>> responsibility="Nonallocating pin and reserved carrier handoff before any allocating guard"; }
part issuer2:IssuerRow { attribute :>> key="reservation"; attribute :>> proposedIssuer="Stable VM native-entry owner"; attribute :>> actualSource="___call begins after caller marker allocation; no exact TicketId issuer found"; attribute :>> status="No existing complete guard signer identified"; attribute :>> responsibility="Publish reserved record and incoming roots outside restored graph"; }
part issuer3:IssuerRow { attribute :>> key="foreign"; attribute :>> proposedIssuer="Generated host-entry prologue owner"; attribute :>> actualSource="c-make-function emits BEGIN before conversion; Tcl and dynamic closure sources located"; attribute :>> status="Must change generator and qualify callback source lifetime"; attribute :>> responsibility="Separate static label, rooted RC payload and unqualified raw argument"; }
part issuer4:IssuerRow { attribute :>> key="exit"; attribute :>> proposedIssuer="Stable outer completion owner"; attribute :>> actualSource="___run catches; ___call can rethrow; SFUN normal tail kills marker"; attribute :>> status="Partial mechanisms reusable; exact witness issuer absent"; attribute :>> responsibility="Restore parent/catcher and close marker; retain unknown ownership"; }
part issuer5:IssuerRow { attribute :>> key="scanner"; attribute :>> proposedIssuer="RootRegistry/context origin owner"; attribute :>> actualSource="mark_execution_roots and mark_rc update actual slots"; attribute :>> status="Existing consumers are not proof of all-origin and scan-close coverage"; attribute :>> responsibility="GC-visible carrier plus mutable source custody and cancellation discipline"; }
part issuer6:IssuerRow { attribute :>> key="retirement"; attribute :>> proposedIssuer="Per-key ledger plus capability-domain owner"; attribute :>> actualSource="Earlier arbitrary-key guard algebra is available"; attribute :>> status="Native issuer and full normalization equivalence remain open"; attribute :>> responsibility="Old immutable receipt cannot target a new ambient execution"; }
part def ClaimRow { attribute key:String; attribute mechanism:String; attribute condition:String; attribute result:String; attribute gap:String; }
part claim0:ClaimRow { attribute :>> key="census"; attribute :>> mechanism="Exact token inventory over declared source roster"; attribute :>> condition="Hashes and all matches retained; comments and generated metadata labelled lexical"; attribute :>> result="All lexical hits in the stated corpus are recorded"; attribute :>> gap="Not expanded Scheme, all external code or indirect alias closure"; }
part claim1:ClaimRow { attribute :>> key="bootstrap"; attribute :>> mechanism="Source pin then reserved scan carrier then allocating guard"; attribute :>> condition="Source origin and pin valid; collector updates both slots"; attribute :>> result="Carrier remains current across modeled moving GC"; attribute :>> gap="Actual no-allocation pin issuer and source scanner closure unimplemented"; }
part claim2:ClaimRow { attribute :>> key="bridge"; attribute :>> mechanism="Admission relation from bootstrap to prior two-ticket entry"; attribute :>> condition="Intent, roots, guard binding and parent relation agree"; attribute :>> result="Earlier enter safety applies after admitted bootstrap"; attribute :>> gap="Not full source simulation or arbitrary nested product"; }
part claim3:ClaimRow { attribute :>> key="raw"; attribute :>> mechanism="Deny optimized receipt for raw local source or unknown caller role"; attribute :>> condition="Preserve existing non-optimized Scheme execution path"; attribute :>> result="No false root or fresh-identity certificate"; attribute :>> gap="Fallback implementation and total semantic equivalence open"; }
part claim4:ClaimRow { attribute :>> key="failure"; attribute :>> mechanism="Retain source or carrier under pre-admission/guard owner"; attribute :>> condition="Failure branch never drops last rooted custody"; attribute :>> result="Unknown allocation/exit retains modeled carrier"; attribute :>> gap="Availability and bounded retention not proved"; }
part claim5:ClaimRow { attribute :>> key="ambient"; attribute :>> mechanism="Freeze source identity before allocation and user callback"; attribute :>> condition="Qualified pin independent of ambient c_closure_self"; attribute :>> result="Avoid selecting another callback payload after reentry"; attribute :>> gap="Conditional historical backend; actual Darwin activation not established"; }
part def MemoryRow { attribute key:String; attribute publication:String; attribute observation:String; attribute obligation:String; attribute overhead:String; }
part memory0:MemoryRow { attribute :>> key="source"; attribute :>> publication="Source owner validates origin/generation and nonallocating pin"; attribute :>> observation="Collector and owner agree same source slot"; attribute :>> obligation="No arbitrary foreign thread list mutation; lock not held across GC"; attribute :>> overhead="Source read lease and reserved capacity"; }
part memory1:MemoryRow { attribute :>> key="carrier"; attribute :>> publication="Copy into pre-reserved registered slot before publication cut"; attribute :>> observation="GC updates carrier and source as admitted roots"; attribute :>> obligation="Atomic visibility alone is not root registration; reload from carrier"; attribute :>> overhead="One carrier per admitted fresh/foreign ingress"; }
part memory2:MemoryRow { attribute :>> key="guard"; attribute :>> publication="Allocate only while carrier scan-visible; publish full immutable identity"; attribute :>> observation="Restored code binds stable owner record"; attribute :>> obligation="Failure before/after commit remains owned; avoid lock across Scheme/GC"; attribute :>> overhead="One native record and short synchronization"; }
part memory3:MemoryRow { attribute :>> key="source-drop"; attribute :>> publication="Release original source after target root acknowledgement"; attribute :>> observation="Collector sees carrier after source retires"; attribute :>> obligation="Source/target scan epochs and deletion drain must be qualified"; attribute :>> overhead="Root-domain acknowledgement"; }
part memory4:MemoryRow { attribute :>> key="exit"; attribute :>> publication="Outer guard hands exact witness to ledger"; attribute :>> observation="Same GuardId read after catcher and parent restoration"; attribute :>> obligation="No ambient retargeting; C return affinity preserved"; attribute :>> overhead="Outcome retention and pinned lookup"; }
part def GainRow { attribute key:String; attribute avoided:String; attribute added:String; attribute condition:String; }
part gain0:GainRow { attribute :>> key="identity"; attribute :>> avoided="H+S+O needless tickets for internal grafts, resumes and conversion operations"; attribute :>> added="Caller-role validation and carrier handoff"; attribute :>> condition="This compares proposed policies; not measured current-Gambit savings"; }
part gain1:GainRow { attribute :>> key="bootstrap"; attribute :>> avoided="Duplicate per-wrapper ad hoc rooting and failure cleanup"; attribute :>> added="Shared reserved carrier, source pin and stable owner"; attribute :>> condition="Only if actual wrappers migrate and retire duplicate support"; }
part gain2:GainRow { attribute :>> key="legacy"; attribute :>> avoided="Unsafe assumption that BEGIN_SFUN_ARG_SCMOBJ or C local is a root"; attribute :>> added="Explicit generated ingress contract"; attribute :>> condition="No blanket rejection of static labels; qualify each live Scheme argument"; }
part gain3:GainRow { attribute :>> key="closure"; attribute :>> avoided="Ambient self reread across allocation or nested entry"; attribute :>> added="Bound payload plus native lifetime lease"; attribute :>> condition="Only applicable where dynamic closure backend is active"; }
part gain4:GainRow { attribute :>> key="normalization"; attribute :>> avoided="At most one redundant metadata traversal"; attribute :>> added="All marginal ingress, root and retention overhead"; attribute :>> condition="Source, platform and emission gates closed and traversal savings larger than costs"; }
part def ContractRow { attribute fromNode:String; attribute toNode:String; attribute custody:String; }
part contract0:ContractRow { attribute :>> fromNode="Caller role"; attribute :>> toNode="Admission validator"; attribute :>> custody="fresh / navigation / scheduler / conversion / foreign / unknown"; }
part contract1:ContractRow { attribute :>> fromNode="Admission validator"; attribute :>> toNode="Existing guard"; attribute :>> custody="trusted navigation scheduling conversion reuse identity"; }
part contract2:ContractRow { attribute :>> fromNode="Admission validator"; attribute :>> toNode="Source root owner"; attribute :>> custody="fresh or foreign requires valid source generation"; }
part contract3:ContractRow { attribute :>> fromNode="Source root owner"; attribute :>> toNode="Reserved carrier"; attribute :>> custody="nonallocating pin and scan-visible handoff"; }
part contract4:ContractRow { attribute :>> fromNode="Reserved carrier"; attribute :>> toNode="Stable guard owner"; attribute :>> custody="guard allocation may GC; reload rooted payload"; }
part contract5:ContractRow { attribute :>> fromNode="Stable guard owner"; attribute :>> toNode="Marker and argument conversion"; attribute :>> custody="root before BEGIN_SFUN allocating prologue"; }
part contract6:ContractRow { attribute :>> fromNode="Marker and argument conversion"; attribute :>> toNode="Restore and nested execution"; attribute :>> custody="FrameSpec and PointId; child parent binding"; }
part contract7:ContractRow { attribute :>> fromNode="Restore and nested execution"; attribute :>> toNode="Outer completion owner"; attribute :>> custody="catcher restoration and marker closure"; }
part contract8:ContractRow { attribute :>> fromNode="Outer completion owner"; attribute :>> toNode="Exact key ledger"; attribute :>> custody="immutable receipt never follows current execution"; }
part contract9:ContractRow { attribute :>> fromNode="Reserved carrier"; attribute :>> toNode="Failure escrow"; attribute :>> custody="allocation unknown retains rooted custody"; }
part contract10:ContractRow { attribute :>> fromNode="Stable guard owner"; attribute :>> toNode="Failure escrow"; attribute :>> custody="unmatched unwind retains record and roots"; }
part contract11:ContractRow { attribute :>> fromNode="Failure escrow"; attribute :>> toNode="Source root owner"; attribute :>> custody="acknowledged recovery or drain; no invented absence"; }
part def BindingRow { attribute actionName:String; attribute lemma:String; attribute scope:String; }
part binding0:BindingRow { attribute :>> actionName="restore_entry_issuers.classifyFresh"; attribute :>> lemma="RestoreIssuer.classifyFreshPreserves"; attribute :>> scope="typed AST; source origin/witness authority external"; }
part binding1:BindingRow { attribute :>> actionName="restore_entry_issuers.classifyNavigation"; attribute :>> lemma="RestoreIssuer.classifyNavigationPreserves"; attribute :>> scope="typed AST; source origin/witness authority external"; }
part binding2:BindingRow { attribute :>> actionName="restore_entry_issuers.classifyScheduler"; attribute :>> lemma="RestoreIssuer.classifySchedulerPreserves"; attribute :>> scope="typed AST; source origin/witness authority external"; }
part binding3:BindingRow { attribute :>> actionName="restore_entry_issuers.classifyForeign"; attribute :>> lemma="RestoreIssuer.classifyForeignPreserves"; attribute :>> scope="typed AST; source origin/witness authority external"; }
part binding4:BindingRow { attribute :>> actionName="restore_entry_issuers.classifyConversion"; attribute :>> lemma="RestoreIssuer.classifyConversionPreserves"; attribute :>> scope="typed AST; source origin/witness authority external"; }
part binding5:BindingRow { attribute :>> actionName="restore_entry_issuers.sourceFrame"; attribute :>> lemma="RestoreIssuer.sourceFramePreserves"; attribute :>> scope="typed AST; source origin/witness authority external"; }
part binding6:BindingRow { attribute :>> actionName="restore_entry_issuers.sourceRc"; attribute :>> lemma="RestoreIssuer.sourceRcPreserves"; attribute :>> scope="typed AST; source origin/witness authority external"; }
part binding7:BindingRow { attribute :>> actionName="restore_entry_issuers.sourceRaw"; attribute :>> lemma="RestoreIssuer.sourceRawPreserves"; attribute :>> scope="typed AST; source origin/witness authority external"; }
part binding8:BindingRow { attribute :>> actionName="restore_entry_issuers.pinSource"; attribute :>> lemma="RestoreIssuer.pinSourcePreserves"; attribute :>> scope="typed AST; source origin/witness authority external"; }
part binding9:BindingRow { attribute :>> actionName="restore_entry_issuers.publishCarrier"; attribute :>> lemma="RestoreIssuer.publishCarrierPreserves"; attribute :>> scope="typed AST; source origin/witness authority external"; }
part binding10:BindingRow { attribute :>> actionName="restore_entry_issuers.gcSourceOnly"; attribute :>> lemma="RestoreIssuer.gcSourceOnlyPreserves"; attribute :>> scope="typed AST; source origin/witness authority external"; }
part binding11:BindingRow { attribute :>> actionName="restore_entry_issuers.gcPublished"; attribute :>> lemma="RestoreIssuer.gcPublishedPreserves"; attribute :>> scope="typed AST; source origin/witness authority external"; }
part binding12:BindingRow { attribute :>> actionName="restore_entry_issuers.reserveGuard"; attribute :>> lemma="RestoreIssuer.reserveGuardPreserves"; attribute :>> scope="typed AST; source origin/witness authority external"; }
part binding13:BindingRow { attribute :>> actionName="restore_entry_issuers.guardAllocationFails"; attribute :>> lemma="RestoreIssuer.guardAllocationFailsPreserves"; attribute :>> scope="typed AST; source origin/witness authority external"; }
part binding14:BindingRow { attribute :>> actionName="restore_entry_issuers.publishGuard"; attribute :>> lemma="RestoreIssuer.publishGuardPreserves"; attribute :>> scope="typed AST; source origin/witness authority external"; }
part binding15:BindingRow { attribute :>> actionName="restore_entry_issuers.releaseSource"; attribute :>> lemma="RestoreIssuer.releaseSourcePreserves"; attribute :>> scope="typed AST; source origin/witness authority external"; }
part binding16:BindingRow { attribute :>> actionName="restore_entry_issuers.allocateMarker"; attribute :>> lemma="RestoreIssuer.allocateMarkerPreserves"; attribute :>> scope="typed AST; source origin/witness authority external"; }
part binding17:BindingRow { attribute :>> actionName="restore_entry_issuers.enter"; attribute :>> lemma="RestoreIssuer.enterPreserves"; attribute :>> scope="typed AST; source origin/witness authority external"; }
part binding18:BindingRow { attribute :>> actionName="restore_entry_issuers.exceptionToOwner"; attribute :>> lemma="RestoreIssuer.exceptionToOwnerPreserves"; attribute :>> scope="typed AST; source origin/witness authority external"; }
part binding19:BindingRow { attribute :>> actionName="restore_entry_issuers.observeOuter"; attribute :>> lemma="RestoreIssuer.observeOuterPreserves"; attribute :>> scope="typed AST; source origin/witness authority external"; }
part binding20:BindingRow { attribute :>> actionName="restore_entry_issuers.killMarker"; attribute :>> lemma="RestoreIssuer.killMarkerPreserves"; attribute :>> scope="typed AST; source origin/witness authority external"; }
part binding21:BindingRow { attribute :>> actionName="restore_entry_issuers.complete"; attribute :>> lemma="RestoreIssuer.completePreserves"; attribute :>> scope="typed AST; source origin/witness authority external"; }
part binding22:BindingRow { attribute :>> actionName="restore_entry_issuers.reuseExisting"; attribute :>> lemma="RestoreIssuer.reuseExistingPreserves"; attribute :>> scope="typed AST; source origin/witness authority external"; }
part binding23:BindingRow { attribute :>> actionName="restore_entry_issuers.rejectRaw"; attribute :>> lemma="RestoreIssuer.rejectRawPreserves"; attribute :>> scope="typed AST; source origin/witness authority external"; }
part binding24:BindingRow { attribute :>> actionName="restore_entry_issuers.recoverPreAdmission"; attribute :>> lemma="RestoreIssuer.recoverPreAdmissionPreserves"; attribute :>> scope="typed AST; source origin/witness authority external"; }
part def ProofRow { attribute key:String; attribute lemma:String; }
part proof0:ProofRow { attribute :>> key="stepPreserves"; attribute :>> lemma="RestoreIssuer.stepPreserves"; }
part proof1:ProofRow { attribute :>> key="reachableSafe"; attribute :>> lemma="RestoreIssuer.reachableSafe"; }
part proof2:ProofRow { attribute :>> key="reservationNeedsCarrier"; attribute :>> lemma="RestoreIssuer.reservationNeedsCarrier"; }
part proof3:ProofRow { attribute :>> key="publishedCarrierTracksGc"; attribute :>> lemma="RestoreIssuer.publishedCarrierTracksGc"; }
part proof4:ProofRow { attribute :>> key="rawCannotReserve"; attribute :>> lemma="RestoreIssuer.rawCannotReserve"; }
part proof5:ProofRow { attribute :>> key="reusedEntryDoesNotIssue"; attribute :>> lemma="RestoreIssuer.reusedEntryDoesNotIssue"; }
part proof6:ProofRow { attribute :>> key="unknownRetainsCarrier"; attribute :>> lemma="RestoreIssuer.unknownRetainsCarrier"; }
part proof7:ProofRow { attribute :>> key="sourceReleaseNeedsPublication"; attribute :>> lemma="RestoreIssuer.sourceReleaseNeedsPublication"; }
part proof8:ProofRow { attribute :>> key="completedMarkerClosed"; attribute :>> lemma="RestoreIssuer.completedMarkerClosed"; }
part proof9:ProofRow { attribute :>> key="entryAgreement"; attribute :>> lemma="RestoreIngressBridge.entryAgreement"; }
part proof10:ProofRow { attribute :>> key="admittedSuccessorSafe"; attribute :>> lemma="RestoreIngressBridge.admittedSuccessorSafe"; }
part proof11:ProofRow { attribute :>> key="admittedRoots"; attribute :>> lemma="RestoreIngressBridge.admittedRoots"; }
part proof12:ProofRow { attribute :>> key="oldWitnessDoesNotFollowAmbient"; attribute :>> lemma="RestoreIngressBridge.oldWitnessDoesNotFollowAmbient"; }
part proof13:ProofRow { attribute :>> key="otherGuardUntouched"; attribute :>> lemma="RestoreGuardAlgebra.otherGuardUntouched"; }
part proof14:ProofRow { attribute :>> key="reuseAgreement"; attribute :>> lemma="RestoreIngressBridge.reuseAgreement"; }
part proof15:ProofRow { attribute :>> key="schedulerBindingAgreement"; attribute :>> lemma="RestoreIngressBridge.schedulerBindingAgreement"; }
part proof16:ProofRow { attribute :>> key="navigationBindingAgreement"; attribute :>> lemma="RestoreIngressBridge.navigationBindingAgreement"; }
part def RouteRow { attribute component:String; attribute actionName:String; attribute lemma:String; attribute producerAnchor:String; attribute obligationId:String; }
part route0:RouteRow { attribute :>> component="entry"; attribute :>> actionName="restore_entry_issuers.classifyFresh"; attribute :>> lemma="RestoreIssuer.classifyFreshPreserves"; attribute :>> producerAnchor="raw-return"; attribute :>> obligationId="RI-entry"; }
part route1:RouteRow { attribute :>> component="entry"; attribute :>> actionName="restore_entry_issuers.classifyNavigation"; attribute :>> lemma="RestoreIssuer.classifyNavigationPreserves"; attribute :>> producerAnchor="wind"; attribute :>> obligationId="RI-entry"; }
part route2:RouteRow { attribute :>> component="entry"; attribute :>> actionName="restore_entry_issuers.classifyScheduler"; attribute :>> lemma="RestoreIssuer.classifySchedulerPreserves"; attribute :>> producerAnchor="thread-schedule"; attribute :>> obligationId="RI-entry"; }
part route3:RouteRow { attribute :>> component="entry"; attribute :>> actionName="restore_entry_issuers.classifyConversion"; attribute :>> lemma="RestoreIssuer.classifyConversionPreserves"; attribute :>> producerAnchor="sfun-error"; attribute :>> obligationId="RI-entry"; }
part route4:RouteRow { attribute :>> component="entry"; attribute :>> actionName="restore_entry_issuers.classifyForeign"; attribute :>> lemma="RestoreIssuer.classifyForeignPreserves"; attribute :>> producerAnchor="tcl-entry"; attribute :>> obligationId="RI-entry"; }
part route5:RouteRow { attribute :>> component="roots"; attribute :>> actionName="restore_entry_issuers.pinSource"; attribute :>> lemma="RestoreIssuer.pinSourcePreserves"; attribute :>> producerAnchor="rc-register"; attribute :>> obligationId="RI-roots"; }
part route6:RouteRow { attribute :>> component="roots"; attribute :>> actionName="restore_entry_issuers.publishCarrier"; attribute :>> lemma="RestoreIssuer.publishCarrierPreserves"; attribute :>> producerAnchor="rc-scan"; attribute :>> obligationId="RI-roots"; }
part route7:RouteRow { attribute :>> component="roots"; attribute :>> actionName="restore_entry_issuers.gcPublished"; attribute :>> lemma="RestoreIssuer.gcPublishedPreserves"; attribute :>> producerAnchor="startup-scan"; attribute :>> obligationId="RI-roots"; }
part route8:RouteRow { attribute :>> component="guard"; attribute :>> actionName="restore_entry_issuers.reserveGuard"; attribute :>> lemma="RestoreIssuer.reserveGuardPreserves"; attribute :>> producerAnchor="sfun-generator"; attribute :>> obligationId="RI-execution"; }
part route9:RouteRow { attribute :>> component="guard"; attribute :>> actionName="restore_entry_issuers.allocateMarker"; attribute :>> lemma="RestoreIssuer.allocateMarkerPreserves"; attribute :>> producerAnchor="reload"; attribute :>> obligationId="RI-execution"; }
part route10:RouteRow { attribute :>> component="guard"; attribute :>> actionName="restore_entry_issuers.exceptionToOwner"; attribute :>> lemma="RestoreIssuer.exceptionToOwnerPreserves"; attribute :>> producerAnchor="call"; attribute :>> obligationId="RI-execution"; }
part route11:RouteRow { attribute :>> component="guard"; attribute :>> actionName="restore_entry_issuers.reuseExisting"; attribute :>> lemma="RestoreIssuer.reuseExistingPreserves"; attribute :>> producerAnchor="graft-wrapper"; attribute :>> obligationId="RI-execution"; }
part def Need { attribute obligationId:String; attribute kind:String; attribute subjectPath:String; attribute subjectScope:String; ref owner:Owner; }
part formal:Need { attribute :>> obligationId="RI-formal"; attribute :>> kind="induction"; attribute :>> subjectPath="dev/refactoring/modern-c/models/lean/RestoreIssuer.lean"; attribute :>> subjectScope="bootstrap root custody and modeled moving-GC safety"; ref :>> owner=guardOwner; }
part bridge:Need { attribute :>> obligationId="RI-bridge"; attribute :>> kind="composition"; attribute :>> subjectPath="dev/refactoring/modern-c/models/lean/RestoreIngressBridge.lean"; attribute :>> subjectScope="admitted bootstrap to earlier two-ticket entry; explicit relation premises"; ref :>> owner=guardOwner; }
part ingress:Need { attribute :>> obligationId="RI-entry"; attribute :>> kind="source"; attribute :>> subjectPath="vendor/gambit/gsc/_t-c-2.scm"; attribute :>> subjectScope="all direct indirect and raw caller-role provenance and admission"; ref :>> owner=entryOwner; }
part execution:Need { attribute :>> obligationId="RI-execution"; attribute :>> kind="source"; attribute :>> subjectPath="vendor/gambit/lib/setup.c"; attribute :>> subjectScope="stable reserve and exit witness issuers including exceptional branches"; ref :>> owner=guardOwner; }
part roots:Need { attribute :>> obligationId="RI-roots"; attribute :>> kind="source"; attribute :>> subjectPath="vendor/gambit/lib/memory/root-origins.inc"; attribute :>> subjectScope="no-allocation bootstrap and mutable source/target scan epochs plus all FFI arguments"; ref :>> owner=rootsOwner; }
part platform:Need { attribute :>> obligationId="RI-platform"; attribute :>> kind="platform"; attribute :>> subjectPath="dev/refactoring/modern-c/language-baseline-design.org"; attribute :>> subjectScope="C23 linearization and generated Darwin correspondence; conditional dynamic closure backend"; ref :>> owner=guardOwner; }
part emission:Need { attribute :>> obligationId="RI-emission"; attribute :>> kind="equivalence"; attribute :>> subjectPath="dev/refactoring/modern-c/restore-entry-guard-design.org"; attribute :>> subjectScope="all late callbacks and writer closure before normalization retirement"; ref :>> owner=entryOwner; }
}
