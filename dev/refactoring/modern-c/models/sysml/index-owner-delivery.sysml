package GambitIndexOwnerDelivery {
  private import ScalarValues::*;
  ref part creation = GambitHashIndexOwnership::creation;
  ref part repair = GambitHashIndexOwnership::repair;
  ref part scheme = GambitHashIndexOwnership::scheme;
  attribute scope:String="Exactly seven vendor paths on db7e3425: four already bootstrapped production paths include/gambit.h.in, lib/_gambit#.scm, lib/_system.scm, lib/_mem/weak-tables.inc and three native Scheme tests tests/smp/gc/scheme-index-gc.scm, primitive-table.scm and index-owner-contract.scm. Tests live and ship in Gambit, not as SMP Evidence fixtures or a patch delivery. Preserve every other staged and working research file.";
  attribute stage:String="Behavioral bootstrap prerequisite after memory organization; establish an immutable runtime REV before starting its own twelve-requirement campaign. Native identity traversal, worker separation and CFFI remain separate source cuts.";
  attribute formalDuty:String="Reuse hash-index ownership's conditional semantic transport/counter-law and finite schedule duties without new QNT or Lean models. Native SysML selects this submission's five gates; ASCENT checks source/tree/profile/artifact/evidence joins and missing/stale/model-only controls. LLM source review supplies the four actual constructor/GC consumer anchors, not native execution credit.";
  part def Need { ref part gate:GambitCommitGates::Gate; attribute id:String; attribute method:String; attribute artifact:String; attribute scope:String; }
  part source:Need { ref part :>> gate=GambitCommitGates::tests; attribute :>> id="I-SOURCE"; attribute :>> method="source-refinement"; attribute :>> artifact="evidence/refactoring/modern-c/index-owner-submission.json"; attribute :>> scope="exact-seven-path-tree; four-production-paths-and-all-existing-canonical-bootstrap-inputs-and-artifacts-match-executed-candidate; three-test-only-additions-have-own-native-validation-and-no-bootstrap-generation-edge; no-mixed-index-content"; }
  part bootstrap:Need { ref part :>> gate=GambitCommitGates::tests; attribute :>> id="I-BOOTSTRAP"; attribute :>> method="native"; attribute :>> artifact="evidence/refactoring/modern-c/bootstrap-index-owner.json"; attribute :>> scope="full-two-pass-from-scratch-exit0-within600-no-heap-or-wait-increase-and-explicit-source-equivalence-to-submission"; }
  part controls:Need { ref part :>> gate=GambitCommitGates::tests; attribute :>> id="I-CONTROLS"; attribute :>> method="native"; attribute :>> artifact="evidence/refactoring/modern-c/index-owner-controls.json"; attribute :>> scope="retained-base-negative-and-candidate32-key-and1588-row-controls; interpreted-and-compiled-construction-resize-copy-retained-weak-and-native-identity-controls; user-hash-not-called-from-GC"; }
  part learning:Need { ref part :>> gate=GambitCommitGates::learning; attribute :>> id="I-LESSON"; attribute :>> method="source-analysis"; attribute :>> artifact="dev/refactoring/modern-c/bootstrap-index-owner.org"; attribute :>> scope="GC-reference-transport-is-not-index-algorithm-ownership; avoid-wrong-linear-rebuild-with-one-existing-flag-bit; no-speedup-or-multicore-closure-inferred"; }
  part processNeed:Need { ref part :>> gate=GambitCommitGates::process; attribute :>> id="I-PROCESS"; attribute :>> method="source-analysis"; attribute :>> artifact="dev/refactoring/modern-c/models/sysml/index-owner-delivery.sysml"; attribute :>> scope="freeze-four-production-and-three-vendor-test-bootstrap-prerequisite-before-own-REV-twelve-requirement-tests; retain-unrelated-research-and-historical-failure"; }
  part models:Need { ref part :>> gate=GambitCommitGates::models; attribute :>> id="I-MODELS"; attribute :>> method="native-model-projection"; attribute :>> artifact="dev/refactoring/modern-c/models/sysml/index-owner-delivery.sysml"; attribute :>> scope="native-SysML-five-gate-scope-and-actual-ASCENT-positive-missing-test-stale-tree-and-model-only-controls; no-duplicate-QNT-Lean"; }
  part questions:Need { ref part :>> gate=GambitCommitGates::questions; attribute :>> id="I-QUESTIONS"; attribute :>> method="source-analysis"; attribute :>> artifact="dev/refactoring/modern-c/bootstrap-index-owner.org"; attribute :>> scope="portable-C-tail-multishot-and-shared-semantics-preserved; stable-Scheme-hash-premise-explicit; native-cursor-old-images-raw-writers-and-full-SMP-not-claimed"; }
}
