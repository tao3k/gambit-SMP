package GambitChunkCapacityCharge { private import ScalarValues::*;
part def SourceRow { attribute key:String; attribute path:String; attribute needle:String; attribute obligation:String; }
part source0:SourceRow { attribute :>> key="threshold-limit"; attribute :>> path="vendor/gambit/lib/mem.c"; attribute :>> needle="alloc_heap_chunk_limit = work->context->mem.alloc_heap_ptr_ + ___MSECTION_CHUNK;"; attribute :>> obligation="Fresh threshold starts after preceding marker"; }
part source1:SourceRow { attribute :>> key="threshold-object"; attribute :>> path="vendor/gambit/lib/mem.c"; attribute :>> needle="if (alloc >= alloc_heap_chunk_limit)"; attribute :>> obligation="Object and captured-frame paths are the only threshold close callers"; }
part source2:SourceRow { attribute :>> key="no-fit"; attribute :>> path="vendor/gambit/lib/mem.c"; attribute :>> needle="work->context->mem.alloc_heap_limit_-alloc < required"; attribute :>> obligation="The early close caller is reserve_copy, before obtaining the next grant"; }
part source3:SourceRow { attribute :>> key="close-marker"; attribute :>> path="vendor/gambit/lib/mem.c"; attribute :>> needle="*work->context->mem.alloc_heap_ptr_++ = NULL_CHUNK_LINK;"; attribute :>> obligation="Empty close still consumes marker; count it even if no chunk is queued"; }
part source4:SourceRow { attribute :>> key="prepare-prefix"; attribute :>> path="vendor/gambit/lib/mem.c"; attribute :>> needle="*work->context->mem.alloc_heap_ptr_++ = NULL_CHUNK_LINK; /* link of msection's first chunk */"; attribute :>> obligation="Prefix word is not copied payload or a threshold charge"; }
part source5:SourceRow { attribute :>> key="prepare-slack"; attribute :>> path="vendor/gambit/lib/mem.c"; attribute :>> needle="work->context->mem.alloc_heap_limit_ -= 2;"; attribute :>> obligation="Two end markers do not imply two chunk births"; }
part source6:SourceRow { attribute :>> key="cancel-private"; attribute :>> path="vendor/gambit/lib/mem.c"; attribute :>> needle="return begin;"; attribute :>> obligation="Cancellation restores grant begin only; earlier close/prepare remains charged"; }
part source7:SourceRow { attribute :>> key="cancel-after-fit"; attribute :>> path="vendor/gambit/lib/mem.c"; attribute :>> needle="alloc = cancel_copy(work,&grant);"; attribute :>> obligation="Lost object forwarding never refunds a section/node already started"; }
part source8:SourceRow { attribute :>> key="frame-grant"; attribute :>> path="vendor/gambit/lib/mem.c"; attribute :>> needle="grant = reserve_copy(work,alloc,words,0);"; attribute :>> obligation="Frame body and extra slots consume allocation spans"; }
part source9:SourceRow { attribute :>> key="padding"; attribute :>> path="vendor/gambit/lib/mem.c"; attribute :>> needle="work->copy_padding_words_ += (grant->past-grant->begin)-(grant->words+1);"; attribute :>> obligation="A counts committed physical spans including padding, not just Scheme payload"; }
part source10:SourceRow { attribute :>> key="counter-check"; attribute :>> path="vendor/gambit/lib/mem.c"; attribute :>> needle="work->copy_reserved_words_-work->copy_cancelled_words_ !="; attribute :>> obligation="Post-weak diagnostic is not a prospective capacity certificate"; }
part source11:SourceRow { attribute :>> key="initial-visits"; attribute :>> path="vendor/gambit/lib/mem.c"; attribute :>> needle="nb_msections_assigned = np*2;"; attribute :>> obligation="Initial prepare calls are already included in L"; }
part source12:SourceRow { attribute :>> key="frozen"; attribute :>> path="vendor/gambit/lib/mem.c"; attribute :>> needle="participant->phase = ___GC_ROOTS_FROZEN;"; attribute :>> obligation="Candidate preflight collective is after frozen barrier before setup side effects"; }
part source13:SourceRow { attribute :>> key="flip"; attribute :>> path="vendor/gambit/lib/mem.c"; attribute :>> needle="tospace_offset = fromspace_offset;"; attribute :>> obligation="Pool plan must be accepted before flip and all setup mutations"; }
part source14:SourceRow { attribute :>> key="strong-done"; attribute :>> path="vendor/gambit/lib/mem.c"; attribute :>> needle="garbage_collect_mark_strong_phase (work);"; attribute :>> obligation="Following real barrier does not reset worker cursors or node occupancy"; }
part source15:SourceRow { attribute :>> key="weak-producers"; attribute :>> path="vendor/gambit/lib/mem.c"; attribute :>> needle="process_wills (work);"; attribute :>> obligation="Weak tracing resumes same allocator state and may allocate further"; }
part source16:SourceRow { attribute :>> key="restore-stack"; attribute :>> path="vendor/gambit/lib/mem.c"; attribute :>> needle="while (p1 != start)\n    *--p2 = *--p1;"; attribute :>> obligation="move_continuation copies stack data; it is not a heap chunk birth"; }
part source17:SourceRow { attribute :>> key="restore-heap"; attribute :>> path="vendor/gambit/lib/mem.c"; attribute :>> needle="if (alloc_heap_ptr > alloc_heap_limit - ___MSECTION_FUDGE)"; attribute :>> obligation="Post-GC restoration next_heap_msection has no prepare_heap_msection caller; cannot invent a node charge"; }
part source18:SourceRow { attribute :>> key="custom"; attribute :>> path="vendor/gambit/lib/mem.c"; attribute :>> needle="return custom_msection_alloc ();"; attribute :>> obligation="Uncertified repeated visits invalidate finite list-derived L"; }
part source19:SourceRow { attribute :>> key="shared-fallback"; attribute :>> path="vendor/gambit/lib/mem.c"; attribute :>> needle="result = ms;"; attribute :>> obligation="Current allocator can use one stack section as heap; no double ownership assumed"; }
part source20:SourceRow { attribute :>> key="shared-stop"; attribute :>> path="vendor/gambit/lib/mem.c"; attribute :>> needle="if (stack_msection == heap_msection)"; attribute :>> obligation="After sharing exhaustion, default allocator terminates; no infinite legitimate fallback lease"; }
part source21:SourceRow { attribute :>> key="K"; attribute :>> path="vendor/gambit/lib/mem.h"; attribute :>> needle="#define ___MSECTION_BIGGEST     255"; attribute :>> obligation="Selected source K; effective build-profile mapping open"; }
part source22:SourceRow { attribute :>> key="H"; attribute :>> path="vendor/gambit/lib/mem.h"; attribute :>> needle="#define ___MSECTION_SIZE        131072"; attribute :>> obligation="Half section H=65536 is a conservative span ceiling"; }
part source23:SourceRow { attribute :>> key="native-gate"; attribute :>> path="vendor/gambit/include/gambit.h.in"; attribute :>> needle="__sync_val_compare_and_swap(p,oldval,newval)"; attribute :>> obligation="Existing adapter is not portable C11 qualification"; }
part def CallRow { attribute key:String; attribute callerName:String; attribute callee:String; attribute siteCount:String; attribute effect:String; }
part call0:CallRow { attribute :>> key="object-end"; attribute :>> callerName="mark_array"; attribute :>> callee="end_heap_chunk"; attribute :>> siteCount="1"; attribute :>> effect="Threshold closure then immediate start"; }
part call1:CallRow { attribute :>> key="frame-end"; attribute :>> callerName="mark_captured_continuation_locked"; attribute :>> callee="end_heap_chunk"; attribute :>> siteCount="1"; attribute :>> effect="Threshold closure after frame commit; backfill custody independent"; }
part call2:CallRow { attribute :>> key="early-end"; attribute :>> callerName="reserve_copy"; attribute :>> callee="end_heap_chunk"; attribute :>> siteCount="1"; attribute :>> effect="No-fit, including zero-span chunk"; }
part call3:CallRow { attribute :>> key="object-start"; attribute :>> callerName="mark_array"; attribute :>> callee="start_heap_chunk"; attribute :>> siteCount="1"; attribute :>> effect="New node birth after threshold end"; }
part call4:CallRow { attribute :>> key="frame-start"; attribute :>> callerName="mark_captured_continuation_locked"; attribute :>> callee="start_heap_chunk"; attribute :>> siteCount="1"; attribute :>> effect="New node birth after threshold end"; }
part call5:CallRow { attribute :>> key="lease-start"; attribute :>> callerName="prepare_heap_msection"; attribute :>> callee="start_heap_chunk"; attribute :>> siteCount="1"; attribute :>> effect="Exactly one initial or later lease birth"; }
part call6:CallRow { attribute :>> key="initial-prepare"; attribute :>> callerName="setup_stack_heap_vmstate"; attribute :>> callee="prepare_heap_msection"; attribute :>> siteCount="1"; attribute :>> effect="Loop repeats P times; site count is not dynamic event count"; }
part call7:CallRow { attribute :>> key="next-prepare"; attribute :>> callerName="reserve_copy"; attribute :>> callee="prepare_heap_msection"; attribute :>> siteCount="1"; attribute :>> effect="One per successful no-fit visit; prepare failure keeps custody"; }
part call8:CallRow { attribute :>> key="stack-setup-exclusion"; attribute :>> callerName="___setup_mem_pstate"; attribute :>> callee="next_stack_msection"; attribute :>> siteCount="1"; attribute :>> effect="Only literal direct stack-section advance caller; exclude concurrent processor setup from admitted tracing profile"; }
part def ChargeRow { attribute key:String; attribute mechanism:String; attribute bound:String; attribute excluded:String; attribute status:String; }
part charge0:ChargeRow { attribute :>> key="birth-topology"; attribute :>> mechanism="Every start is threshold successor or prepare entry"; attribute :>> bound="starts = T + L"; attribute :>> excluded="No extra P when L includes initial prepares"; attribute :>> status="Lexical caller inventory closed in pinned mem.c; effective call graph open"; }
part charge1:ChargeRow { attribute :>> key="threshold"; attribute :>> mechanism="Disjoint committed spans since each start"; attribute :>> bound="255*T <= A; T <= floor(A/255)"; attribute :>> excluded="Uncommitted losing CAS reservations, markers and raw source payload count"; attribute :>> status="Conditional invariant induction proved; physical interval injection open"; }
part charge2:ChargeRow { attribute :>> key="partial-and-empty"; attribute :>> mechanism="Early close changes marker and closes current lease; prepare creates next node"; attribute :>> bound="end = T + E; L = E + open for one slice"; attribute :>> excluded="No second node for a marker; no refund on canceled next grant"; attribute :>> status="Modeled closure and exact lexical callers; exception segment refinement open"; }
part charge3:ChargeRow { attribute :>> key="per-lease"; attribute :>> mechanism="Threshold spans do not cross lease close; phase cut does not close a lease"; attribute :>> bound="B_data <= sum_i(floor(U_i/255)+1)"; attribute :>> excluded="No separate worker increment beyond initial leases"; attribute :>> status="Lean list-sum bound conditional on per-lease charge relation"; }
part charge4:ChargeRow { attribute :>> key="fixed-default"; attribute :>> mechanism="N frozen sections, P initial heap and P initial stack; at most N-2P fresh heap visits plus P stack fallbacks"; attribute :>> bound="L<=N; B_total<=258*N+D for H=65536"; attribute :>> excluded="Custom allocator, concurrent resize/extension, stack reassignment or GC reentry"; attribute :>> status="Derived under explicit profile; native issuer not yet implemented"; }
part charge5:ChargeRow { attribute :>> key="phase-carry"; attribute :>> mechanism="Strong and weak share cursor, span, lease and node identities"; attribute :>> bound="254+1 threshold requires one whole charge; preserve prior starts and visits"; attribute :>> excluded="Separately flooring phase byte totals or resetting open span"; attribute :>> status="Cut preservation and negative control proved"; }
part charge6:ChargeRow { attribute :>> key="restoration"; attribute :>> mechanism="Actual move_continuation only changes stack cursor; later heap restore does not prepare a chunk"; attribute :>> bound="No invented additional start from these two endpoints"; attribute :>> excluded="Future redesign may add a new producer class only with explicit budget"; attribute :>> status="Source-specific classification; future users still matter for lifetime"; }
part def ReceiptRow { attribute key:String; attribute issuer:String; attribute condition:String; attribute failure:String; attribute gap:String; }
part receipt0:ReceiptRow { attribute :>> key="preflight-cut"; attribute :>> issuer="Frozen-roster coordinator plus lease/pool owners"; attribute :>> condition="After roots-frozen barrier, before any setup flip or still-list mutations; all participants share decision"; attribute :>> failure="OOM/rejection collectively retains old parity and roots; no processor-only return"; attribute :>> gap="Existing path has no such allocation receipt or collective branch"; }
part receipt1:ReceiptRow { attribute :>> key="manifest"; attribute :>> issuer="Storage owner"; attribute :>> condition="N stable, acyclic unique section list, finite default path, no custom allocator, no intervening stack reassignment"; attribute :>> failure="Unknown producer/profile or capacity overflow rejects signature"; attribute :>> gap="Raw struct availability is not proof of ownership or absence of external writer"; }
part receipt2:ReceiptRow { attribute :>> key="capacity"; attribute :>> issuer="Pool owner plus charge-class auditor"; attribute :>> condition="Per-lease U, K/profile, starts before forwarding, checked bytes, D dummy records, allocation success"; attribute :>> failure="Post-forward failure retains node/copy/Tail; cannot roll back accepted graph"; attribute :>> gap="No native allocation-plan implementation or C11 handoff proof"; }
part receipt3:ReceiptRow { attribute :>> key="weak-continuity"; attribute :>> issuer="Every worker allocator owner plus stage coordinator"; attribute :>> condition="Same epoch, same section/start/cursor, accumulated spans, retained nodes and grants/Tail accounted"; attribute :>> failure="Do not re-sign a fresh pool or refund old markers at strong cut"; attribute :>> gap="Model carries physical counters; exact source snapshot and completion proof open"; }
part receipt4:ReceiptRow { attribute :>> key="reclaim"; attribute :>> issuer="Existing pool lifecycle coordinator"; attribute :>> condition="Capacity closure plus work completion, users closed, head detached, receipts and borrowers gone"; attribute :>> failure="Unknown result retains old epoch; reentry may prevent completion"; attribute :>> gap="Capacity proof does not replace old last-user and generation obligations"; }
part def MemoryRow { attribute key:String; attribute ordering:String; attribute obligation:String; attribute gap:String; }
part memory0:MemoryRow { attribute :>> key="owner-counters"; attribute :>> ordering="Owner-private committed cursor and local charge counters"; attribute :>> obligation="Do not add a global atomic on every payload word; materialize stable snapshot at collective cut"; attribute :>> gap="No native local-counter layout generated"; }
part memory1:MemoryRow { attribute :>> key="preflight-publish"; attribute :>> ordering="Initialize immutable plan then release; every participant acquire and acknowledge same generation"; attribute :>> obligation="Failure branch must be collective before setup, not coordinator-only early return"; attribute :>> gap="Exact BARRIER/atomic adapter and failure semantics open"; }
part memory2:MemoryRow { attribute :>> key="phase-carry"; attribute :>> ordering="All worker final local writes before release acknowledgement; next phase consumes after acquire"; attribute :>> obligation="Cut snapshot includes open-span remainder, current node, physical interval and outstanding tasks"; attribute :>> gap="Phase enum alone does not prove publication or initialization closure"; }
part memory3:MemoryRow { attribute :>> key="birth-ledger"; attribute :>> ordering="Reserve child node and task before parent settlement / forwarding; synchronize queue via gate"; attribute :>> obligation="Threshold or lease birth is paired with exactly one root or derived old-pool reserve"; attribute :>> gap="Native indivisible segment and task identity open"; }
part memory4:MemoryRow { attribute :>> key="overflow"; attribute :>> ordering="Checked native cardinality and byte arithmetic before admission"; attribute :>> obligation="Mathematical integer division and list lengths do not prove size_t safety"; attribute :>> gap="Generation wrap remains fail/retain; no silent rollover"; }
part def GainRow { attribute key:String; attribute avoided:String; attribute added:String; attribute condition:String; }
part gain0:GainRow { attribute :>> key="tighter-bound"; attribute :>> avoided="Remove duplicated initial-worker allowance when visits include initial prepares"; attribute :>> added="Retain exact per-lease budget and caller classification"; attribute :>> condition="Against preceding bound saves up to P data-record allowances at equal L"; }
part gain1:GainRow { attribute :>> key="finite-budget"; attribute :>> avoided="Dense one-node-per-word ceiling unnecessary under qualified topology"; attribute :>> added="At three 8-byte pointer fields, >=24*(258*N+D) bytes reserved for selected full-section plan"; attribute :>> condition="258N+D is a capacity choice under profile; actual stride/pins add overhead"; }
part gain2:GainRow { attribute :>> key="normalized-space"; attribute :>> avoided="Fields for 258 nodes per full half-section: 6192 bytes, ~1.181% of 524288 bytes"; attribute :>> added="Dummy records, pool metadata, retained epochs and allocator rounding additional"; attribute :>> condition="Arithmetic only, not actual live heap fraction or measured resident memory"; }
part gain3:GainRow { attribute :>> key="no-rollback-tax"; attribute :>> avoided="Cancellation reuses current open-node reservation; no new record per failed copy CAS"; attribute :>> added="Stable grant ownership and charge-preserving rollback"; attribute :>> condition="Earlier no-fit/prepare remains retained even if next copy loses"; }
part gain4:GainRow { attribute :>> key="phase-reuse"; attribute :>> avoided="No second node pool and no repeated threshold charge at strong/weak transition"; attribute :>> added="One local stable snapshot and existing collective reuse where proven"; attribute :>> condition="Never remove barriers based solely on arithmetic"; }
part gain5:GainRow { attribute :>> key="net-benefit"; attribute :>> avoided="Ordinary C classifiers and bounded native pool can avoid heap-wide atomic conversion"; attribute :>> added="Plan validation, per-start reservation, queue records, memory pressure and lifetime coordination"; attribute :>> condition="Positive only if saved work exceeds all transport and extra-GC costs; no timings claimed"; }
part def ContractRow { attribute fromNode:String; attribute toNode:String; attribute custody:String; }
part contract0:ContractRow { attribute :>> fromNode="frozen-roster"; attribute :>> toNode="manifest"; attribute :>> custody="Freeze finite leases and complete producer classes"; }
part contract1:ContractRow { attribute :>> fromNode="manifest"; attribute :>> toNode="capacity-plan"; attribute :>> custody="Sum per-lease threshold and prepare budgets; checked allocation"; }
part contract2:ContractRow { attribute :>> fromNode="capacity-plan"; attribute :>> toNode="collective-admit"; attribute :>> custody="All participants see the same success or failure before flip"; }
part contract3:ContractRow { attribute :>> fromNode="collective-admit"; attribute :>> toNode="copy-owner"; attribute :>> custody="One open node reservation precedes forwarding"; }
part contract4:ContractRow { attribute :>> fromNode="copy-owner"; attribute :>> toNode="threshold-close"; attribute :>> custody="Committed spans uniquely charge a new successor node"; }
part contract5:ContractRow { attribute :>> fromNode="copy-owner"; attribute :>> toNode="early-close"; attribute :>> custody="Partial or empty close retains prior node and marker"; }
part contract6:ContractRow { attribute :>> fromNode="early-close"; attribute :>> toNode="lease-prepare"; attribute :>> custody="Preparing next lease issues one new node"; }
part contract7:ContractRow { attribute :>> fromNode="threshold-close"; attribute :>> toNode="same-pool-ledger"; attribute :>> custody="Pair birth with root/child reserve exactly once"; }
part contract8:ContractRow { attribute :>> fromNode="lease-prepare"; attribute :>> toNode="same-pool-ledger"; attribute :>> custody="No separate acceptance on queue publication"; }
part contract9:ContractRow { attribute :>> fromNode="same-pool-ledger"; attribute :>> toNode="weak-continuity"; attribute :>> custody="Carry old occupancy plus unfinished physical span"; }
part contract10:ContractRow { attribute :>> fromNode="weak-continuity"; attribute :>> toNode="retire-cut"; attribute :>> custody="Allocation close and old last-user obligations both required"; }
part def ObligationRow { attribute key:String; attribute status:String; attribute scope:String; attribute gap:String; }
part obligation0:ObligationRow { attribute :>> key="callers"; attribute :>> status="checked-snapshot"; attribute :>> scope="All literal start/end/prepare callers in pinned mem.c"; attribute :>> gap="Lexical evidence does not verify preprocessed arbitrary C callbacks"; }
part obligation1:ObligationRow { attribute :>> key="charge"; attribute :>> status="conditional-proved"; attribute :>> scope="Typed AST all-step invariants, floor and per-lease arithmetic"; attribute :>> gap="Inject real intervals and visit permissions without alias/reuse"; }
part obligation2:ObligationRow { attribute :>> key="composition"; attribute :>> status="conditional-proved"; attribute :>> scope="Guarded charge/pool product and paired root/child births"; attribute :>> gap="C instruction-level coupling, interrupted segments and identity mapping open"; }
part obligation3:ObligationRow { attribute :>> key="default-profile"; attribute :>> status="conditional-source-argument"; attribute :>> scope="N frozen, default allocator, fixed stacks during strong/weak"; attribute :>> gap="Prove no external writers or native GC reentry; reject uncertified profile"; }
part obligation4:ObligationRow { attribute :>> key="C11"; attribute :>> status="open"; attribute :>> scope="Owner snapshots and collective release/acquire decisions"; attribute :>> gap="No weak-memory execution checker or machine-code receipt"; }
part obligation5:ObligationRow { attribute :>> key="net-benefit"; attribute :>> status="open"; attribute :>> scope="Memory bounds and per-birth cost terms"; attribute :>> gap="No runtime implementation native test or performance qualification"; }
part def BindingRow { attribute actionName:String; attribute lemma:String; attribute targetStep:String; attribute simulation:String; }
part binding0:BindingRow { attribute :>> actionName="chunk_capacity_charge.reserveOne"; attribute :>> lemma="CapacityCharge.reserveOnePreserves"; attribute :>> targetStep="chunk_node_pool.stutter"; attribute :>> simulation="CapacityChargeComposition.reserveOneCouples"; }
part binding1:BindingRow { attribute :>> actionName="chunk_capacity_charge.reserveNear"; attribute :>> lemma="CapacityCharge.reserveNearPreserves"; attribute :>> targetStep="chunk_node_pool.stutter"; attribute :>> simulation="CapacityChargeComposition.reserveNearCouples"; }
part binding2:BindingRow { attribute :>> actionName="chunk_capacity_charge.reserveOvershoot"; attribute :>> lemma="CapacityCharge.reserveOvershootPreserves"; attribute :>> targetStep="chunk_node_pool.stutter"; attribute :>> simulation="CapacityChargeComposition.reserveOvershootCouples"; }
part binding3:BindingRow { attribute :>> actionName="chunk_capacity_charge.publishForward"; attribute :>> lemma="CapacityCharge.publishForwardPreserves"; attribute :>> targetStep="chunk_node_pool.stutter"; attribute :>> simulation="CapacityChargeComposition.publishForwardCouples"; }
part binding4:BindingRow { attribute :>> actionName="chunk_capacity_charge.commit"; attribute :>> lemma="CapacityCharge.commitPreserves"; attribute :>> targetStep="chunk_node_pool.stutter"; attribute :>> simulation="CapacityChargeComposition.commitCouples"; }
part binding5:BindingRow { attribute :>> actionName="chunk_capacity_charge.cancel"; attribute :>> lemma="CapacityCharge.cancelPreserves"; attribute :>> targetStep="chunk_node_pool.stutter"; attribute :>> simulation="CapacityChargeComposition.cancelCouples"; }
part binding6:BindingRow { attribute :>> actionName="chunk_capacity_charge.closeThreshold"; attribute :>> lemma="CapacityCharge.closeThresholdPreserves"; attribute :>> targetStep="chunk_node_pool.reserve"; attribute :>> simulation="CapacityChargeComposition.thresholdRoot"; }
part binding7:BindingRow { attribute :>> actionName="chunk_capacity_charge.observeNoFit"; attribute :>> lemma="CapacityCharge.observeNoFitPreserves"; attribute :>> targetStep="chunk_node_pool.stutter"; attribute :>> simulation="CapacityChargeComposition.observeNoFitCouples"; }
part binding8:BindingRow { attribute :>> actionName="chunk_capacity_charge.closeEarly"; attribute :>> lemma="CapacityCharge.closeEarlyPreserves"; attribute :>> targetStep="chunk_node_pool.stutter"; attribute :>> simulation="CapacityChargeComposition.closeEarlyCouples"; }
part binding9:BindingRow { attribute :>> actionName="chunk_capacity_charge.advanceVisit"; attribute :>> lemma="CapacityCharge.advanceVisitPreserves"; attribute :>> targetStep="chunk_node_pool.reserve"; attribute :>> simulation="CapacityChargeComposition.visitRoot"; }
part binding10:BindingRow { attribute :>> actionName="chunk_capacity_charge.cutToWeak"; attribute :>> lemma="CapacityCharge.cutToWeakPreserves"; attribute :>> targetStep="chunk_node_pool.stutter"; attribute :>> simulation="CapacityChargeComposition.cutToWeakCouples"; }
part binding11:BindingRow { attribute :>> actionName="chunk_capacity_charge.closeCapacity"; attribute :>> lemma="CapacityCharge.closeCapacityPreserves"; attribute :>> targetStep="chunk_node_pool.stutter"; attribute :>> simulation="CapacityChargeComposition.closeCapacityCouples"; }
part def ProofRow { attribute key:String; attribute lemma:String; attribute scope:String; }
part proof0:ProofRow { attribute :>> key="birth-count"; attribute :>> lemma="CapacityCharge.exactBirthCount"; attribute :>> scope="No extra worker count beyond visits"; }
part proof1:ProofRow { attribute :>> key="floor-bound"; attribute :>> lemma="CapacityCharge.tightCeiling"; attribute :>> scope="Whole-epoch threshold budget"; }
part proof2:ProofRow { attribute :>> key="per-lease"; attribute :>> lemma="CapacityCharge.leaseSumBound"; attribute :>> scope="Conditional sum of per-lease floor budgets"; }
part proof3:ProofRow { attribute :>> key="threshold-space"; attribute :>> lemma="CapacityCharge.thresholdHasSpace"; attribute :>> scope="Threshold event has successor node capacity"; }
part proof4:ProofRow { attribute :>> key="visit-space"; attribute :>> lemma="CapacityCharge.visitHasSpace"; attribute :>> scope="Remaining lease has node capacity"; }
part proof5:ProofRow { attribute :>> key="cut-carry"; attribute :>> lemma="CapacityCharge.cutCarriesState"; attribute :>> scope="Strong cut leaves physical counters unchanged"; }
part proof6:ProofRow { attribute :>> key="cancel"; attribute :>> lemma="CapacityCharge.cancellationKeepsTopology"; attribute :>> scope="Cancel refunds grant, not prior node birth"; }
part proof7:ProofRow { attribute :>> key="fraction-control"; attribute :>> lemma="CapacityCharge.separatelyRoundedPhasesLoseCarry"; attribute :>> scope="Concrete 254+1 phase rounding counterexample"; }
part proof8:ProofRow { attribute :>> key="product"; attribute :>> lemma="CapacityChargeComposition.reachableGood"; attribute :>> scope="Actual old pool plus source-charge abstraction"; }
part proof9:ProofRow { attribute :>> key="threshold-child"; attribute :>> lemma="CapacityChargeComposition.thresholdChild"; attribute :>> scope="Derived child birth after root close"; }
part proof10:ProofRow { attribute :>> key="visit-child"; attribute :>> lemma="CapacityChargeComposition.visitChild"; attribute :>> scope="Derived no-fit successor birth"; }
part proof11:ProofRow { attribute :>> key="retire-control"; attribute :>> lemma="CapacityChargeComposition.lifetimeCutNecessary"; attribute :>> scope="No pool completion while source allocation admission remains open"; }
part history:GambitAssuranceRouting::ModelNeed { ref part :>> owner=GambitAssuranceRelations::modelUse3; attribute :>> obligationId="CC-history"; attribute :>> kind="interleaving"; attribute :>> subjectPath="dev/refactoring/modern-c/models/quint/chunk_capacity_charge.qnt"; attribute :>> subjectScope="Threshold early empty cancellation and strong-weak carry histories"; attribute :>> premise="Research only; conditional formal proof is not native qualification"; }
part induction:GambitAssuranceRouting::ModelNeed { ref part :>> owner=GambitAssuranceRelations::modelUse3; attribute :>> obligationId="CC-induction"; attribute :>> kind="induction"; attribute :>> subjectPath="dev/refactoring/modern-c/models/lean/CapacityCharge.lean"; attribute :>> subjectScope="Actual typed AST step safety and conditional charge arithmetic"; attribute :>> premise="Research only; conditional formal proof is not native qualification"; }
part composition:GambitAssuranceRouting::ModelNeed { ref part :>> owner=GambitAssuranceRelations::modelUse3; attribute :>> obligationId="CC-composition"; attribute :>> kind="induction"; attribute :>> subjectPath="dev/refactoring/modern-c/models/lean/CapacityChargeComposition.lean"; attribute :>> subjectScope="Guarded product with exact preceding NodePool AST"; attribute :>> premise="Research only; conditional formal proof is not native qualification"; }
part projection:GambitAssuranceRouting::ModelNeed { ref part :>> owner=GambitAssuranceRelations::modelUse3; attribute :>> obligationId="CC-projection"; attribute :>> kind="restricted-projection"; attribute :>> subjectPath="dev/refactoring/modern-c/models/lean/CapacityChargeAst.lean"; attribute :>> subjectScope="Typed binding identity plus literal-coefficient multiplication"; attribute :>> premise="Research only; conditional formal proof is not native qualification"; }
part source:GambitAssuranceRouting::ModelNeed { ref part :>> owner=GambitAssuranceRelations::modelUse3; attribute :>> obligationId="CC-source"; attribute :>> kind="source-refinement"; attribute :>> subjectPath="dev/refactoring/modern-c/chunk-capacity-charge-design.org"; attribute :>> subjectScope="Physical disjoint leases and actual collective receipt issuer open"; attribute :>> premise="Research only; conditional formal proof is not native qualification"; }
part platform:GambitAssuranceRouting::ModelNeed { ref part :>> owner=GambitAssuranceRelations::modelUse3; attribute :>> obligationId="CC-platform"; attribute :>> kind="native-memory-order"; attribute :>> subjectPath="dev/refactoring/modern-c/chunk-capacity-charge-design.org"; attribute :>> subjectScope="C11 cut publication generation native arithmetic open"; attribute :>> premise="Research only; conditional formal proof is not native qualification"; }
part def Seam { ref part producer:GambitRuntimeComposition::BlueprintModule; ref part consumer:GambitRuntimeComposition::BlueprintModule; attribute contract:String; attribute modelNeed:String; }
part seam0:Seam { ref part :>> producer=GambitRuntimeComposition::blueprintModule4; ref part :>> consumer=GambitRuntimeComposition::blueprintModule4; attribute :>> contract="Physical charge to old pool task reservation"; attribute :>> modelNeed="CC-composition"; }
part seam1:Seam { ref part :>> producer=GambitRuntimeComposition::blueprintModule4; ref part :>> consumer=GambitRuntimeComposition::blueprintModule5; attribute :>> contract="Frozen cohort collective capacity decision"; attribute :>> modelNeed="CC-source"; }
part seam2:Seam { ref part :>> producer=GambitRuntimeComposition::blueprintModule4; ref part :>> consumer=GambitRuntimeComposition::blueprintModule1; attribute :>> contract="Native allocator profile and snapshot publication"; attribute :>> modelNeed="CC-platform"; }
}
