package GambitLayoutFixturePortability {
  private import ScalarValues::*;
  attribute scope:String="One vendor path: tests/frame-spec.scm. Emit array-member offsetof plus literal index times sizeof actual element instead of compound array-element offsetof. Retain all290 declaration IDs, expected coordinates, target/feature guards and existing test entrypoints. No production source, public name, workflow, heap or timeout changes";
  attribute stage:String="Pre-publication local qualification of the bounded fixture follow-up to bf08f39f. Actual MSVC and five-platform CI are post-push requirements; root-dispatch code remains blocked until that exact new head is all-green";
  attribute formalDuty:String="C array-element layout identity and complete generated-header equivalence, checked against actual consumers and wrong-value controls. No new concurrency protocol or QNT/Lean proof; use native SysML and existing ASCENT five-gate policy";
  attribute benefit:String="Retain independent Scheme-coordinate versus real C-layout assertions while using simple offsetof member syntax accepted by the supported C implementation. Resolve the observed MSVC fixture expression failure without deleting an assertion or changing an expected value. Actual remote MSVC result is not inferred from local Clang";
  attribute addedCost:String="Fifty generated expressions spell array base, literal index and sizeof(actual element); all are compile-time typedef bounds. No runtime allocation, object layout, root scan, native build profile or production code-generation cost is added. Reuse exact existing production binaries/generated products";
  part def Need { ref part gate:GambitCommitGates::Gate; attribute id:String; attribute method:String; attribute artifact:String; attribute scope:String; }
  part source:Need { ref part :>> gate=GambitCommitGates::tests; attribute :>> id="LF-SOURCE"; attribute :>> method="source-refinement"; attribute :>> artifact=".cache/tasks/modern-c-frame-contract/runs/layout-fixture-submission/evidence/source-refinement.json"; attribute :>> scope="Exact one-path delta; complete old/new header equality after independently reversing only50 array-offset spellings; same290 IDs/order/expected constants/guards and unchanged original frame assertions; all production/build/namespace bytes unchanged"; }
  part native:Need { ref part :>> gate=GambitCommitGates::tests; attribute :>> id="LF-NATIVE"; attribute :>> method="native"; attribute :>> artifact=".cache/tasks/modern-c-frame-contract/runs/layout-fixture-local/result.json"; attribute :>> scope="Same workspace/profile/artifact identities; actual GCC/Clang original/fixed normal/lowlevel consumers;20 active wrong-coordinate compile rejections; unchanged existing frame/continuation/root and runtime-role targets. Remote MSVC is not claimed by local qualification"; }
  part learning:Need { ref part :>> gate=GambitCommitGates::learning; attribute :>> id="LF-AUDIT"; attribute :>> method="source-analysis"; attribute :>> artifact="dev/refactoring/modern-c/layout-fixture-portability.org"; attribute :>> scope="Explain concrete C constant-expression portability mechanism, independent oracle, proof identity, benefit, zero runtime impact, necessity of the single file and original remote failure witness"; }
  part processNeed:Need { ref part :>> gate=GambitCommitGates::process; attribute :>> id="LF-PROCESS"; attribute :>> method="source-analysis"; attribute :>> artifact="dev/refactoring/modern-c/layout-fixture-portability.org"; attribute :>> scope="Fixture-only follow-up before root dispatch; precise producer reuse rather than source rebuild. Post-push exact-head CI is required before lifting the successor's predecessor gate"; }
  part models:Need { ref part :>> gate=GambitCommitGates::models; attribute :>> id="LF-MODELS"; attribute :>> method="native-model-projection"; attribute :>> artifact=".cache/tasks/modern-c-frame-contract/runs/layout-fixture-submission/evidence/model.json"; attribute :>> scope="Strict native SysML selects six needs/five gates; actual ASCENT must reject missing needs, stale tree/profile/artifact and model-only evidence. Do not duplicate QNT/Lean for this expression spelling change"; }
  part questions:Need { ref part :>> gate=GambitCommitGates::questions; attribute :>> id="LF-QUESTIONS"; attribute :>> method="source-analysis"; attribute :>> artifact="dev/refactoring/modern-c/layout-fixture-portability.org"; attribute :>> scope="No deleted assertions, weakened expected values, new platform guards, workflow/name/limit changes, false local-MSVC equivalence, source-copy rebuild or inherited SMP success. Root dispatch stays unadmitted until actual new-head CI succeeds"; }
}
