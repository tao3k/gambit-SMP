package GambitCIConsumers {
 private import ScalarValues::*;
 attribute scope:String="Repair CI consumer contracts without runtime, scheduler, workload, timeout or heap changes. Original test manifests remain complete.";
 attribute stage:String="Support only; architecture3/4, SMP1/12. Diagnostic source-core and hosted macOS remain separate before fourth integration admission.";
 attribute formalDuty:String="Native SysML drives existing ASCENT five support gates. Pure evidence/fixture transport changes add no QNT or Lean duplicate obligations.";
 part def Need { attribute id:String; ref part gate:GambitCommitGates::Gate; attribute method:String; attribute artifact:String; attribute scope:String; }
 part tests:Need { attribute :>> id="CONSUMER-TESTS"; ref part :>> gate=GambitCommitGates::tests; attribute :>> method="native"; attribute :>> artifact="evidence/research/retained/modern-c/ci-consumers/receipt.json"; attribute :>> scope="Declared CI consumer cut, not remote/runtime admission"; }
 part learning:Need { attribute :>> id="CONSUMER-LEARNING"; ref part :>> gate=GambitCommitGates::learning; attribute :>> method="source-analysis"; attribute :>> artifact="evidence/research/retained/modern-c/ci-consumers/receipt.json"; attribute :>> scope="Declared CI consumer cut, not remote/runtime admission"; }
 part process:Need { attribute :>> id="CONSUMER-PROCESS"; ref part :>> gate=GambitCommitGates::process; attribute :>> method="source-analysis"; attribute :>> artifact="evidence/research/retained/modern-c/ci-consumers/receipt.json"; attribute :>> scope="Declared CI consumer cut, not remote/runtime admission"; }
 part models:Need { attribute :>> id="CONSUMER-MODELS"; ref part :>> gate=GambitCommitGates::models; attribute :>> method="source-analysis"; attribute :>> artifact="evidence/research/retained/modern-c/ci-consumers/receipt.json"; attribute :>> scope="Declared CI consumer cut, not remote/runtime admission"; }
 part questions:Need { attribute :>> id="CONSUMER-QUESTIONS"; ref part :>> gate=GambitCommitGates::questions; attribute :>> method="source-analysis"; attribute :>> artifact="evidence/research/retained/modern-c/ci-consumers/receipt.json"; attribute :>> scope="Declared CI consumer cut, not remote/runtime admission"; }
 part submission:GambitCommitGates::SubmissionUnit { attribute :>> kind="support"; attribute :>> result=""; attribute :>> progressDelta=0; attribute :>> supportPaths="tests/test_upstream_tests.py;tests/test_gambit_ci.py;evidence/research-audit.json;evidence/research/retained/modern-c/ci-consumers/historical-thread.json;evidence/research/retained/modern-c/ci-consumers/historical-base.json;dev/refactoring/modern-c/models/sysml/ci-consumers.sysml;dev/refactoring/modern-c/ci-consumers.org;dev/refactoring/modern-c/branch-checklist.org;evidence/research/retained/modern-c/ci-consumers/receipt.json"; attribute :>> testModules="tests/test_upstream_tests.py;tests/test_gambit_ci.py"; }
}
