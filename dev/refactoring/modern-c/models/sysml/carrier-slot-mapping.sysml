package GambitCarrierSlotMapping { private import ScalarValues::*;
part def Owner { attribute componentId:String; }
part registryOwner:Owner { attribute :>> componentId="registry"; }
part rootsOwner:Owner { attribute :>> componentId="roots"; }
part lookupOwner:Owner { attribute :>> componentId="lookup"; }
part writerOwner:Owner { attribute :>> componentId="writer"; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-register"; attribute :>> path="vendor/gambit/lib/memory/rc-allocation.inc"; attribute :>> needle="tail->next = h;"; attribute :>> obligation="Plain list insertion requires owner and collector exclusion"; }
part source4:SourceRow { attribute :>> key="rc-free"; attribute :>> path="vendor/gambit/lib/memory/rc-allocation.inc"; attribute :>> needle="if (--h->refcount == 0)"; attribute :>> obligation="Nonatomic decrement and unlink are not safe arbitrary-thread admission"; }
part source5:SourceRow { attribute :>> key="rc-read"; attribute :>> path="vendor/gambit/lib/memory/rc-allocation.inc"; attribute :>> needle="return h->data;"; attribute :>> obligation="Raw native copy is not a registered update slot"; }
part source6:SourceRow { attribute :>> key="rc-write"; attribute :>> path="vendor/gambit/lib/memory/rc-allocation.inc"; attribute :>> needle="h->data = val;"; attribute :>> obligation="All semantic writers must join freeze/generation protocol or deny admission"; }
part source7:SourceRow { attribute :>> key="rc-cleanup"; attribute :>> path="vendor/gambit/lib/memory/rc-allocation.inc"; attribute :>> needle="___HIDDEN void cleanup_rc"; attribute :>> obligation="Bulk cleanup frees chain independent of per-entry leases"; }
part source8:SourceRow { attribute :>> key="rc-scan"; attribute :>> path="vendor/gambit/lib/memory/rc-roots.inc"; attribute :>> needle="mark_array (work, &h->data, 1);"; attribute :>> obligation="Actual GC slot update; target private carrier is not implicitly scanned"; }
part source9:SourceRow { attribute :>> key="retire-refuse"; attribute :>> path="vendor/gambit/lib/memory/capacity-resize.inc"; attribute :>> needle="return 0; /* no freeze receipt for external RC/native borrowers */"; attribute :>> obligation="Current processor retirement refuses nonempty RC rather than manufacturing a lease"; }
part source10:SourceRow { attribute :>> key="pstate-cleanup"; attribute :>> path="vendor/gambit/lib/memory/memory-lifecycle.inc"; attribute :>> needle="free_still_objs (___ps);"; attribute :>> obligation="cleanup_mem_pstate frees still storage before cleanup_rc; not an active-lease release helper"; }
part source11:SourceRow { attribute :>> key="setter-export"; attribute :>> path="vendor/gambit/lib/setup.c"; attribute :>> needle="= ___set_data_rc;"; attribute :>> obligation="Public GSTATE function pointer permits indirect/out-of-tree callers; lexical sites do not close writer authority"; }
part source12:SourceRow { attribute :>> key="register-export"; attribute :>> path="vendor/gambit/lib/setup.c"; attribute :>> needle="= ___register_rc;"; attribute :>> obligation="Public registration ABI is not a stable VM SourceOwner registry"; }
part source13:SourceRow { attribute :>> key="closure-writer"; attribute :>> path="vendor/gambit/lib/os_dyn.c"; attribute :>> needle="___set_data_rc (c_closure, proc);"; attribute :>> obligation="Concrete semantic payload installer, architecture conditional"; }
part source14:SourceRow { attribute :>> key="epoch-limit"; attribute :>> path="vendor/gambit/lib/memory/heap-sections.inc"; attribute :>> needle="if (___vms->gc_round.epoch >= ___MAX_FIX)"; attribute :>> obligation="Existing round identity refuses exhaustion; no unchecked wrapping receipt"; }
part source15:SourceRow { attribute :>> key="epoch-new"; attribute :>> path="vendor/gambit/lib/memory/heap-sections.inc"; attribute :>> needle="___vms->gc_round.epoch++;"; attribute :>> obligation="Round number created at setup, distinct from semantic payload generation"; }
part source16:SourceRow { attribute :>> key="origin-publish"; attribute :>> path="vendor/gambit/lib/memory/heap-sections.inc"; attribute :>> needle="!___gc_root_task_publish(&___vms->gc_root_tasks[i],"; attribute :>> obligation="Publish follows frozen origin; not generic new-source enrollment"; }
part source17:SourceRow { attribute :>> key="origin-claim"; attribute :>> path="vendor/gambit/lib/memory/collection-round.inc"; attribute :>> needle="if (___gc_root_task_claim(task,___vms->gc_round.epoch,owner))"; attribute :>> obligation="Actual claim checks current round and worker owner"; }
part source18:SourceRow { attribute :>> key="origin-finish"; attribute :>> path="vendor/gambit/lib/memory/collection-round.inc"; attribute :>> needle="if (!___gc_root_task_finish(task,___vms->gc_round.epoch,owner))"; attribute :>> obligation="Task finish has exact owner and epoch boundary"; }
part source19:SourceRow { attribute :>> key="origin-thaw"; attribute :>> path="vendor/gambit/lib/memory/collection-round.inc"; attribute :>> needle="if (!___gc_origin_thaw(&___vms->gc_root_tasks[id],___vms->gc_round.epoch))"; attribute :>> obligation="Resume requires completed origin; not a payload-version receipt"; }
part source20:SourceRow { attribute :>> key="view-drain"; attribute :>> path="vendor/gambit/lib/memory/collection-round.inc"; attribute :>> needle="BARRIER(); /* no worker may retain a stopped root view past this cut */"; attribute :>> obligation="Root view grace cut precedes ordinary execution"; }
part source21:SourceRow { attribute :>> key="shrink-cleanup"; attribute :>> path="vendor/gambit/lib/setup.c"; attribute :>> needle="___transfer_retired_still (ps, ___ps);"; attribute :>> obligation="Shrink known join transfers still before cleanup; does not qualify arbitrary native roots"; }
part source22:SourceRow { attribute :>> key="vm-root-retained"; attribute :>> path="vendor/gambit/lib/setup.c"; attribute :>> needle="return; /* do not erase retained source roots through repeated setup */"; attribute :>> obligation="Whole VM cleanup checks resize source requests; generic SourceRegistry not covered"; }
part source23:SourceRow { attribute :>> key="vm-request-slots"; attribute :>> path="vendor/gambit/lib/memory/root-origins.inc"; attribute :>> needle="&___vms->resize_requests[i].thunk"; attribute :>> obligation="All VM request slots scanned independently of participant membership; precedent not generic registry"; }
part source24:SourceRow { attribute :>> key="context-rc-roots"; attribute :>> path="vendor/gambit/lib/memory/root-origins.inc"; attribute :>> needle="mark_rc (work, context);"; attribute :>> obligation="RC roots reached through frozen execution origin"; }
part source25:SourceRow { attribute :>> key="context-startup"; attribute :>> path="vendor/gambit/lib/memory/root-origins.inc"; attribute :>> needle="&context->startup_thunk"; attribute :>> obligation="Startup root remains a stable update slot"; }
part source26:SourceRow { attribute :>> key="root-hook"; attribute :>> path="vendor/gambit/lib/memory/root-origins.inc"; attribute :>> needle="___GC_ROOT_CONTROL(work);"; attribute :>> obligation="Default hook has no storage or code; not proof of generic carrier coverage"; }
part source27:SourceRow { attribute :>> key="origin-layout"; attribute :>> path="vendor/gambit/include/gambit.h.in"; attribute :>> needle="typedef struct ___gc_root_origin_struct"; attribute :>> obligation="Stable context identity and pinned origin storage, not an arbitrary host lease"; }
part source28:SourceRow { attribute :>> key="task-layout"; attribute :>> path="vendor/gambit/include/gambit.h.in"; attribute :>> needle="typedef struct ___gc_root_task_struct"; attribute :>> obligation="Task contains origin pointer, incarnation, epoch, claim state"; }
part source29:SourceRow { attribute :>> key="origin-freeze-body"; attribute :>> path="vendor/gambit/include/gambit.h.in"; attribute :>> needle="___STARTUP_INLINE int ___gc_origin_freeze"; attribute :>> obligation="Real publisher requires physical root-writer stop and exclusive round admission"; }
part source30:SourceRow { attribute :>> key="task-publish-body"; attribute :>> path="vendor/gambit/include/gambit.h.in"; attribute :>> needle="t->origin = o; t->incarnation = o->incarnation; t->epoch = epoch;"; attribute :>> obligation="Descriptor publication assumes exclusive slot reuse and drained prior readers"; }
part source31:SourceRow { attribute :>> key="task-claim-body"; attribute :>> path="vendor/gambit/include/gambit.h.in"; attribute :>> needle="t->incarnation != t->origin->incarnation"; attribute :>> obligation="Claim dereferences descriptor/origin before CAS; not a safe retain of freed storage"; }
part source32:SourceRow { attribute :>> key="task-finish-body"; attribute :>> path="vendor/gambit/include/gambit.h.in"; attribute :>> needle="___gc_cas(&t->claim,owner,2) == owner"; attribute :>> obligation="Exact owner completion within a stable pinned round"; }
part source33:SourceRow { attribute :>> key="origin-thaw-body"; attribute :>> path="vendor/gambit/include/gambit.h.in"; attribute :>> needle="___gc_atomic_load(&t->claim) == 2"; attribute :>> obligation="Completion does not itself supply whole-round resume permission"; }
part source34:SourceRow { attribute :>> key="vm-root-layout"; attribute :>> path="vendor/gambit/include/gambit.h.in"; attribute :>> needle="___gc_root_task gc_root_tasks[___MAX_PROCESSORS];"; attribute :>> obligation="VM allocation stores task descriptors; current task census is processor origins"; }
part source35:SourceRow { attribute :>> key="incarnation-issuer"; attribute :>> path="vendor/gambit/lib/setup.c"; attribute :>> needle="___vms->gc_origins[i].incarnation++;"; attribute :>> obligation="Real context incarnation signer after finite exhaustion check"; }
part source36:SourceRow { attribute :>> key="cas-wrapper"; attribute :>> path="vendor/gambit/include/gambit.h.in"; attribute :>> needle="return ___COMPARE_AND_SWAP_WORD(p,old_value,new_value);"; attribute :>> obligation="Platform-selecting CAS is not an explicit C23 atomic ABI"; }
part source37:SourceRow { attribute :>> key="cas-sync-builtins"; attribute :>> path="vendor/gambit/include/gambit.h.in"; attribute :>> needle="__sync_val_compare_and_swap(p,oldval,newval)"; attribute :>> obligation="One alternative implementation; effective Darwin selection remains open"; }
part source38:SourceRow { attribute :>> key="slot-read"; attribute :>> path="vendor/gambit/lib/memory/copy-reservations.inc"; attribute :>> needle="___WORD obj = *cell;"; attribute :>> obligation="Ordinary root-slot load requires writer and duplicate-scanner exclusion"; }
part source39:SourceRow { attribute :>> key="copy-loser-slot-write"; attribute :>> path="vendor/gambit/lib/memory/copy-reservations.inc"; attribute :>> needle="*cell = ___TAG(___UNTAG_AS(head_now, ___FORW), ___TYP(obj));"; attribute :>> obligation="Forwarding loser still writes the root slot"; }
part source40:SourceRow { attribute :>> key="copy-winner-slot-write"; attribute :>> path="vendor/gambit/lib/memory/copy-reservations.inc"; attribute :>> needle="*cell = ___TAG(alloc - ___REFERENCE_TO_BODY, ___TYP(obj));"; attribute :>> obligation="Forwarding winner writes the root slot before copying all payload"; }
part source41:SourceRow { attribute :>> key="already-forwarded-slot-write"; attribute :>> path="vendor/gambit/lib/memory/copy-reservations.inc"; attribute :>> needle="*cell = ___TAG(___UNTAG_AS(head, ___FORW), ___TYP(obj));"; attribute :>> obligation="Same object in two cells still needs both cell updates"; }
part source42:SourceRow { attribute :>> key="frame-run-lifetime"; attribute :>> path="vendor/gambit/include/gambit.h.in"; attribute :>> needle="module or crosses a safepoint.  Runs preserve mark_array"; attribute :>> obligation="Existing nonallocating root cursor has module and safepoint lifetime constraints"; }
part source43:SourceRow { attribute :>> key="default-root-hook"; attribute :>> path="vendor/gambit/lib/memory/copy-reservations.inc"; attribute :>> needle="#define ___GC_ROOT_CONTROL(work) ((void)0)"; attribute :>> obligation="No general VM carrier registry consumer is supplied by this hook"; }
part def IdentityRow { attribute key:String; attribute structure:String; attribute rule:String; attribute caveat:String; }
part identity0:IdentityRow { attribute :>> key="physical-slot"; attribute :>> structure="VM + StorageId + storage generation + word offset"; attribute :>> rule="Canonicalize writable cell identity, never SCMOBJ contents"; attribute :>> caveat="Storage issuer must prove native address/key adequacy over the admitted universe"; }
part identity1:IdentityRow { attribute :>> key="logical-entry"; attribute :>> structure="DescriptorId + descriptor generation + SlotKey runs"; attribute :>> rule="Multiple entries can reference the same physical cell"; attribute :>> caveat="Root-task deduplication does not merge borrowing or storage ownership"; }
part identity2:IdentityRow { attribute :>> key="snapshot"; attribute :>> structure="CollectorRoundId + frozen registry cut + root policy"; attribute :>> rule="Exactly one scan authority per canonical cell"; attribute :>> caveat="Incompatible strong/weak or layout policies must be rejected or separately proved"; }
part identity3:IdentityRow { attribute :>> key="lookup"; attribute :>> structure="Stable VM index plus fixed lookup identity"; attribute :>> rule="Pin before descriptor dereference; validate active generation before borrow acceptance"; attribute :>> caveat="Finite model has fixed identities and no slot reuse; native ABA proof remains open"; }
part identity4:IdentityRow { attribute :>> key="code"; attribute :>> structure="ModuleHandle + scan ABI + layout fingerprint"; attribute :>> rule="All descriptor and task readers retain scan code until grace"; attribute :>> caveat="Module pointer reachability is not native module unload permission"; }
part def IssuerRow { attribute key:String; attribute proposedIssuer:String; attribute actualSource:String; attribute status:String; attribute responsibility:String; }
part issuer0:IssuerRow { attribute :>> key="storage-key"; attribute :>> proposedIssuer="VM storage registration owner"; attribute :>> actualSource="Existing RC allocation/header and VM fixed arrays; no complete canonical SlotKey issuer found"; attribute :>> status="native gap"; attribute :>> responsibility="Validate extent, alignment, overlap, generation and stable cell storage"; }
part issuer1:IssuerRow { attribute :>> key="registry"; attribute :>> proposedIssuer="VM carrier registry commit owner"; attribute :>> actualSource="register_rc links context RC nodes; GSTATE exports public APIs"; attribute :>> status="native gap"; attribute :>> responsibility="Root candidate, atomically publish complete runs and lifetime references"; }
part issuer2:IssuerRow { attribute :>> key="round"; attribute :>> proposedIssuer="GC origin/round publisher"; attribute :>> actualSource="setup_pstate increments incarnation; heap setup increments epoch and freezes/publishes"; attribute :>> status="partial real source signer"; attribute :>> responsibility="Freeze all writers; snapshot complete root union; pin descriptors"; }
part issuer3:IssuerRow { attribute :>> key="scan"; attribute :>> proposedIssuer="Root-task claimant and completer"; attribute :>> actualSource="gc_root_task_claim and gc_root_task_finish bodies plus mark_execution_roots"; attribute :>> status="real for existing origin tasks only"; attribute :>> responsibility="Unique canonical cell ownership and moving-slot update; parent origin tasks alone insufficient"; }
part issuer4:IssuerRow { attribute :>> key="lookup"; attribute :>> proposedIssuer="Stable registry index admission owner"; attribute :>> actualSource="Raw data_rc/addref_rc paths provide no guarded pre-dereference lookup"; attribute :>> status="native gap"; attribute :>> responsibility="Reject late generation/closed admission without accessing freed descriptor"; }
part issuer5:IssuerRow { attribute :>> key="grace"; attribute :>> proposedIssuer="Collector and native reader grace owners"; attribute :>> actualSource="gc_origin_thaw plus final collective barrier"; attribute :>> status="partial; unrelated FFI readers not covered"; attribute :>> responsibility="Drain root views, lookup pins, borrowers and scan-code readers"; }
part issuer6:IssuerRow { attribute :>> key="cleanup"; attribute :>> proposedIssuer="Slot backing and foreign resource owners"; attribute :>> actualSource="free_still_objs then cleanup_rc; known resize join retains/settles existing resources"; attribute :>> status="partial; no generic registry settlement receipt"; attribute :>> responsibility="Do not free aliased RC root cell or still arena while a retained carrier references it"; }
part def ClaimRow { attribute key:String; attribute mechanism:String; attribute condition:String; attribute result:String; attribute gap:String; }
part claim0:ClaimRow { attribute :>> key="same-cell"; attribute :>> mechanism="One canonical task for aliases of one physical cell"; attribute :>> condition="Exact key/address equivalence; policy-compatible immutable snapshot"; attribute :>> result="No concurrent duplicate ordinary writes to the cell"; attribute :>> gap="No existing generic carrier alias path identified; native adequacy open"; }
part claim1:ClaimRow { attribute :>> key="equal-values"; attribute :>> mechanism="Distinct physical keys produce distinct scan tasks"; attribute :>> condition="Cell values can be identical and both move"; attribute :>> result="Both roots updated even when forwarding copies object once"; attribute :>> gap="Actual addresses and moving GC refinement open"; }
part claim2:ClaimRow { attribute :>> key="late-lookup"; attribute :>> mechanism="Registry index pins before metadata access then revalidates admission"; attribute :>> condition="Lookup accepted before close retains metadata; payload admission after close refused"; attribute :>> result="No retirement until lookup pin and payload borrower drain"; attribute :>> gap="Fixed model identities; native generation/ABA and multiplicity not proved"; }
part claim3:ClaimRow { attribute :>> key="alias-cleanup"; attribute :>> mechanism="Shared SlotKey retains backing independently of retired descriptor"; attribute :>> condition="All referencing live or closing entries remain in root union"; attribute :>> result="Source descriptor retirement cannot free an aliased root cell"; attribute :>> gap="Native RC-header/arena handoff integration open"; }
part claim4:ClaimRow { attribute :>> key="generic-census"; attribute :>> mechanism="Finite list mapping and key deduplication preserves membership"; attribute :>> condition="Registry complete and canonical keys adequate"; attribute :>> result="No duplicate keys and every live descriptor represented"; attribute :>> gap="Not arbitrary concurrent native trace refinement"; }
part claim5:ClaimRow { attribute :>> key="parent-bridge"; attribute :>> mechanism="Physical coverage implies parent membership obligation"; attribute :>> condition="Explicit phase, descriptor and membership relation"; attribute :>> result="Refines prior per-descriptor coverage proposition"; attribute :>> gap="Full product, initialization and writer protocol composition open"; }
part def MemoryRow { attribute key:String; attribute publication:String; attribute observation:String; attribute obligation:String; attribute overhead:String; }
part memory0:MemoryRow { attribute :>> key="registration"; attribute :>> publication="Prepare metadata and roots under source pin then publish"; attribute :>> observation="Acquire complete descriptor before root mapping"; attribute :>> obligation="Collector exclusion or registered private slot; no unrooted value copy"; attribute :>> overhead="Registration plus generation and owner records"; }
part memory1:MemoryRow { attribute :>> key="census"; attribute :>> publication="Freeze registry mutation and physical root writers"; attribute :>> observation="Workers acquire immutable interval/root policy snapshot"; attribute :>> obligation="Expand all overlaps, canonicalize before distributing writable slots"; attribute :>> overhead="Sorting/index or linear presorted interval sweep"; }
part memory2:MemoryRow { attribute :>> key="task"; attribute :>> publication="READY to owner claim then completed release"; attribute :>> observation="Reclaimer acquires exact completion and grace"; attribute :>> obligation="Forwarding CAS is not root-cell arbitration"; attribute :>> overhead="One claim per canonical task or proven disjoint batch"; }
part memory3:MemoryRow { attribute :>> key="lookup"; attribute :>> publication="Stable VM index guard before descriptor read"; attribute :>> observation="Accept payload only after active generation check"; attribute :>> obligation="Closing rejects new borrow but retains accepted lookup pins"; attribute :>> overhead="Guard slots/counters and tombstone retention"; }
part memory4:MemoryRow { attribute :>> key="storage"; attribute :>> publication="Close/unlink descriptor after scan/borrow/lookup drain"; attribute :>> observation="Backing owner checks all aliases, including closing entries"; attribute :>> obligation="Do not confuse descriptor free with physical root-cell or Scheme arena free"; attribute :>> overhead="Independent slot and payload backing leases"; }
part memory5:MemoryRow { attribute :>> key="unknown"; attribute :>> publication="Unknown lookup/scan remains owned"; attribute :>> observation="Exact same-identity resolver observes result"; attribute :>> obligation="No timeout-based reset or recreation under a new identity"; attribute :>> overhead="Retention; progress and bounded memory not proved"; }
part def GainRow { attribute key:String; attribute avoided:String; attribute added:String; attribute condition:String; }
part gain0:GainRow { attribute :>> key="alias-scan"; attribute :>> avoided="M-S duplicate cell visits per round"; attribute :>> added="Canonicalization and run coalescing"; attribute :>> condition="M logical slot references, S canonical physical cells; existing duplicate path not demonstrated"; }
part gain1:GainRow { attribute :>> key="task-granularity"; attribute :>> avoided="Potential repeated claims for aliases"; attribute :>> added="Pin descriptor/backing references for every dependent logical entry"; attribute :>> condition="Task de-dup does not discard any ownership edge"; }
part gain2:GainRow { attribute :>> key="origin-exit"; attribute :>> avoided="Keeping old processor solely for its root-slot metadata"; attribute :>> added="VM registry, independent storage ownership and grace"; attribute :>> condition="Every other context and arena consumer independently settled"; }
part gain3:GainRow { attribute :>> key="bulk-scan"; attribute :>> avoided="Repeated per-word metadata decoding"; attribute :>> added="Maintain coalesced policy-compatible disjoint intervals"; attribute :>> condition="Preserve mark_array bulk runs; native integration and complexity open"; }
part gain4:GainRow { attribute :>> key="language"; attribute :>> avoided="Shared modern-C root/ABI contract"; attribute :>> added="C23 protocol and proof obligations remain"; attribute :>> condition="Zig cannot eliminate lifetime or canonical address authority; additional payoff unproved"; }
part def CostRow { attribute key:String; attribute avoided:String; attribute added:String; attribute positiveCondition:String; attribute boundary:String; }
part cost0:CostRow { attribute :>> key="scan-work"; attribute :>> avoided="K*(M-S)*visit_cost"; attribute :>> added="canonicalize + coalesce + K*claim_cost + grace"; attribute :>> positiveCondition="avoided > added"; attribute :>> boundary="M-S is a conditional work count, not measured current duplication"; }
part cost1:CostRow { attribute :>> key="task-work"; attribute :>> avoided="K*(logical_tasks-canonical_batches)*claim_cost"; attribute :>> added="all dependent descriptor/backing pin work"; attribute :>> positiveCondition="avoided > added"; attribute :>> boundary="Batching needs disjoint slot coverage and task refinement"; }
part cost2:CostRow { attribute :>> key="retention"; attribute :>> avoided="Processor-only retained resources after full transfer"; attribute :>> added="Descriptor + index + root-cell/payload storage + source write lease + unresolved leases"; attribute :>> positiveCondition="All independent dependencies settled; lower retained resources"; attribute :>> boundary="Aliasing old RC cell can retain its header and arena; no unconditional saving"; }
part cost3:CostRow { attribute :>> key="modern-c-zig"; attribute :>> avoided="Necessary support actually removed by Zig"; attribute :>> added="Second toolchain + FFI + ownership support"; attribute :>> positiveCondition="Retired support exceeds new support"; attribute :>> boundary="No additional positive Zig-specific net benefit established"; }
part def ContractRow { attribute fromNode:String; attribute toNode:String; attribute custody:String; }
part contract0:ContractRow { attribute :>> fromNode="SourceOwner"; attribute :>> toNode="RegistryCommit"; attribute :>> custody="Rooted payload and complete metadata"; }
part contract1:ContractRow { attribute :>> fromNode="StorageIssuer"; attribute :>> toNode="SlotKey"; attribute :>> custody="Unique storage identity and validated extent"; }
part contract2:ContractRow { attribute :>> fromNode="RegistryCommit"; attribute :>> toNode="FrozenRootUnion"; attribute :>> custody="Keep all active and closing entries"; }
part contract3:ContractRow { attribute :>> fromNode="LegacyRootDomains"; attribute :>> toNode="FrozenRootUnion"; attribute :>> custody="Context VM globals frames RC and pending roots"; }
part contract4:ContractRow { attribute :>> fromNode="SlotKey"; attribute :>> toNode="CanonicalRuns"; attribute :>> custody="Equal physical cells share a key"; }
part contract5:ContractRow { attribute :>> fromNode="FrozenRootUnion"; attribute :>> toNode="CanonicalRuns"; attribute :>> custody="Deduplicate slots never values"; }
part contract6:ContractRow { attribute :>> fromNode="CanonicalRuns"; attribute :>> toNode="RootTasks"; attribute :>> custody="Disjoint writable intervals and policy"; }
part contract7:ContractRow { attribute :>> fromNode="RootTasks"; attribute :>> toNode="ScanOwner"; attribute :>> custody="Acquire pinned descriptor and code"; }
part contract8:ContractRow { attribute :>> fromNode="ScanOwner"; attribute :>> toNode="UpdatedSlots"; attribute :>> custody="Each physical slot updated once"; }
part contract9:ContractRow { attribute :>> fromNode="UpdatedSlots"; attribute :>> toNode="ScanGrace"; attribute :>> custody="Finish after last root-slot use"; }
part contract10:ContractRow { attribute :>> fromNode="StableIndex"; attribute :>> toNode="LookupPin"; attribute :>> custody="Pin before descriptor access"; }
part contract11:ContractRow { attribute :>> fromNode="LookupPin"; attribute :>> toNode="BorrowDecision"; attribute :>> custody="Revalidate generation and admission"; }
part contract12:ContractRow { attribute :>> fromNode="CloseAdmission"; attribute :>> toNode="BorrowDecision"; attribute :>> custody="Reject late acceptance"; }
part contract13:ContractRow { attribute :>> fromNode="LookupPin"; attribute :>> toNode="NativeGrace"; attribute :>> custody="Unknown lookup retains descriptor"; }
part contract14:ContractRow { attribute :>> fromNode="BorrowDecision"; attribute :>> toNode="NativeGrace"; attribute :>> custody="Accepted user must settle"; }
part contract15:ContractRow { attribute :>> fromNode="ScanGrace"; attribute :>> toNode="DescriptorRetirement"; attribute :>> custody="No frozen root/task reader"; }
part contract16:ContractRow { attribute :>> fromNode="NativeGrace"; attribute :>> toNode="DescriptorRetirement"; attribute :>> custody="No lookup user or code reader"; }
part contract17:ContractRow { attribute :>> fromNode="DescriptorRetirement"; attribute :>> toNode="DescriptorFree"; attribute :>> custody="Unlink after grace"; }
part contract18:ContractRow { attribute :>> fromNode="CanonicalRuns"; attribute :>> toNode="SlotBackingPermit"; attribute :>> custody="All alias references retained"; }
part contract19:ContractRow { attribute :>> fromNode="DescriptorRetirement"; attribute :>> toNode="SlotBackingPermit"; attribute :>> custody="Every referencing entry retired"; }
part contract20:ContractRow { attribute :>> fromNode="SlotBackingPermit"; attribute :>> toNode="RootCellFree"; attribute :>> custody="Independent from descriptor free"; }
part contract21:ContractRow { attribute :>> fromNode="PayloadArenaReceipt"; attribute :>> toNode="CleanupPermit"; attribute :>> custody="Still arena and destructor responsibility"; }
part contract22:ContractRow { attribute :>> fromNode="RootCellFree"; attribute :>> toNode="CleanupPermit"; attribute :>> custody="No aliased RC header slot remains"; }
part contract23:ContractRow { attribute :>> fromNode="CleanupPermit"; attribute :>> toNode="CleanupRC"; attribute :>> custody="Only after full storage settlement"; }
part def BindingRow { attribute actionName:String; attribute lemma:String; attribute scope:String; }
part binding0:BindingRow { attribute :>> actionName="carrier_slot_mapping.registerAlias"; attribute :>> lemma="SlotMapping.registerAliasPreserves"; attribute :>> scope="fixed two descriptors and two physical slots; native refinement open"; }
part binding1:BindingRow { attribute :>> actionName="carrier_slot_mapping.registerCopy"; attribute :>> lemma="SlotMapping.registerCopyPreserves"; attribute :>> scope="fixed two descriptors and two physical slots; native refinement open"; }
part binding2:BindingRow { attribute :>> actionName="carrier_slot_mapping.beginLookup0"; attribute :>> lemma="SlotMapping.beginLookup0Preserves"; attribute :>> scope="fixed two descriptors and two physical slots; native refinement open"; }
part binding3:BindingRow { attribute :>> actionName="carrier_slot_mapping.acceptBorrow0"; attribute :>> lemma="SlotMapping.acceptBorrow0Preserves"; attribute :>> scope="fixed two descriptors and two physical slots; native refinement open"; }
part binding4:BindingRow { attribute :>> actionName="carrier_slot_mapping.lookupUnknown0"; attribute :>> lemma="SlotMapping.lookupUnknown0Preserves"; attribute :>> scope="fixed two descriptors and two physical slots; native refinement open"; }
part binding5:BindingRow { attribute :>> actionName="carrier_slot_mapping.resolveLookup0"; attribute :>> lemma="SlotMapping.resolveLookup0Preserves"; attribute :>> scope="fixed two descriptors and two physical slots; native refinement open"; }
part binding6:BindingRow { attribute :>> actionName="carrier_slot_mapping.rejectLookup0"; attribute :>> lemma="SlotMapping.rejectLookup0Preserves"; attribute :>> scope="fixed two descriptors and two physical slots; native refinement open"; }
part binding7:BindingRow { attribute :>> actionName="carrier_slot_mapping.returnBorrow0"; attribute :>> lemma="SlotMapping.returnBorrow0Preserves"; attribute :>> scope="fixed two descriptors and two physical slots; native refinement open"; }
part binding8:BindingRow { attribute :>> actionName="carrier_slot_mapping.close0"; attribute :>> lemma="SlotMapping.close0Preserves"; attribute :>> scope="fixed two descriptors and two physical slots; native refinement open"; }
part binding9:BindingRow { attribute :>> actionName="carrier_slot_mapping.retire0"; attribute :>> lemma="SlotMapping.retire0Preserves"; attribute :>> scope="fixed two descriptors and two physical slots; native refinement open"; }
part binding10:BindingRow { attribute :>> actionName="carrier_slot_mapping.lateRequest0"; attribute :>> lemma="SlotMapping.lateRequest0Preserves"; attribute :>> scope="fixed two descriptors and two physical slots; native refinement open"; }
part binding11:BindingRow { attribute :>> actionName="carrier_slot_mapping.claim0"; attribute :>> lemma="SlotMapping.claim0Preserves"; attribute :>> scope="fixed two descriptors and two physical slots; native refinement open"; }
part binding12:BindingRow { attribute :>> actionName="carrier_slot_mapping.scan0"; attribute :>> lemma="SlotMapping.scan0Preserves"; attribute :>> scope="fixed two descriptors and two physical slots; native refinement open"; }
part binding13:BindingRow { attribute :>> actionName="carrier_slot_mapping.scanUnknown0"; attribute :>> lemma="SlotMapping.scanUnknown0Preserves"; attribute :>> scope="fixed two descriptors and two physical slots; native refinement open"; }
part binding14:BindingRow { attribute :>> actionName="carrier_slot_mapping.resolveScan0"; attribute :>> lemma="SlotMapping.resolveScan0Preserves"; attribute :>> scope="fixed two descriptors and two physical slots; native refinement open"; }
part binding15:BindingRow { attribute :>> actionName="carrier_slot_mapping.beginLookup1"; attribute :>> lemma="SlotMapping.beginLookup1Preserves"; attribute :>> scope="fixed two descriptors and two physical slots; native refinement open"; }
part binding16:BindingRow { attribute :>> actionName="carrier_slot_mapping.acceptBorrow1"; attribute :>> lemma="SlotMapping.acceptBorrow1Preserves"; attribute :>> scope="fixed two descriptors and two physical slots; native refinement open"; }
part binding17:BindingRow { attribute :>> actionName="carrier_slot_mapping.lookupUnknown1"; attribute :>> lemma="SlotMapping.lookupUnknown1Preserves"; attribute :>> scope="fixed two descriptors and two physical slots; native refinement open"; }
part binding18:BindingRow { attribute :>> actionName="carrier_slot_mapping.resolveLookup1"; attribute :>> lemma="SlotMapping.resolveLookup1Preserves"; attribute :>> scope="fixed two descriptors and two physical slots; native refinement open"; }
part binding19:BindingRow { attribute :>> actionName="carrier_slot_mapping.rejectLookup1"; attribute :>> lemma="SlotMapping.rejectLookup1Preserves"; attribute :>> scope="fixed two descriptors and two physical slots; native refinement open"; }
part binding20:BindingRow { attribute :>> actionName="carrier_slot_mapping.returnBorrow1"; attribute :>> lemma="SlotMapping.returnBorrow1Preserves"; attribute :>> scope="fixed two descriptors and two physical slots; native refinement open"; }
part binding21:BindingRow { attribute :>> actionName="carrier_slot_mapping.close1"; attribute :>> lemma="SlotMapping.close1Preserves"; attribute :>> scope="fixed two descriptors and two physical slots; native refinement open"; }
part binding22:BindingRow { attribute :>> actionName="carrier_slot_mapping.retire1"; attribute :>> lemma="SlotMapping.retire1Preserves"; attribute :>> scope="fixed two descriptors and two physical slots; native refinement open"; }
part binding23:BindingRow { attribute :>> actionName="carrier_slot_mapping.lateRequest1"; attribute :>> lemma="SlotMapping.lateRequest1Preserves"; attribute :>> scope="fixed two descriptors and two physical slots; native refinement open"; }
part binding24:BindingRow { attribute :>> actionName="carrier_slot_mapping.claim1"; attribute :>> lemma="SlotMapping.claim1Preserves"; attribute :>> scope="fixed two descriptors and two physical slots; native refinement open"; }
part binding25:BindingRow { attribute :>> actionName="carrier_slot_mapping.scan1"; attribute :>> lemma="SlotMapping.scan1Preserves"; attribute :>> scope="fixed two descriptors and two physical slots; native refinement open"; }
part binding26:BindingRow { attribute :>> actionName="carrier_slot_mapping.scanUnknown1"; attribute :>> lemma="SlotMapping.scanUnknown1Preserves"; attribute :>> scope="fixed two descriptors and two physical slots; native refinement open"; }
part binding27:BindingRow { attribute :>> actionName="carrier_slot_mapping.resolveScan1"; attribute :>> lemma="SlotMapping.resolveScan1Preserves"; attribute :>> scope="fixed two descriptors and two physical slots; native refinement open"; }
part binding28:BindingRow { attribute :>> actionName="carrier_slot_mapping.freeze000"; attribute :>> lemma="SlotMapping.freeze000Preserves"; attribute :>> scope="fixed two descriptors and two physical slots; native refinement open"; }
part binding29:BindingRow { attribute :>> actionName="carrier_slot_mapping.freeze001"; attribute :>> lemma="SlotMapping.freeze001Preserves"; attribute :>> scope="fixed two descriptors and two physical slots; native refinement open"; }
part binding30:BindingRow { attribute :>> actionName="carrier_slot_mapping.freeze010"; attribute :>> lemma="SlotMapping.freeze010Preserves"; attribute :>> scope="fixed two descriptors and two physical slots; native refinement open"; }
part binding31:BindingRow { attribute :>> actionName="carrier_slot_mapping.freeze011"; attribute :>> lemma="SlotMapping.freeze011Preserves"; attribute :>> scope="fixed two descriptors and two physical slots; native refinement open"; }
part binding32:BindingRow { attribute :>> actionName="carrier_slot_mapping.freeze100"; attribute :>> lemma="SlotMapping.freeze100Preserves"; attribute :>> scope="fixed two descriptors and two physical slots; native refinement open"; }
part binding33:BindingRow { attribute :>> actionName="carrier_slot_mapping.freeze101"; attribute :>> lemma="SlotMapping.freeze101Preserves"; attribute :>> scope="fixed two descriptors and two physical slots; native refinement open"; }
part binding34:BindingRow { attribute :>> actionName="carrier_slot_mapping.freeze110"; attribute :>> lemma="SlotMapping.freeze110Preserves"; attribute :>> scope="fixed two descriptors and two physical slots; native refinement open"; }
part binding35:BindingRow { attribute :>> actionName="carrier_slot_mapping.freeze111"; attribute :>> lemma="SlotMapping.freeze111Preserves"; attribute :>> scope="fixed two descriptors and two physical slots; native refinement open"; }
part binding36:BindingRow { attribute :>> actionName="carrier_slot_mapping.finishRound"; attribute :>> lemma="SlotMapping.finishRoundPreserves"; attribute :>> scope="fixed two descriptors and two physical slots; native refinement open"; }
part binding37:BindingRow { attribute :>> actionName="carrier_slot_mapping.freeStore0"; attribute :>> lemma="SlotMapping.freeStore0Preserves"; attribute :>> scope="fixed two descriptors and two physical slots; native refinement open"; }
part binding38:BindingRow { attribute :>> actionName="carrier_slot_mapping.freeStore1"; attribute :>> lemma="SlotMapping.freeStore1Preserves"; attribute :>> scope="fixed two descriptors and two physical slots; native refinement open"; }
part binding39:BindingRow { attribute :>> actionName="carrier_slot_mapping.exitProcessor"; attribute :>> lemma="SlotMapping.exitProcessorPreserves"; attribute :>> scope="fixed two descriptors and two physical slots; native refinement open"; }
part def ProofRow { attribute key:String; attribute lemma:String; }
part proof0:ProofRow { attribute :>> key="stepPreserves"; attribute :>> lemma="SlotMapping.stepPreserves"; }
part proof1:ProofRow { attribute :>> key="reachableSafe"; attribute :>> lemma="SlotMapping.reachableSafe"; }
part proof2:ProofRow { attribute :>> key="sameSlotUsesOneTask"; attribute :>> lemma="SlotMapping.sameSlotUsesOneTask"; }
part proof3:ProofRow { attribute :>> key="bothDistinctCovered"; attribute :>> lemma="SlotMapping.bothDistinctCovered"; }
part proof4:ProofRow { attribute :>> key="lateBorrowDenied"; attribute :>> lemma="SlotMapping.lateBorrowDenied"; }
part proof5:ProofRow { attribute :>> key="unknownLookupBlocksRetirement"; attribute :>> lemma="SlotMapping.unknownLookupBlocksRetirement"; }
part proof6:ProofRow { attribute :>> key="closingAliasRetainsSlot"; attribute :>> lemma="SlotMapping.closingAliasRetainsSlot"; }
part proof7:ProofRow { attribute :>> key="sharedSlotBlocksFree"; attribute :>> lemma="SlotMapping.sharedSlotBlocksFree"; }
part proof8:ProofRow { attribute :>> key="acceptedLookupRetainsDescriptor"; attribute :>> lemma="SlotMapping.acceptedLookupRetainsDescriptor"; }
part proof9:ProofRow { attribute :>> key="secondClaimDenied"; attribute :>> lemma="SlotMapping.secondClaimDenied"; }
part proof10:ProofRow { attribute :>> key="unknownScanBlocksFinish"; attribute :>> lemma="SlotMapping.unknownScanBlocksFinish"; }
part proof11:ProofRow { attribute :>> key="memUnique"; attribute :>> lemma="SlotCensus.memUnique"; }
part proof12:ProofRow { attribute :>> key="uniqueNodup"; attribute :>> lemma="SlotCensus.uniqueNodup"; }
part proof13:ProofRow { attribute :>> key="uniqueLength"; attribute :>> lemma="SlotCensus.uniqueLength"; }
part proof14:ProofRow { attribute :>> key="allRegisteredSlots"; attribute :>> lemma="SlotCensus.allRegisteredSlots"; }
part proof15:ProofRow { attribute :>> key="censusNoDuplicate"; attribute :>> lemma="SlotCensus.censusNoDuplicate"; }
part proof16:ProofRow { attribute :>> key="boundedByEntries"; attribute :>> lemma="SlotCensus.boundedByEntries"; }
part proof17:ProofRow { attribute :>> key="twoKeysBothRepresented"; attribute :>> lemma="SlotCensus.twoKeysBothRepresented"; }
part proof18:ProofRow { attribute :>> key="addressAliasIffKey"; attribute :>> lemma="SlotCensus.addressAliasIffKey"; }
part proof19:ProofRow { attribute :>> key="physicalCarrierCoverage"; attribute :>> lemma="SlotMappingBridge.physicalCarrierCoverage"; }
part proof20:ProofRow { attribute :>> key="parentMembershipObligation"; attribute :>> lemma="SlotMappingBridge.parentMembershipObligation"; }
part proof21:ProofRow { attribute :>> key="allAliasesHoldBacking"; attribute :>> lemma="SlotMappingBridge.allAliasesHoldBacking"; }
part def RouteRow { attribute component:String; attribute actionName:String; attribute lemma:String; attribute producerAnchor:String; attribute obligationId:String; }
part route0:RouteRow { attribute :>> component="registry"; attribute :>> actionName="carrier_slot_mapping.registerAlias"; attribute :>> lemma="SlotMapping.registerAliasPreserves"; attribute :>> producerAnchor="rc-register"; attribute :>> obligationId="SM-source"; }
part route1:RouteRow { attribute :>> component="registry"; attribute :>> actionName="carrier_slot_mapping.registerCopy"; attribute :>> lemma="SlotMapping.registerCopyPreserves"; attribute :>> producerAnchor="tcl-install"; attribute :>> obligationId="SM-source"; }
part route2:RouteRow { attribute :>> component="roots"; attribute :>> actionName="carrier_slot_mapping.freeze111"; attribute :>> lemma="SlotMapping.freeze111Preserves"; attribute :>> producerAnchor="origin-publish"; attribute :>> obligationId="SM-roots"; }
part route3:RouteRow { attribute :>> component="roots"; attribute :>> actionName="carrier_slot_mapping.freeze011"; attribute :>> lemma="SlotMapping.freeze011Preserves"; attribute :>> producerAnchor="task-publish-body"; attribute :>> obligationId="SM-roots"; }
part route4:RouteRow { attribute :>> component="roots"; attribute :>> actionName="carrier_slot_mapping.claim0"; attribute :>> lemma="SlotMapping.claim0Preserves"; attribute :>> producerAnchor="task-claim-body"; attribute :>> obligationId="SM-roots"; }
part route5:RouteRow { attribute :>> component="roots"; attribute :>> actionName="carrier_slot_mapping.scan0"; attribute :>> lemma="SlotMapping.scan0Preserves"; attribute :>> producerAnchor="copy-winner-slot-write"; attribute :>> obligationId="SM-roots"; }
part route6:RouteRow { attribute :>> component="roots"; attribute :>> actionName="carrier_slot_mapping.scan1"; attribute :>> lemma="SlotMapping.scan1Preserves"; attribute :>> producerAnchor="already-forwarded-slot-write"; attribute :>> obligationId="SM-roots"; }
part route7:RouteRow { attribute :>> component="lookup"; attribute :>> actionName="carrier_slot_mapping.beginLookup0"; attribute :>> lemma="SlotMapping.beginLookup0Preserves"; attribute :>> producerAnchor="rc-read"; attribute :>> obligationId="SM-execution"; }
part route8:RouteRow { attribute :>> component="lookup"; attribute :>> actionName="carrier_slot_mapping.acceptBorrow0"; attribute :>> lemma="SlotMapping.acceptBorrow0Preserves"; attribute :>> producerAnchor="tcl-call"; attribute :>> obligationId="SM-execution"; }
part route9:RouteRow { attribute :>> component="lookup"; attribute :>> actionName="carrier_slot_mapping.retire0"; attribute :>> lemma="SlotMapping.retire0Preserves"; attribute :>> producerAnchor="task-claim-body"; attribute :>> obligationId="SM-execution"; }
part route10:RouteRow { attribute :>> component="lookup"; attribute :>> actionName="carrier_slot_mapping.lookupUnknown0"; attribute :>> lemma="SlotMapping.lookupUnknown0Preserves"; attribute :>> producerAnchor="register-export"; attribute :>> obligationId="SM-execution"; }
part route11:RouteRow { attribute :>> component="storage"; attribute :>> actionName="carrier_slot_mapping.freeStore0"; attribute :>> lemma="SlotMapping.freeStore0Preserves"; attribute :>> producerAnchor="rc-cleanup"; attribute :>> obligationId="SM-storage"; }
part route12:RouteRow { attribute :>> component="storage"; attribute :>> actionName="carrier_slot_mapping.retire1"; attribute :>> lemma="SlotMapping.retire1Preserves"; attribute :>> producerAnchor="tcl-delete-native"; attribute :>> obligationId="SM-storage"; }
part route13:RouteRow { attribute :>> component="writer"; attribute :>> actionName="carrier_slot_mapping.close0"; attribute :>> lemma="SlotMapping.close0Preserves"; attribute :>> producerAnchor="setter-export"; attribute :>> obligationId="SM-writers"; }
part def Need { attribute obligationId:String; attribute kind:String; attribute subjectPath:String; attribute subjectScope:String; ref owner:Owner; }
part formalNeed:Need { attribute :>> obligationId="SM-formal"; attribute :>> kind="induction"; attribute :>> subjectPath="dev/refactoring/modern-c/models/lean/SlotMapping.lean"; attribute :>> subjectScope="two descriptors physical alias mapping lookup/borrow and backing safety"; ref :>> owner=lookupOwner; }
part bridgeNeed:Need { attribute :>> obligationId="SM-bridge"; attribute :>> kind="composition"; attribute :>> subjectPath="dev/refactoring/modern-c/models/lean/SlotMappingBridge.lean"; attribute :>> subjectScope="generic canonical census and conditional parent membership relation"; ref :>> owner=lookupOwner; }
part sourceNeed:Need { attribute :>> obligationId="SM-source"; attribute :>> kind="source"; attribute :>> subjectPath="vendor/gambit/lib/memory/rc-allocation.inc"; attribute :>> subjectScope="authoritative VM registry and canonical storage/address adequacy"; ref :>> owner=registryOwner; }
part executionNeed:Need { attribute :>> obligationId="SM-execution"; attribute :>> kind="source"; attribute :>> subjectPath="vendor/gambit/lib/c_intf.c"; attribute :>> subjectScope="stable pre-dereference lookup guard and every native indirect borrower"; ref :>> owner=lookupOwner; }
part rootsNeed:Need { attribute :>> obligationId="SM-roots"; attribute :>> kind="source"; attribute :>> subjectPath="vendor/gambit/lib/memory/root-origins.inc"; attribute :>> subjectScope="complete frozen native slot union; no overlapping scan authorities"; ref :>> owner=rootsOwner; }
part writersNeed:Need { attribute :>> obligationId="SM-writers"; attribute :>> kind="source"; attribute :>> subjectPath="vendor/gambit/lib/setup.c"; attribute :>> subjectScope="public writer closure and GC update exclusion"; ref :>> owner=writerOwner; }
part platformNeed:Need { attribute :>> obligationId="SM-platform"; attribute :>> kind="platform"; attribute :>> subjectPath="vendor/gambit/include/gambit.h.in"; attribute :>> subjectScope="C23 atomic objects effective Darwin conditional ABI and generated artifacts"; ref :>> owner=lookupOwner; }
part storageNeed:Need { attribute :>> obligationId="SM-storage"; attribute :>> kind="source"; attribute :>> subjectPath="vendor/gambit/lib/memory/memory-lifecycle.inc"; attribute :>> subjectScope="RC root cell still payload arena and scan code grace"; ref :>> owner=storageOwner; }
part claim6:ClaimRow { attribute :>> key="alias-binding"; attribute :>> mechanism="Alias physical storage only with compatible logical binding policy"; attribute :>> condition="Bound payload generation requires source semantic-write lease; otherwise independent copied registered cell"; attribute :>> result="GC relocation changes address without silently rebinding to a new source payload"; attribute :>> gap="Model has collector-only slot updates; native setter/payload product refinement remains open"; }
}
