/* Cross-cutting amplification model; canonical runtime ownership is referenced, never redefined. */
package GambitAdvantageArchitecture { private import ScalarValues::*;
part def OwnerUse { ref part module : GambitRuntimeComposition::BlueprintModule; }
part def DecisionUse { ref part decision : GambitModernizationTarget::ArchitectureDecision; }
part def Advantage { attribute key:String; attribute paper:String; attribute section:String; attribute basis:String; attribute frameDesign:String; attribute control:String; attribute gcSmp:String; attribute build:String; attribute refutation:String; }
part def Contract { ref part seam:GambitRuntimeComposition::BlueprintInterface; attribute key:String; attribute actionName:String; attribute guardName:String; attribute lemmaName:String; attribute sourcePath:String; attribute sourceNeedle:String; attribute premise:String; attribute retirement:String; attribute benefit:String; attribute added:String; attribute gap:String; }
part def AdvantageUse { ref part advantage:Advantage; ref part contract:Contract; attribute obligation:String; }
part def Benefit { attribute key:String; attribute avoided:String; attribute added:String; attribute condition:String; attribute evidence:String; }
part def OpenScope { attribute key:String; attribute qualified:Boolean; attribute subjectPath:String; attribute scope:String; attribute reason:String; }

part owner0:OwnerUse { ref part :>> module=GambitRuntimeComposition::blueprintModule0; }
part owner1:OwnerUse { ref part :>> module=GambitRuntimeComposition::blueprintModule1; }
part owner2:OwnerUse { ref part :>> module=GambitRuntimeComposition::blueprintModule2; }
part owner3:OwnerUse { ref part :>> module=GambitRuntimeComposition::blueprintModule3; }
part owner4:OwnerUse { ref part :>> module=GambitRuntimeComposition::blueprintModule4; }
part owner5:OwnerUse { ref part :>> module=GambitRuntimeComposition::blueprintModule5; }
part owner6:OwnerUse { ref part :>> module=GambitRuntimeComposition::blueprintModule6; }
part owner7:OwnerUse { ref part :>> module=GambitRuntimeComposition::blueprintModule7; }
part owner8:OwnerUse { ref part :>> module=GambitRuntimeComposition::blueprintModule8; }
part decision0:DecisionUse { ref part :>> decision=GambitModernizationTarget::decision0; }
part decision1:DecisionUse { ref part :>> decision=GambitModernizationTarget::decision1; }
part decision2:DecisionUse { ref part :>> decision=GambitModernizationTarget::decision2; }
part decision3:DecisionUse { ref part :>> decision=GambitModernizationTarget::decision3; }
part decision4:DecisionUse { ref part :>> decision=GambitModernizationTarget::decision4; }
part decision5:DecisionUse { ref part :>> decision=GambitModernizationTarget::decision5; }
part advantage0:Advantage { attribute :>> paper="https://www.iro.umontreal.ca/~feeley/papers/FeeleyMillerLFP90.pdf"; attribute :>> key="logical-frames"; attribute :>> section="2,2.3"; attribute :>> basis="Logical implementation objects and frame slot coordinates bridge source and machine"; attribute :>> frameDesign="Generate stack/heap/internal-return decoders, pointer maps and ABI from one logical schema"; attribute :>> control="Each capture and shot uses same frame identity; mutable exposed frames retain alias semantics"; attribute :>> gcSmp="Precise running/saved/native root consumers and promotion interpret the same slots"; attribute :>> build="Cache semantic contract separately from physical layout and native compiler inputs"; attribute :>> refutation="Fails if duplicated layout decisions remain or frame/reflection observations change"; }
part advantage1:Advantage { attribute :>> paper="https://www.iro.umontreal.ca/~feeley/papers/FeeleyMillerLFP90.pdf"; attribute :>> key="bidirectional-target"; attribute :>> section="2"; attribute :>> basis="Target descriptions carry registers, calls, closures, primitives and declarations back to frontend"; attribute :>> frameDesign="Separate semantic profile, layout ABI and mechanical C emission; feed legal target facts back before completion"; attribute :>> control="Tail/non-tail and allocating/exceptional successors retain full semantic information"; attribute :>> gcSmp="Checkpoint, allocation and barrier obligations are negotiated instead of rediscovered in macros"; attribute :>> build="Gambit supplies sealed stages; Gerbil schedules exact phase products; LLVM/MLIR consumes semantic plan at declared level"; attribute :>> refutation="Fails if native-only edits unnecessarily redo expansion or semantic edits incorrectly hit old cache"; }
part advantage2:Advantage { attribute :>> paper="https://www.iro.umontreal.ca/~feeley/papers/FeeleyMillerLFP90.pdf"; attribute :>> key="explicit-storage"; attribute :>> section="2.1"; attribute :>> basis="Operand classes expose distinct storage; heap-memory operand remains an alias exception"; attribute :>> frameDesign="Logical slot kinds and declared alias escapes delimit optimization eligibility"; attribute :>> control="Share eligible immutable captured structure; never clone shared Scheme heap or replay effects"; attribute :>> gcSmp="Context nurseries, precise roots and remembered stores allow clean mature graphs to avoid minor traversal"; attribute :>> build="Immutable target/support descriptions may share; mutable registry, expander and context instances remain owned"; attribute :>> refutation="Fails on any missed mature-to-young writer, unrooted native alias, or shared mutable compiler state"; }
part advantage3:Advantage { attribute :>> paper="https://www.iro.umontreal.ca/~feeley/papers/FeeleyMillerLFP90.pdf"; attribute :>> key="measurement-feedback"; attribute :>> section="abstract"; attribute :>> basis="VM usage measurements can inform representation and optimization decisions"; attribute :>> frameDesign="Record emitted/preprocessed bytes, descriptor size and decode work by contract cohort"; attribute :>> control="Count per-shot materialization and required wind/native effects separately from reusable representation"; attribute :>> gcSmp="Count mature bytes avoided, remembered scans, promotion, barriers, peak reserve and pause/coordination"; attribute :>> build="Measure executed actions and critical path for no-change, leaf, macro, layout and tool changes"; attribute :>> refutation="Fails when saved work does not exceed added validation, coordination, copies and retained storage"; }
part contract0:Contract { ref part :>> seam=GambitRuntimeComposition::blueprintInterface0; attribute :>> key="semantic-seal"; attribute :>> actionName="sealPlan"; attribute :>> guardName="s.traceClosed"; attribute :>> lemmaName="sealNeedsSnapshot"; attribute :>> sourcePath="vendor/gambit/gsc/_front.scm"; attribute :>> sourceNeedle="(compile-parsed-program"; attribute :>> premise="semantic source/target/decl/effect trace closed; result graph detached or ownership transferred"; attribute :>> retirement="Distributed repeated semantic inference inside C emission after exact schema migration"; attribute :>> benefit="One semantic completion reused by layout/backend consumers"; attribute :>> added="Deep sealing, origin/declaration fidelity and ABI manifest"; attribute :>> gap="Output-to-model encoding and full semantic completion remain unproved"; }
part contract1:Contract { ref part :>> seam=GambitRuntimeComposition::generatedEntryInterface; attribute :>> key="module-cohort"; attribute :>> actionName="bindModule"; attribute :>> guardName="s.native"; attribute :>> lemmaName="bindCompatible"; attribute :>> sourcePath="vendor/gambit/gsc/_front.scm"; attribute :>> sourceNeedle="(module-descr"; attribute :>> premise="no live old activation/root/borrow is replaced; descriptor/code/runtime cohort checked"; attribute :>> retirement="Implicit module/label layout assumptions after all loaders and entry consumers migrate"; attribute :>> benefit="Reject ABI mismatch before execution; keep old cohort pinned for active continuations"; attribute :>> added="Module validation and retained old code/storage"; attribute :>> gap="Dynamic module loading and native ABI simulation remain open"; }
part contract2:Contract { ref part :>> seam=GambitRuntimeComposition::blueprintInterface2; attribute :>> key="captured-roots"; attribute :>> actionName="capture"; attribute :>> guardName="s.roots"; attribute :>> lemmaName="captureRequiresRoot"; attribute :>> sourcePath="vendor/gambit/include/gambit.h.in"; attribute :>> sourceNeedle="#define ___CONTINUATION_CAPTURE"; attribute :>> premise="publish all current/saved/register/denv/native roots before collecting transfer"; attribute :>> retirement="Separate capture/GC/restore/serialization frame interpretations after all consumers migrate"; attribute :>> benefit="One logical frame schema supports debugger, collector and repeatable control"; attribute :>> added="Root descriptor generation, root updates and materialization"; attribute :>> gap="Full root coverage and reflective frame identity are open"; }
part contract3:Contract { ref part :>> seam=GambitRuntimeComposition::blueprintInterface2; attribute :>> key="remembered-store"; attribute :>> actionName="storeYoung"; attribute :>> guardName="s.reserved"; attribute :>> lemmaName="storePreserves"; attribute :>> sourcePath="vendor/gambit/lib/_kernel.scm"; attribute :>> sourceNeedle="(define-prim (##frame-set!"; attribute :>> premise="every mature-to-young store covered; reserve-before-store or conservative fallback; barrier itself cannot GC"; attribute :>> retirement="Whole mature graph scan per minor only for proven writer-closed eligible graph"; attribute :>> benefit="Minor scan may depend on young live plus roots and remembered edges"; attribute :>> added="Barriers, logs, promotion and overflow checkpoint"; attribute :>> gap="Complete continuation/denv/FFI/native writer inventory and overflow proof remain open"; }
part contract4:Contract { ref part :>> seam=GambitRuntimeComposition::blueprintInterface1; attribute :>> key="minor-root-cut"; attribute :>> actionName="beginMinor"; attribute :>> guardName="s.frozen==Set(0,1)"; attribute :>> lemmaName="minorNeedsCompleteCut"; attribute :>> sourcePath="vendor/gambit/lib/mem.c"; attribute :>> sourceNeedle="mark_continuation ("; attribute :>> premise="VM-owned complete membership and frozen updateable root views; scanners acquire grant"; attribute :>> retirement="PSTATE as inseparable execution/carrier/root/collector authority after source migration"; attribute :>> benefit="Parked native carriers can stop blocking admitted GC; contexts outnumber carriers"; attribute :>> added="Epoch close, polls, frozen roots, participation and reload"; attribute :>> gap="Fair progress and full nonzero-processor RC closure remain open"; }
part contract5:Contract { ref part :>> seam=GambitRuntimeComposition::blueprintInterface4; attribute :>> key="copy-publication"; attribute :>> actionName="publishCopy"; attribute :>> guardName="s.copying"; attribute :>> lemmaName="copyPublicationConserves"; attribute :>> sourcePath="vendor/gambit/lib/mem.c"; attribute :>> sourceNeedle="___HIDDEN void end_heap_chunk"; attribute :>> premise="Initialization and private copy/child responsibility precede publish; no debt loss at handoff"; attribute :>> retirement="Per-PSTATE private work as untracked lifetime after collector context migration"; attribute :>> benefit="Independent worker load balance while preserving parent/child custody"; attribute :>> added="Copy reserve, scan queues, CAS and debt accounting"; attribute :>> gap="Forwarding/PAIR/Tail and weak-memory source refinement remain open"; }
part contract6:Contract { ref part :>> seam=GambitRuntimeComposition::blueprintInterface4; attribute :>> key="collector-finish"; attribute :>> actionName="finishMinor"; attribute :>> guardName="s.debt==0"; attribute :>> lemmaName="finishNeedsNoPrivate"; attribute :>> sourcePath="vendor/gambit/lib/mem.c"; attribute :>> sourceNeedle="Other processors are still actively scanning chunks"; attribute :>> premise="membership closed and all root/private/queued/derived work accounted; no in-flight copies"; attribute :>> retirement="Empty-queue or idle-only termination inference within new collector"; attribute :>> benefit="Finish based on global work closure instead of carrier lifetime"; attribute :>> added="Complete producer census and closure acknowledgement"; attribute :>> gap="Weak/finalizer phases, failure, capacity and reopening product remain open"; }
part contract7:Contract { ref part :>> seam=GambitRuntimeComposition::blueprintInterface3; attribute :>> key="ffi-park"; attribute :>> actionName="parkNative"; attribute :>> guardName="s.roots"; attribute :>> lemmaName="unknownRetainsCustody"; attribute :>> sourcePath="vendor/gambit/lib/c_intf.c"; attribute :>> sourceNeedle="TODO: proc_or_false may have been GC'd"; attribute :>> premise="roots before allocation; surrender derived pointers and borrow, preserve result debt"; attribute :>> retirement="Per-wrapper ad hoc marker/root ownership after actual caller migration"; attribute :>> benefit="Share root-safe entry and park/reentry service across FFI wrappers"; attribute :>> added="Handles, affinity, nested activations and conservative raw mode"; attribute :>> gap="Arbitrary C-stack continuation escape and native cancellation remain open"; }
part contract8:Contract { ref part :>> seam=GambitRuntimeComposition::blueprintInterface6; attribute :>> key="native-delivery"; attribute :>> actionName="settleNative"; attribute :>> guardName="s.result"; attribute :>> lemmaName="reloadMatches"; attribute :>> sourcePath="vendor/gambit/lib/setup.c"; attribute :>> sourceNeedle="___EXP_FUNC(___SCMOBJ,___call)"; attribute :>> premise="known rooted outcome plus exact epoch reload and execution grant; no repeated native effect caching"; attribute :>> retirement="Independent callback/result cleanup authorities after source closure"; attribute :>> benefit="One outcome custodian survives carrier exit and delivers only to admitted execution"; attribute :>> added="Outcome slots, roots, drain and per-shot effect execution"; attribute :>> gap="dynamic-wind, nested callback and exception observations remain open"; }
part contract9:Contract { ref part :>> seam=GambitRuntimeComposition::blueprintInterface7; attribute :>> key="artifact-reuse"; attribute :>> actionName="cacheHit"; attribute :>> guardName="s.planSource==s.source"; attribute :>> lemmaName="backendDoesNotChangePlan"; attribute :>> sourcePath="../gerbil-gambit-bootstrap-audit/src/gerbil/compiler/driver.ss"; attribute :>> sourceNeedle="(def (compile-scm-file"; attribute :>> premise="complete dynamic input trace, support identity, declarations, origins and frozen dependency snapshot"; attribute :>> retirement="Repeated unaffected expansion/file handoff/native work after producer/consumer equivalence"; attribute :>> benefit="Backend/tool-only change reuses valid frontend plan; safe consumers run concurrently"; attribute :>> added="Validation, fresh instances, query metadata and bounded scheduling"; attribute :>> gap="Complete registry/eval/native-read trace and result encoding remain open"; }
part contract10:Contract { ref part :>> seam=GambitRuntimeComposition::generatedEntryInterface; attribute :>> key="resumption-grant"; attribute :>> actionName="resume"; attribute :>> guardName="s.restored==s.epoch"; attribute :>> lemmaName="resumeKeepsIdentity"; attribute :>> sourcePath="vendor/gambit/lib/_thread.scm"; attribute :>> sourceNeedle="(define-prim (##continuation-graft-aux"; attribute :>> premise="same captured computation; private execution image per shot; reload and exclusive grant"; attribute :>> retirement="Opaque carrier ownership and duplicate restore root choreography after alias simulation"; attribute :>> benefit="Sequential multi-shot semantics remain reusable; effects are reexecuted as required"; attribute :>> added="Per-shot restore, wind, scheduling and possible COW"; attribute :>> gap="Finite shots do not prove unbounded or concurrent invocation; semantic simulation open"; }
part contract11:Contract { ref part :>> seam=GambitRuntimeComposition::blueprintInterface5; attribute :>> key="release-custody"; attribute :>> actionName="loseResult"; attribute :>> guardName="s.nativeDebt"; attribute :>> lemmaName="unknownRetainsCustody"; attribute :>> sourcePath="vendor/gambit/lib/mem.c"; attribute :>> sourceNeedle="free_still_objs ("; attribute :>> premise="all resource descendants and real native users retain VM custody after unknown result"; attribute :>> retirement="Inline arbitrary foreign destruction in GC critical phase after real caller replacement"; attribute :>> benefit="Admitted GC can finish without owner callback; release can drain separately"; attribute :>> added="Resource affinity queues, roots and potentially unbounded unknown retention"; attribute :>> gap="Device/Tcl/still destructor source closure and whole shutdown progress open"; }
part use0:AdvantageUse { ref part :>> advantage=advantage0; ref part :>> contract=contract0; attribute :>> obligation="AA-S"; }
part use1:AdvantageUse { ref part :>> advantage=advantage0; ref part :>> contract=contract1; attribute :>> obligation="AA-S"; }
part use2:AdvantageUse { ref part :>> advantage=advantage0; ref part :>> contract=contract2; attribute :>> obligation="AA-S"; }
part use3:AdvantageUse { ref part :>> advantage=advantage0; ref part :>> contract=contract8; attribute :>> obligation="AA-S"; }
part use4:AdvantageUse { ref part :>> advantage=advantage0; ref part :>> contract=contract10; attribute :>> obligation="AA-S"; }
part use5:AdvantageUse { ref part :>> advantage=advantage1; ref part :>> contract=contract1; attribute :>> obligation="AA-S"; }
part use6:AdvantageUse { ref part :>> advantage=advantage1; ref part :>> contract=contract0; attribute :>> obligation="AA-S"; }
part use7:AdvantageUse { ref part :>> advantage=advantage1; ref part :>> contract=contract8; attribute :>> obligation="AA-S"; }
part use8:AdvantageUse { ref part :>> advantage=advantage1; ref part :>> contract=contract4; attribute :>> obligation="AA-S"; }
part use9:AdvantageUse { ref part :>> advantage=advantage1; ref part :>> contract=contract9; attribute :>> obligation="AA-S"; }
part use10:AdvantageUse { ref part :>> advantage=advantage2; ref part :>> contract=contract1; attribute :>> obligation="AA-S"; }
part use11:AdvantageUse { ref part :>> advantage=advantage2; ref part :>> contract=contract2; attribute :>> obligation="AA-S"; }
part use12:AdvantageUse { ref part :>> advantage=advantage2; ref part :>> contract=contract3; attribute :>> obligation="AA-S"; }
part use13:AdvantageUse { ref part :>> advantage=advantage2; ref part :>> contract=contract5; attribute :>> obligation="AA-S"; }
part use14:AdvantageUse { ref part :>> advantage=advantage2; ref part :>> contract=contract6; attribute :>> obligation="AA-S"; }
part use15:AdvantageUse { ref part :>> advantage=advantage2; ref part :>> contract=contract7; attribute :>> obligation="AA-S"; }
part use16:AdvantageUse { ref part :>> advantage=advantage2; ref part :>> contract=contract10; attribute :>> obligation="AA-S"; }
part use17:AdvantageUse { ref part :>> advantage=advantage2; ref part :>> contract=contract11; attribute :>> obligation="AA-S"; }
part use18:AdvantageUse { ref part :>> advantage=advantage3; ref part :>> contract=contract3; attribute :>> obligation="AA-S"; }
part use19:AdvantageUse { ref part :>> advantage=advantage3; ref part :>> contract=contract0; attribute :>> obligation="AA-S"; }
part use20:AdvantageUse { ref part :>> advantage=advantage3; ref part :>> contract=contract5; attribute :>> obligation="AA-S"; }
part use21:AdvantageUse { ref part :>> advantage=advantage3; ref part :>> contract=contract6; attribute :>> obligation="AA-S"; }
part use22:AdvantageUse { ref part :>> advantage=advantage3; ref part :>> contract=contract9; attribute :>> obligation="AA-S"; }
part benefit0:Benefit { attribute :>> key="frame-support"; attribute :>> avoided="Duplicated semantic/layout decisions and repeated root choreography"; attribute :>> added="Schema, metadata, checked decoders and bootstrap"; attribute :>> condition="Actual old producer/consumer duties retire; not merely a wrapper"; attribute :>> evidence="Source anchors exist; full encoder/decoder/root equivalence open"; }
part benefit1:Benefit { attribute :>> key="multishot"; attribute :>> avoided="Eligible repeated representation work and clean mature graph minor scans"; attribute :>> added="Private restore, barriers, wind, suffix effects and alias handling"; attribute :>> condition="Saved graph work exceeds bookkeeping; effectful suffix is never memoized"; attribute :>> evidence="Finite two-shot custody and conditional unbounded identity laws; not Scheme simulation"; }
part benefit2:Benefit { attribute :>> key="gc-smp"; attribute :>> avoided="Mature traversal and blocked-owner-dependent collector work"; attribute :>> added="Remembered edges, promotion/copy reserve, synchronization and unknown retention"; attribute :>> condition="Avoided mature scan and eliminated waits exceed added work/space; all writers/participants close"; attribute :>> evidence="Existing GC is parallel copying/still, not proven generational; source refinement open"; }
part benefit3:Benefit { attribute :>> key="incremental"; attribute :>> avoided="Unchanged expansion/emission/native actions and unnecessary readiness waits"; attribute :>> added="Trace validation, private sessions, support instances and memory budget"; attribute :>> condition="Delta work is exact transitive consumed projection closure; saved span min(U,B) exceeds added critical path"; attribute :>> evidence="Two-consumer finite protocol; no 12-core utilization or Darwin speed multiplier established"; }
part benefit4:Benefit { attribute :>> key="shared-foundation"; attribute :>> avoided="Repeated per-module frame/root/FFI/build validation logic"; attribute :>> added="One schema and service authority plus integration proof"; attribute :>> condition="If old authorities remain, their cost remains; shared check is charged once per actual cohort"; attribute :>> evidence="No person-day or guessed speed numbers used"; }
part benefit5:Benefit { attribute :>> key="llvm-service"; attribute :>> avoided="Reanalysis of semantics already present in Scheme/GVM"; attribute :>> added="Dialect/lowering, full effects/GC/statepoint/continuation contract and toolchain invalidation"; attribute :>> condition="Semantic input exported before destructive C lowering; service upgrade invalidates only affected contracts"; attribute :>> evidence="MLIR not required for GC/SMP correctness; Zig has no demonstrated incremental benefit"; }
part open0:OpenScope { attribute :>> qualified=false; attribute :>> key="frame-simulation"; attribute :>> subjectPath="dev/refactoring/modern-c/models/sysml/modernization-target.sysml"; attribute :>> scope="MW-SEMANTIC-Q/L"; attribute :>> reason="All frame kinds, roots, tail/non-tail successors, module linkage and exact encoding"; }
part open1:OpenScope { attribute :>> qualified=false; attribute :>> key="continuation-observations"; attribute :>> subjectPath="dev/refactoring/modern-c/models/sysml/map-multishot-composition.sysml"; attribute :>> scope="MM-SIM; MM-FRAME; MW-CONTROL-Q/L"; attribute :>> reason="Values, dynamic-wind, mutation aliases, multiple values, exceptions and unbounded shots"; }
part open2:OpenScope { attribute :>> qualified=false; attribute :>> key="gc-writer-capacity"; attribute :>> subjectPath="dev/refactoring/modern-c/models/sysml/modernization-target.sysml"; attribute :>> scope="MW-HEAP-Q/L; MM-WRITERS"; attribute :>> reason="Complete stores, nursery policy, promotion failure, capacity conservation and weak phases"; }
part open3:OpenScope { attribute :>> qualified=false; attribute :>> key="smp-progress-memory"; attribute :>> subjectPath="dev/refactoring/modern-c/models/sysml/map-multishot-composition.sysml"; attribute :>> scope="MW-DOMAIN-Q/L; MM-MEMORY; MM-PROGRESS"; attribute :>> reason="Closed membership, private work, finite polls, C11 memory order and no wait cycles"; }
part open4:OpenScope { attribute :>> qualified=false; attribute :>> key="foreign-cleanup"; attribute :>> subjectPath="dev/architecture/toolchain/models/sysml/marker-alias-revocation.sysml"; attribute :>> scope="MAR-S/E; MW-FOREIGN-Q/L"; attribute :>> reason="Actual native callers, nonzero roots, callback/exception/continuation last use and resource descendants"; }
part open5:OpenScope { attribute :>> qualified=false; attribute :>> key="build-source-reflection"; attribute :>> subjectPath="dev/architecture/toolchain/models/sysml/iter-compiler-service.sysml"; attribute :>> scope="IS-S/E; MW-BUILD-Q/L"; attribute :>> reason="Dynamic dependency and phase/support closure, independent sessions, stable snapshots and observation reflection"; }
part open6:OpenScope { attribute :>> qualified=false; attribute :>> key="native-performance"; attribute :>> subjectPath="dev/refactoring/modern-c/modernization-target.org"; attribute :>> scope="unchanged native acceptance; matched full consumer metrics"; attribute :>> reason="Current receipt is design/model only; installed native capability and whole matched performance unresolved"; }
part history:GambitAssuranceRouting::ModelNeed { ref part :>> owner=GambitBuildAssurance::planner.component; attribute :>> obligationId="AA-H"; attribute :>> kind="interleaving"; attribute :>> subjectPath="dev/refactoring/modern-c/models/quint/advantage_architecture.qnt"; attribute :>> subjectScope="Finite two-participant/two-consumer/two-shot architecture custody and invalidation histories; no general semantic simulation"; attribute :>> premise="Paper motivates architecture; local finite/projection receipts never qualify whole-source composition, native adoption or speed"; }
part induction:GambitAssuranceRouting::ModelNeed { ref part :>> owner=GambitBuildAssurance::planner.component; attribute :>> obligationId="AA-I"; attribute :>> kind="induction"; attribute :>> subjectPath="dev/refactoring/modern-c/models/lean/AdvantageArchitecture.lean"; attribute :>> subjectScope="Typed counter/lease-independent product preservation, unbounded captured identity, cache projection and symbolic work/span laws; not all QNT actions"; attribute :>> premise="Paper motivates architecture; local finite/projection receipts never qualify whole-source composition, native adoption or speed"; }
part source:GambitAssuranceRouting::ModelNeed { ref part :>> owner=GambitBuildAssurance::planner.component; attribute :>> obligationId="AA-S"; attribute :>> kind="source-refinement"; attribute :>> subjectPath="dev/refactoring/modern-c/advantage-architecture-design.org"; attribute :>> subjectScope="All six existing replacement decisions and nine owners/interfaces; full Gambit/Gerbil source observation and model refinement OPEN"; attribute :>> premise="Paper motivates architecture; local finite/projection receipts never qualify whole-source composition, native adoption or speed"; }
part platform:GambitAssuranceRouting::ModelNeed { ref part :>> owner=GambitBuildAssurance::planner.component; attribute :>> obligationId="AA-E"; attribute :>> kind="environment-refinement"; attribute :>> subjectPath="dev/refactoring/modern-c/advantage-architecture-design.org"; attribute :>> subjectScope="Modern C memory order, target ABI, Darwin/Linux native equivalence, scheduler progress and measured work/span OPEN"; attribute :>> premise="Paper motivates architecture; local finite/projection receipts never qualify whole-source composition, native adoption or speed"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=IterCompilerService::source; }
part dependency4:GambitAssuranceRouting::NeedDependency { ref part :>> dependent=source; ref part :>> prerequisite=MarkerAliasRevocation::source; }
}
