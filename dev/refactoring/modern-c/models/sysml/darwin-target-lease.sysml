package GambitDarwinTargetLease { private import ScalarValues::*;
part def SourceRow { attribute key:String; attribute path:String; attribute needle:String; attribute limit:String; }
part source0:SourceRow { attribute :>> key="vendor-config"; attribute :>> path="vendor/gambit/include/config.h"; attribute :>> needle="/* #undef ___CAN_IMPORT_DYNAMICALLY */"; attribute :>> limit="configured defaults; not loaded consumer flags"; }
part source1:SourceRow { attribute :>> key="vendor-status"; attribute :>> path="vendor/gambit/config.status"; attribute :>> needle="'--disable-smp'"; attribute :>> limit="current vendor cohort disables SMP/multiple VMs"; }
part source2:SourceRow { attribute :>> key="vendor-driver"; attribute :>> path="vendor/gambit/bin/gambuild-C.unix"; attribute :>> needle="-D___DYNAMIC"; attribute :>> limit="dynamic-mode default flag only"; }
part source3:SourceRow { attribute :>> key="vendor-header"; attribute :>> path="vendor/gambit/include/gambit.h"; attribute :>> needle="#ifdef ___DYNAMIC"; attribute :>> limit="dynamic forces late binding unless conflicts/overrides"; }
part source4:SourceRow { attribute :>> key="vendor-make"; attribute :>> path="vendor/gambit/lib/makefile"; attribute :>> needle="-D___LIBRARY"; attribute :>> limit="runtime library recipe does not imply DYNAMIC"; }
part source5:SourceRow { attribute :>> key="retained-config"; attribute :>> path="../ci-source-patch-check/src/gambit/include/config.h"; attribute :>> needle="/* #undef ___DEBUG_LOG */"; attribute :>> limit="separate retained Darwin cohort"; }
part source6:SourceRow { attribute :>> key="retained-status"; attribute :>> path="../ci-source-patch-check/src/gambit/config.status"; attribute :>> needle="'--enable-smp'"; attribute :>> limit="retained cohort enables SMP/multiple VMs"; }
part source7:SourceRow { attribute :>> key="retained-driver"; attribute :>> path="../ci-source-patch-check/src/gambit/bin/gambuild-C.unix"; attribute :>> needle="C_COMPILER=\"/opt/homebrew/bin/gcc-16\""; attribute :>> limit="retained exact generated driver"; }
part source8:SourceRow { attribute :>> key="retained-header"; attribute :>> path="../ci-source-patch-check/src/gambit/include/gambit.h"; attribute :>> needle="#define ___EXT(f)(___GSTATE->f)"; attribute :>> limit="retained monolithic generated header, not current modular ABI"; }
part source9:SourceRow { attribute :>> key="retained-base"; attribute :>> path="../ci-source-patch-check/src/gambit/lib/os_base.c"; attribute :>> needle="ptr = malloc (bytes);"; attribute :>> limit="byte equality to current allocator wrapper checked independently"; }
part source10:SourceRow { attribute :>> key="allocator"; attribute :>> path="vendor/gambit/lib/os_base.c"; attribute :>> needle="ptr = malloc (bytes);"; attribute :>> limit="raw libc import; dyld provider not determined"; }
part source11:SourceRow { attribute :>> key="free"; attribute :>> path="vendor/gambit/lib/os_base.c"; attribute :>> needle="free (ptr);"; attribute :>> limit="matching family and wrapper/ABI lifetime must persist"; }
part source12:SourceRow { attribute :>> key="logger"; attribute :>> path="vendor/gambit/lib/os_base.c"; attribute :>> needle="result = vfprintf (stream, format, ap);"; attribute :>> limit="debug branch; fflush follows"; }
part source13:SourceRow { attribute :>> key="stream-setup"; attribute :>> path="vendor/gambit/lib/os_base.c"; attribute :>> needle="___base_mod.debug = ___fopen (\"gambit.log\", \"w\");"; attribute :>> limit="fopen or stderr fallback under DEBUG_LOG"; }
part source14:SourceRow { attribute :>> key="stream-close"; attribute :>> path="vendor/gambit/lib/os_base.c"; attribute :>> needle="___fclose (___base_mod.debug);"; attribute :>> limit="cleanup closes owned log stream, not stderr"; }
part source15:SourceRow { attribute :>> key="base-state"; attribute :>> path="vendor/gambit/lib/os_base.h"; attribute :>> needle="extern ___base_module ___base_mod;"; attribute :>> limit="public alias to base state; refcount is not active-I/O enrollment"; }
part source16:SourceRow { attribute :>> key="rts-bind"; attribute :>> path="vendor/gambit/lib/setup.c"; attribute :>> needle="= ___alloc_mem;"; attribute :>> limit="named table initialization, not all-writer closure"; }
part source17:SourceRow { attribute :>> key="free-bind"; attribute :>> path="vendor/gambit/lib/setup.c"; attribute :>> needle="= ___free_mem;"; attribute :>> limit="named free table initializer"; }
part source18:SourceRow { attribute :>> key="state-escape"; attribute :>> path="vendor/gambit/lib/setup.c"; attribute :>> needle="___mod_or_lnk mol = linker (___GSTATE);"; attribute :>> limit="native linker receives mutable global state"; }
part source19:SourceRow { attribute :>> key="ext-mode"; attribute :>> path="vendor/gambit/include/_gambit/module_generation.h.in"; attribute :>> needle="#define ___EXT(f)(___GSTATE->f)"; attribute :>> limit="Gambit runtime indirection differs from CLIBEXT"; }
part source20:SourceRow { attribute :>> key="abi"; attribute :>> path="vendor/gambit/include/_gambit/global_state.h.in"; attribute :>> needle="void *(*___alloc_mem)"; attribute :>> limit="DEBUG_ALLOC_MEM changes function-pointer call signature"; }
part source21:SourceRow { attribute :>> key="alloc-protocol"; attribute :>> path="vendor/gambit/include/_gambit/runtime_protocols.h.in"; attribute :>> needle="#define ___ALLOC_MEM(bytes)"; attribute :>> limit="ordinary/debug wrapper ABI branches"; }
part source22:SourceRow { attribute :>> key="rc-private"; attribute :>> path="vendor/gambit/lib/_mem/rc-allocation.inc"; attribute :>> needle="h = ___CAST(___rc_header*, ___ALLOC_MEM"; attribute :>> limit="native return precedes private header initialization"; }
part source23:SourceRow { attribute :>> key="native-prefix"; attribute :>> path="dev/refactoring/modern-c/models/lean/NativePrefixAst.lean"; attribute :>> needle="def grantFastGuard"; attribute :>> limit="actual upstream effect-grant consumer"; }
part source24:SourceRow { attribute :>> key="native-extent-paper"; attribute :>> path="evidence/research/source-references/feeley-sfp/8bb2fae8ae4b54d3a86206596f90e9cf73da39846af0f39244a476074cf81ed4.txt"; attribute :>> needle="5       Pra"; attribute :>> limit="Scheme/native extent distinction; not a provider lease theorem"; }
part def CohortRow { attribute key:String; attribute source:String; attribute compiler:String; attribute smp:String; attribute multipleVMs:String; attribute status:String; }
part cohort0:CohortRow { attribute :>> key="vendor"; attribute :>> source="vendor-status"; attribute :>> compiler="/opt/homebrew/Cellar/gcc/16.2.0/bin/gcc-16 -B/usr/bin/"; attribute :>> smp="disabled"; attribute :>> multipleVMs="disabled"; attribute :>> status="configured-source-only"; }
part cohort1:CohortRow { attribute :>> key="retained"; attribute :>> source="retained-status"; attribute :>> compiler="/opt/homebrew/bin/gcc-16"; attribute :>> smp="enabled"; attribute :>> multipleVMs="enabled"; attribute :>> status="configured-source-only"; }
part def BindingRow { attribute key:String; attribute cohort:String; attribute mode:String; attribute source:String; attribute dynamic:String; attribute extRoute:String; attribute clibRoute:String; attribute debugLog:String; attribute debugAlloc:String; attribute signature:String; attribute boundary:String; }
part binding0:BindingRow { attribute :>> key="vendor-OBJ"; attribute :>> cohort="vendor"; attribute :>> mode="OBJ"; attribute :>> source="vendor-driver"; attribute :>> dynamic="no"; attribute :>> extRoute="direct-runtime-symbol"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part binding1:BindingRow { attribute :>> key="vendor-DYN"; attribute :>> cohort="vendor"; attribute :>> mode="DYN"; attribute :>> source="vendor-driver"; attribute :>> dynamic="yes"; attribute :>> extRoute="GSTATE-slot"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part binding2:BindingRow { attribute :>> key="vendor-RTS"; attribute :>> cohort="vendor"; attribute :>> mode="RTS"; attribute :>> source="vendor-driver"; attribute :>> dynamic="no"; attribute :>> extRoute="direct-runtime-symbol"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part binding3:BindingRow { attribute :>> key="retained-OBJ"; attribute :>> cohort="retained"; attribute :>> mode="OBJ"; attribute :>> source="retained-driver"; attribute :>> dynamic="no"; attribute :>> extRoute="direct-runtime-symbol"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part binding4:BindingRow { attribute :>> key="retained-DYN"; attribute :>> cohort="retained"; attribute :>> mode="DYN"; attribute :>> source="retained-driver"; attribute :>> dynamic="yes"; attribute :>> extRoute="GSTATE-slot"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part binding5:BindingRow { attribute :>> key="retained-RTS"; attribute :>> cohort="retained"; attribute :>> mode="RTS"; attribute :>> source="retained-driver"; attribute :>> dynamic="no"; attribute :>> extRoute="direct-runtime-symbol"; attribute :>> clibRoute="direct-CLIBEXT; allocator itself calls bare malloc/free"; attribute :>> debugLog="disabled-default"; attribute :>> debugAlloc="disabled-default"; attribute :>> signature="alloc(size)/free(ptr)"; attribute :>> boundary="recorded driver defaults without additional flags; loaded image binding unresolved"; }
part def WriterRow { attribute key:String; attribute source:String; attribute storage:String; attribute known:String; attribute closure:String; }
part writer0:WriterRow { attribute :>> key="runtime-slots"; attribute :>> source="rts-bind"; attribute :>> storage="GSTATE alloc_mem/free_mem function fields"; attribute :>> known="setup.c installs corresponding runtime symbols"; attribute :>> closure="no source evidence of sealing all native alias writers"; }
part writer1:WriterRow { attribute :>> key="native-linker"; attribute :>> source="state-escape"; attribute :>> storage="GSTATE and reachable function fields"; attribute :>> known="linker receives actual mutable state pointer"; attribute :>> closure="arbitrary external C cannot be exhaustively closed by named-assignment search"; }
part writer2:WriterRow { attribute :>> key="log-stream"; attribute :>> source="stream-setup"; attribute :>> storage="base_mod.debug and FILE lifetime"; attribute :>> known="setup assigns fopen result or stderr; cleanup closes owned stream"; attribute :>> closure="base refcount does not count in-flight printf/fflush"; }
part writer3:WriterRow { attribute :>> key="base-lifecycle"; attribute :>> source="base-state"; attribute :>> storage="base_mod.refcount and debug state"; attribute :>> known="setup increments and cleanup decrements module refcount"; attribute :>> closure="call/VM lifecycle and external alias closure required"; }
part writer4:WriterRow { attribute :>> key="libc-provider"; attribute :>> source="allocator"; attribute :>> storage="raw malloc/free imported targets and allocator family"; attribute :>> known="source calls bare C symbols"; attribute :>> closure="not controlled by GSTATE epoch; loaded image/interposition unresolved"; }
part writer5:WriterRow { attribute :>> key="debug-abi"; attribute :>> source="abi"; attribute :>> storage="function-pointer signature plus consumer declarations"; attribute :>> known="size vs size,line,file branches selected by DEBUG_ALLOC_MEM"; attribute :>> closure="runtime/modules need same ABI; cannot live-rebind across incompatible signature"; }
part def IssuerRow { attribute key:String; attribute source:String; attribute signature:String; attribute condition:String; attribute gap:String; }
part issuer0:IssuerRow { attribute :>> key="profile-owner"; attribute :>> source="vendor-driver"; attribute :>> signature="cohort, request/include order, ABI and consumer mode"; attribute :>> condition="bind exact generated flags and override policy"; attribute :>> gap="no single effective binary/profile attested"; }
part issuer1:IssuerRow { attribute :>> key="provider-owner"; attribute :>> source="allocator"; attribute :>> signature="wrapper and external import closure plus allocator family"; attribute :>> condition="pin code/images/state and matching free domain"; attribute :>> gap="direct symbol route is not a loaded provider certificate"; }
part issuer2:IssuerRow { attribute :>> key="bundle-registry"; attribute :>> source="rts-bind"; attribute :>> signature="immutable ProviderBundle and generation admission word"; attribute :>> condition="lease acquire and close have one linearization; all writers mediated"; attribute :>> gap="old raw EXT readers are not this interface"; }
part issuer3:IssuerRow { attribute :>> key="origin-owner"; attribute :>> source="rc-private"; attribute :>> signature="operation record, pointer or unknown debt, allocator/free origin"; attribute :>> condition="reserve before call; keep origin hold after invocation ends"; attribute :>> gap="native pointer capture and same-operation recovery adapter missing"; }
part issuer4:IssuerRow { attribute :>> key="stream-owner"; attribute :>> source="stream-close"; attribute :>> signature="FILE ownership and in-flight bundle dependency"; attribute :>> condition="close after all dependencies including future origin frees drain"; attribute :>> gap="current refcount does not prove this order"; }
part def RouteRow { attribute actionName:String; attribute lemma:String; attribute source:String; attribute obligationId:String; }
part route0:RouteRow { attribute :>> actionName="publishPlain"; attribute :>> lemma="TargetLease.publishPlainPreserves"; attribute :>> source="rts-bind"; attribute :>> obligationId="lease-safety"; }
part route1:RouteRow { attribute :>> actionName="publishAdmittedHooks"; attribute :>> lemma="TargetLease.publishAdmittedHooksPreserves"; attribute :>> source="rts-bind"; attribute :>> obligationId="lease-safety"; }
part route2:RouteRow { attribute :>> actionName="acquireOuter"; attribute :>> lemma="TargetLease.acquireOuterPreserves"; attribute :>> source="rts-bind"; attribute :>> obligationId="lease-safety"; }
part route3:RouteRow { attribute :>> actionName="closeOrdinary"; attribute :>> lemma="TargetLease.closeOrdinaryPreserves"; attribute :>> source="rts-bind"; attribute :>> obligationId="lease-safety"; }
part route4:RouteRow { attribute :>> actionName="publishReplacement"; attribute :>> lemma="TargetLease.publishReplacementPreserves"; attribute :>> source="rts-bind"; attribute :>> obligationId="lease-safety"; }
part route5:RouteRow { attribute :>> actionName="beginMalloc"; attribute :>> lemma="TargetLease.beginMallocPreserves"; attribute :>> source="rc-private"; attribute :>> obligationId="lease-safety"; }
part route6:RouteRow { attribute :>> actionName="obtainPointer"; attribute :>> lemma="TargetLease.obtainPointerPreserves"; attribute :>> source="rc-private"; attribute :>> obligationId="lease-safety"; }
part route7:RouteRow { attribute :>> actionName="recordSuccess"; attribute :>> lemma="TargetLease.recordSuccessPreserves"; attribute :>> source="rc-private"; attribute :>> obligationId="lease-safety"; }
part route8:RouteRow { attribute :>> actionName="recordNull"; attribute :>> lemma="TargetLease.recordNullPreserves"; attribute :>> source="rc-private"; attribute :>> obligationId="lease-safety"; }
part route9:RouteRow { attribute :>> actionName="enterNested"; attribute :>> lemma="TargetLease.enterNestedPreserves"; attribute :>> source="rts-bind"; attribute :>> obligationId="lease-safety"; }
part route10:RouteRow { attribute :>> actionName="leaveNested"; attribute :>> lemma="TargetLease.leaveNestedPreserves"; attribute :>> source="rts-bind"; attribute :>> obligationId="lease-safety"; }
part route11:RouteRow { attribute :>> actionName="loseBeforeCapture"; attribute :>> lemma="TargetLease.loseBeforeCapturePreserves"; attribute :>> source="rc-private"; attribute :>> obligationId="lease-safety"; }
part route12:RouteRow { attribute :>> actionName="loseRecordedAck"; attribute :>> lemma="TargetLease.loseRecordedAckPreserves"; attribute :>> source="rts-bind"; attribute :>> obligationId="lease-safety"; }
part route13:RouteRow { attribute :>> actionName="recoverRecorded"; attribute :>> lemma="TargetLease.recoverRecordedPreserves"; attribute :>> source="rts-bind"; attribute :>> obligationId="lease-safety"; }
part route14:RouteRow { attribute :>> actionName="releaseOuter"; attribute :>> lemma="TargetLease.releaseOuterPreserves"; attribute :>> source="rts-bind"; attribute :>> obligationId="lease-safety"; }
part route15:RouteRow { attribute :>> actionName="beginOriginFree"; attribute :>> lemma="TargetLease.beginOriginFreePreserves"; attribute :>> source="free"; attribute :>> obligationId="lease-safety"; }
part route16:RouteRow { attribute :>> actionName="applyFree"; attribute :>> lemma="TargetLease.applyFreePreserves"; attribute :>> source="free"; attribute :>> obligationId="lease-safety"; }
part route17:RouteRow { attribute :>> actionName="recordFreeBackend"; attribute :>> lemma="TargetLease.recordFreeBackendPreserves"; attribute :>> source="free"; attribute :>> obligationId="lease-safety"; }
part route18:RouteRow { attribute :>> actionName="loseFreeReturn"; attribute :>> lemma="TargetLease.loseFreeReturnPreserves"; attribute :>> source="free"; attribute :>> obligationId="lease-safety"; }
part route19:RouteRow { attribute :>> actionName="settleFree"; attribute :>> lemma="TargetLease.settleFreePreserves"; attribute :>> source="free"; attribute :>> obligationId="lease-safety"; }
part route20:RouteRow { attribute :>> actionName="reconcileFree"; attribute :>> lemma="TargetLease.reconcileFreePreserves"; attribute :>> source="free"; attribute :>> obligationId="lease-safety"; }
part route21:RouteRow { attribute :>> actionName="releaseMaintenance"; attribute :>> lemma="TargetLease.releaseMaintenancePreserves"; attribute :>> source="rts-bind"; attribute :>> obligationId="lease-safety"; }
part route22:RouteRow { attribute :>> actionName="retireOldBundle"; attribute :>> lemma="TargetLease.retireOldBundlePreserves"; attribute :>> source="rts-bind"; attribute :>> obligationId="lease-safety"; }
part def ComponentRow { attribute componentId:String; attribute actionSlice:String; attribute sharedContract:String; attribute proof:String; attribute source:String; }
part component0:ComponentRow { attribute :>> componentId="provider-admission"; attribute :>> actionSlice="publishPlain/acquireOuter/closeOrdinary/publishReplacement"; attribute :>> sharedContract="writer-closure"; attribute :>> proof="TargetLease.closureBlocksOrdinaryAcquire"; attribute :>> source="rts-bind"; }
part component1:ComponentRow { attribute :>> componentId="invocation-drain"; attribute :>> actionSlice="enterNested/leaveNested/releaseOuter"; attribute :>> sharedContract="lease-safety"; attribute :>> proof="TargetLease.closeDoesNotDrain"; attribute :>> source="ext-mode"; }
part component2:ComponentRow { attribute :>> componentId="origin-custody"; attribute :>> actionSlice="beginMalloc/recordSuccess/loseBeforeCapture/recoverRecorded"; attribute :>> sharedContract="allocation-capture"; attribute :>> proof="TargetLease.unknownKeepsOrigin"; attribute :>> source="rc-private"; }
part component3:ComponentRow { attribute :>> componentId="origin-cleanup"; attribute :>> actionSlice="beginOriginFree/applyFree/recordFreeBackend/reconcileFree"; attribute :>> sharedContract="free-receipt"; attribute :>> proof="TargetLease.originFreeUsesOldFamily"; attribute :>> source="free"; }
part component4:ComponentRow { attribute :>> componentId="bundle-retirement"; attribute :>> actionSlice="releaseMaintenance/retireOldBundle"; attribute :>> sharedContract="native-retirement"; attribute :>> proof="TargetLease.retirementNeedsAllDebts"; attribute :>> source="stream-close"; }
part def JoinRow { attribute key:String; attribute lemma:String; attribute source:String; attribute premise:String; attribute status:String; }
part join0:JoinRow { attribute :>> key="plain-prefix-grant"; attribute :>> lemma="TargetLease.plainPrefixStep"; attribute :>> source="native-prefix"; attribute :>> premise="certificate includes no-GC/no-reentry/no-abandon and upstream source/native lifetime premises"; attribute :>> status="conditional-lemma"; }
part join1:JoinRow { attribute :>> key="hook-prefix-grant"; attribute :>> lemma="TargetLease.hookPrefixStep"; attribute :>> source="native-prefix"; attribute :>> premise="admitted hook summary and upstream complete durable source set"; attribute :>> status="conditional-lemma"; }
part join2:JoinRow { attribute :>> key="origin-not-call"; attribute :>> lemma="TargetLease.oldOriginPinsProvider"; attribute :>> source="rc-private"; attribute :>> premise="old allocator/free family and provider handles live with the origin"; attribute :>> status="conditional-lemma"; }
part join3:JoinRow { attribute :>> key="unknown-not-free"; attribute :>> lemma="TargetLease.appliedFreeIsNotReceipt"; attribute :>> source="free"; attribute :>> premise="actual effect ghost is not observable backend receipt"; attribute :>> status="conditional-lemma"; }
part def ObligationRow { attribute key:String; attribute status:String; attribute condition:String; }
part obligation0:ObligationRow { attribute :>> key="lease-safety"; attribute :>> status="conditional-model"; attribute :>> condition="23 actions preserve invocation and origin custody across close/replacement"; }
part obligation1:ObligationRow { attribute :>> key="prefix-join"; attribute :>> status="conditional-model"; attribute :>> condition="actual NativePrefix fast/durable Step joins at acquisition"; }
part obligation2:ObligationRow { attribute :>> key="configured-branches"; attribute :>> status="source-bound"; attribute :>> condition="two coherent static Darwin cohorts and six mode/default reductions"; }
part obligation3:ObligationRow { attribute :>> key="effective-loader"; attribute :>> status="unresolved"; attribute :>> condition="actual consumer argv/include order, Mach-O/provider images and import binding; no executable artifact qualified"; }
part obligation4:ObligationRow { attribute :>> key="writer-closure"; attribute :>> status="unresolved"; attribute :>> condition="all GSTATE, bundle, stream and loader mutation paths mediated or excluded"; }
part obligation5:ObligationRow { attribute :>> key="allocation-capture"; attribute :>> status="unresolved"; attribute :>> condition="native return before stable capture cannot abandon or retains recoverable same-operation custody"; }
part obligation6:ObligationRow { attribute :>> key="free-receipt"; attribute :>> status="unresolved"; attribute :>> condition="known free receipt before debt settlement; libc free itself returns no such durable record"; }
part obligation7:ObligationRow { attribute :>> key="native-retirement"; attribute :>> status="unresolved"; attribute :>> condition="real callback/GC/maintenance/module/image/FILE users close and drain before release"; }
part obligation8:ObligationRow { attribute :>> key="c23-refinement"; attribute :>> status="unresolved"; attribute :>> condition="linearizable enrollment/close, release/acquire publication and actual reads-from/storage types"; }
part obligation9:ObligationRow { attribute :>> key="native-product"; attribute :>> status="unresolved"; attribute :>> condition="lease/origin/root/return-domain composition and unbounded participants; bounded join only"; }
part def MemoryRow { attribute key:String; attribute ordering:String; attribute premise:String; attribute obligationId:String; }
part memory0:MemoryRow { attribute :>> key="publish"; attribute :>> ordering="release immutable bundle; acquire same bundle before native dereference"; attribute :>> premise="snapshot includes wrapper, family, ABI and provider dependencies"; attribute :>> obligationId="c23-refinement"; }
part memory1:MemoryRow { attribute :>> key="close"; attribute :>> ordering="single admission order for ordinary acquire versus close"; attribute :>> premise="raw load followed by independent increment cannot serve as proof"; attribute :>> obligationId="c23-refinement"; }
part memory2:MemoryRow { attribute :>> key="last-use"; attribute :>> ordering="release call enrollment after stable completion and final target access"; attribute :>> premise="do not read freed bundle to decide whether to release its count"; attribute :>> obligationId="native-retirement"; }
part memory3:MemoryRow { attribute :>> key="origin"; attribute :>> ordering="register origin debt before allocator invocation; retain matching deallocator"; attribute :>> premise="call lease retirement does not settle a successful or unknown allocation"; attribute :>> obligationId="allocation-capture"; }
part memory4:MemoryRow { attribute :>> key="maintenance"; attribute :>> ordering="derive cleanup authority from captured origin after ordinary closure; root storage reclaim permit already required"; attribute :>> premise="not a fresh ordinary grant; unknown free keeps origin/provider pins"; attribute :>> obligationId="free-receipt"; }
part memory5:MemoryRow { attribute :>> key="legacy"; attribute :>> ordering="atomic replacement needs new opaque storage/access protocol or quiescent compatibility write"; attribute :>> premise="legacy function-pointer fields and ordinary reads cannot be made C23 atomic by casting"; attribute :>> obligationId="writer-closure"; }
part def GainRow { attribute key:String; attribute benefit:String; attribute overhead:String; attribute positive:String; attribute refutation:String; }
part gain0:GainRow { attribute :>> key="immutable-install"; attribute :>> benefit="static lifetime certificate may erase per-call counter traffic"; attribute :>> overhead="provider/lifecycle closure and immutable targets still need proof"; attribute :>> positive="no live rebind/unload or premature base teardown; stable family for all origins"; attribute :>> refutation="adding hot replacement or global counters without a use case increases maintenance/work"; }
part gain1:GainRow { attribute :>> key="scope-amortization"; attribute :>> benefit="one lease can cover the whole native prefix dependency bundle"; attribute :>> overhead="one enrollment and one settlement per scope in replaceable mode, not per EXT read"; attribute :>> positive="all nested calls and free/log dependencies use captured bundle"; attribute :>> refutation="reload mutable GSTATE for each dependency mixes generations"; }
part gain2:GainRow { attribute :>> key="allocation-origin"; attribute :>> benefit="match free to old allocator family after call finishes or replacement"; attribute :>> overhead="one origin hold per outstanding non-null or unknown allocation"; attribute :>> positive="reuse existing stable allocation/cleanup ledger"; attribute :>> refutation="zero readers does not imply allocator code or family can retire"; }
part gain3:GainRow { attribute :>> key="debug-default"; attribute :>> benefit="no new log-stream lease is needed for default-disabled logging"; attribute :>> overhead="debug override requires separate ABI and FILE lifecycle qualification"; attribute :>> positive="both configured cohorts retain DEBUG_LOG and DEBUG_ALLOC_MEM disabled"; attribute :>> refutation="conditional logging cost must not be charged to ordinary default allocation"; }
part gain4:GainRow { attribute :>> key="unknown"; attribute :>> benefit="zero blind free/realloc replay after unknown completion"; attribute :>> overhead="provider/stream/root/intent retention may be unbounded"; attribute :>> positive="same-operation backend receipt proves known result"; attribute :>> refutation="freeApplied ghost or a timeout cannot authorize reclamation"; }
part gain5:GainRow { attribute :>> key="c23-baseline"; attribute :>> benefit="unify checked target/ownership services in modern C"; attribute :>> overhead="legacy compatibility, native ABI and loader qualification remain"; attribute :>> positive="retire managed raw table reads only after caller migration"; attribute :>> refutation="Zig does not remove allocator family, I/O or C lifetime proofs"; }
part def EdgeRow { attribute fromNode:String; attribute toNode:String; attribute contract:String; }
part edge0:EdgeRow { attribute :>> fromNode="vendor_cohort"; attribute :>> toNode="mode_plan"; attribute :>> contract="No SMP/multiple VMs; keep own hashes"; }
part edge1:EdgeRow { attribute :>> fromNode="retained_cohort"; attribute :>> toNode="mode_plan"; attribute :>> contract="SMP/multiple VMs; keep own hashes"; }
part edge2:EdgeRow { attribute :>> fromNode="mode_plan"; attribute :>> toNode="wrapper_binding"; attribute :>> contract="OBJ/RTS direct; DYN GSTATE slot under recorded defaults"; }
part edge3:EdgeRow { attribute :>> fromNode="wrapper_binding"; attribute :>> toNode="external_imports"; attribute :>> contract="bare malloc/free provider not covered by GSTATE generation"; }
part edge4:EdgeRow { attribute :>> fromNode="external_imports"; attribute :>> toNode="ProviderBundle"; attribute :>> contract="ABI + family + images + optional FILE owner"; }
part edge5:EdgeRow { attribute :>> fromNode="ProviderBundle"; attribute :>> toNode="call_lease"; attribute :>> contract="atomic acquisition versus ordinary close"; }
part edge6:EdgeRow { attribute :>> fromNode="call_lease"; attribute :>> toNode="NativePrefix"; attribute :>> contract="actual conditional fast/durable grant Step"; }
part edge7:EdgeRow { attribute :>> fromNode="call_lease"; attribute :>> toNode="origin_debt"; attribute :>> contract="reserve before malloc; record same operation"; }
part edge8:EdgeRow { attribute :>> fromNode="origin_debt"; attribute :>> toNode="unknown_custodian"; attribute :>> contract="uncaptured pointer retains provider; no retry"; }
part edge9:EdgeRow { attribute :>> fromNode="origin_debt"; attribute :>> toNode="maintenance_lease"; attribute :>> contract="closed ordinary gate still permits origin cleanup"; }
part edge10:EdgeRow { attribute :>> fromNode="maintenance_lease"; attribute :>> toNode="old_free_family"; attribute :>> contract="captured origin, never current replacement"; }
part edge11:EdgeRow { attribute :>> fromNode="old_free_family"; attribute :>> toNode="free_receipt"; attribute :>> contract="physical free effect alone is not receipt"; }
part edge12:EdgeRow { attribute :>> fromNode="free_receipt"; attribute :>> toNode="debt_settlement"; attribute :>> contract="release only after known completion"; }
part edge13:EdgeRow { attribute :>> fromNode="call_lease"; attribute :>> toNode="nested_use"; attribute :>> contract="parent authority retains same bundle"; }
part edge14:EdgeRow { attribute :>> fromNode="debt_settlement"; attribute :>> toNode="retirement"; attribute :>> contract="all ordinary/nested/maintenance/origin/unknown users drained"; }
part edge15:EdgeRow { attribute :>> fromNode="retirement"; attribute :>> toNode="stream_and_images"; attribute :>> contract="release FILE/code/state only after final dependency"; }
part edge16:EdgeRow { attribute :>> fromNode="SysML"; attribute :>> toNode="ASCENT"; attribute :>> contract="cohorts, binding rows, writer and issuer contracts"; }
part edge17:EdgeRow { attribute :>> fromNode="SysML"; attribute :>> toNode="QNT"; attribute :>> contract="23 explicit atomic steps"; }
part edge18:EdgeRow { attribute :>> fromNode="QNT"; attribute :>> toNode="Lean"; attribute :>> contract="typed IR and all-step preservation"; }
part edge19:EdgeRow { attribute :>> fromNode="Lean"; attribute :>> toNode="ASCENT"; attribute :>> contract="compiled joins; loaded native gaps remain blocked"; }
part source25:SourceRow { attribute :>> key="retained-make"; attribute :>> path="../ci-source-patch-check/src/gambit/lib/makefile"; attribute :>> needle="-D___LIBRARY"; attribute :>> limit="retained runtime recipe, separate from generated driver modes"; }
part source26:SourceRow { attribute :>> key="rc-unlink"; attribute :>> path="vendor/gambit/lib/_mem/rc-allocation.inc"; attribute :>> needle="h->next->prev = h->prev;"; attribute :>> limit="RC unlinks root storage before FREE_MEM; root retirement is a separate prerequisite"; }
}
