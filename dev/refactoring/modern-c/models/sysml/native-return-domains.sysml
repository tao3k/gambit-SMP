package GambitNativeReturnDomains { private import ScalarValues::*;
part def Owner { attribute componentId:String; }
part threadOwner:Owner { attribute :>> componentId="thread"; }
part returnOwner:Owner { attribute :>> componentId="return"; }
part controlOwner:Owner { attribute :>> componentId="control"; }
part rootsOwner:Owner { attribute :>> componentId="roots"; }
part def SourceRow { attribute key:String; attribute path:String; attribute needle:String; attribute obligation:String; }
part source0:SourceRow { attribute :>> key="return-owner"; attribute :>> path="vendor/gambit/lib/_kernel.scm"; attribute :>> needle="/* not the same processor that created frame */"; attribute :>> obligation="owner-affinity"; }
part source1:SourceRow { attribute :>> key="return-stale"; attribute :>> path="vendor/gambit/lib/_kernel.scm"; attribute :>> needle="/* not first return */"; attribute :>> obligation="one-native-return"; }
part source2:SourceRow { attribute :>> key="return-unwind"; attribute :>> path="vendor/gambit/lib/_kernel.scm"; attribute :>> needle="___throw_error (___PSP ___FIX(___UNWIND_C_STACK));"; attribute :>> obligation="live-catcher"; }
part source3:SourceRow { attribute :>> key="call-frame"; attribute :>> path="vendor/gambit/lib/setup.c"; attribute :>> needle="___fp[-2] = stack_marker;"; attribute :>> obligation="frame-marker-coordinate"; }
part source4:SourceRow { attribute :>> key="call-catcher"; attribute :>> path="vendor/gambit/lib/setup.c"; attribute :>> needle="stack_marker != ___ps->context->fp[___FRAME_SPACE(2)-2]"; attribute :>> obligation="unwind-destination"; }
part source5:SourceRow { attribute :>> key="marker-root"; attribute :>> path="vendor/gambit/lib/c_intf.c"; attribute :>> needle="proc_or_false = *proc_root; /* reload after allocating the marker */"; attribute :>> obligation="root-reload"; }
part source6:SourceRow { attribute :>> key="marker-kill"; attribute :>> path="vendor/gambit/lib/c_intf.c"; attribute :>> needle="___VECTORELEM(marker, 0) = ___FAL; /* invalidate the C stack frame */"; attribute :>> obligation="return-invalidation"; }
part source7:SourceRow { attribute :>> key="legacy-root"; attribute :>> path="vendor/gambit/lib/c_intf.c"; attribute :>> needle="wrapper. Managed startup uses the explicit rooted endpoint above."; attribute :>> obligation="legacy-not-rooted"; }
part source8:SourceRow { attribute :>> key="catcher-local"; attribute :>> path="vendor/gambit/include/_gambit/foreign_conversion.h.in"; attribute :>> needle="___jmpbuf_struct ___jbuf, *___old_catcher = ___ps->catcher;"; attribute :>> obligation="c-stack-dynamic-extent"; }
part source9:SourceRow { attribute :>> key="catcher-restore"; attribute :>> path="vendor/gambit/include/_gambit/foreign_conversion.h.in"; attribute :>> needle="#define ___END_TRY } ___ps->catcher = ___old_catcher; }"; attribute :>> obligation="nested-catcher-restore"; }
part source10:SourceRow { attribute :>> key="continuation-closure"; attribute :>> path="vendor/gambit/lib/_thread.scm"; attribute :>> needle="(##continuation-return-aux cont val1 val2 val3 others)"; attribute :>> obligation="multi-shot-logical-control"; }
part source11:SourceRow { attribute :>> key="wind-user"; attribute :>> path="vendor/gambit/lib/_thread.scm"; attribute :>> needle="((macro-dynwind-after src))"; attribute :>> obligation="reentrant-winding"; }
part source12:SourceRow { attribute :>> key="direct-no-winding"; attribute :>> path="vendor/gambit/lib/_thread.scm"; attribute :>> needle="(define-prim ##continuation-return-no-winding"; attribute :>> obligation="cannot-use-dynamic-wind-only"; }
part source13:SourceRow { attribute :>> key="saved-roots"; attribute :>> path="vendor/gambit/lib/_mem/root-origins.inc"; attribute :>> needle="mark_array (work, context->saved, sizeof(context->saved)/sizeof(*context->saved));"; attribute :>> obligation="saved-registers"; }
part source14:SourceRow { attribute :>> key="entry-root"; attribute :>> path="vendor/gambit/lib/_mem/root-origins.inc"; attribute :>> needle="mark_array (work, &context->entry_marker, 1);"; attribute :>> obligation="context-marker-root"; }
part source15:SourceRow { attribute :>> key="rc-root"; attribute :>> path="vendor/gambit/lib/_mem/rc-roots.inc"; attribute :>> needle="context->mem.rc_head_.next"; attribute :>> obligation="context-owned-rc"; }
part source16:SourceRow { attribute :>> key="tcl-reentry"; attribute :>> path="vendor/gambit/examples/tcltk/tcltk.scm"; attribute :>> needle="___EXT(___data_rc) (___CAST(void*,client_data))"; attribute :>> obligation="raw-before-guard"; }
part source17:SourceRow { attribute :>> key="tls-status"; attribute :>> path="vendor/gambit/lib/os_thread.c"; attribute :>> needle="pthread_setspecific (___thread_mod.tls_ptr_key, ptr); /* ignore error */"; attribute :>> obligation="checked-binding-required"; }
part source18:SourceRow { attribute :>> key="thread-id"; attribute :>> path="vendor/gambit/lib/os_thread.c"; attribute :>> needle="thread->thread_id = pthread_self ();"; attribute :>> obligation="native-thread-identity"; }
part source19:SourceRow { attribute :>> key="paper-fulltext"; attribute :>> path="evidence/research/guard-thread-admission/feeley-sfp-paper.txt"; attribute :>> needle="We have not yet implemented this approa h in Gambit-C."; attribute :>> obligation="historical-proposal-not-current"; }
part def IssuerRow { attribute key:String; attribute proposedIssuer:String; attribute actualSource:String; attribute status:String; attribute responsibility:String; }
part issuer0:IssuerRow { attribute :>> key="thread"; attribute :>> proposedIssuer="NativeDomainRegistry"; attribute :>> actualSource="os_thread.c thread_init_from_self / thread_set_pstate"; attribute :>> status="required refactoring; no qualified signer"; attribute :>> responsibility="generation-bearing thread identity; TLS checked; no unknown detachment"; }
part issuer1:IssuerRow { attribute :>> key="return"; attribute :>> proposedIssuer="NativeReturnOwner"; attribute :>> actualSource="_kernel return handler / setup.c ___call"; attribute :>> status="required refactoring; no qualified signer"; attribute :>> responsibility="return lease, live catcher and segment identity; ordinary C return path is serialized by owner"; }
part issuer2:IssuerRow { attribute :>> key="guard"; attribute :>> proposedIssuer="NativeEntrySpec generated entry"; attribute :>> actualSource="foreign_conversion BEGIN_SFUN / BEGIN_TRY"; attribute :>> status="required refactoring; no qualified signer"; attribute :>> responsibility="fresh activation ticket outside captured frames; source pin and completion ownership"; }
part issuer3:IssuerRow { attribute :>> key="roots"; attribute :>> proposedIssuer="VMRootRegistry"; attribute :>> actualSource="root-origins context roots and RC scan"; attribute :>> status="required refactoring; no qualified signer"; attribute :>> responsibility="mutable GC slots published before source release; scan acknowledgement and retirement grace"; }
part issuer4:IssuerRow { attribute :>> key="retire"; attribute :>> proposedIssuer="DomainRetirementCoordinator"; attribute :>> actualSource="setup.c run / c_intf kill marker"; attribute :>> status="required refactoring; no qualified signer"; attribute :>> responsibility="no stack free from marker invalidation; native exit and root/code-reader drain all required"; }
part def NeedRow { attribute key:String; attribute kind:String; attribute path:String; attribute scope:String; ref owner:Owner; }
part need0:NeedRow { attribute :>> key="Domain-formal"; attribute :>> kind="formal"; attribute :>> path="dev/refactoring/modern-c/models/quint/native_return_domains.qnt"; attribute :>> scope="finite-domain-safety"; ref :>> owner = controlOwner; }
part need1:NeedRow { attribute :>> key="Domain-bridge"; attribute :>> kind="bridge"; attribute :>> path="dev/refactoring/modern-c/models/lean/NativeReturn.lean"; attribute :>> scope="typed-ir-lean"; ref :>> owner = controlOwner; }
part need2:NeedRow { attribute :>> key="Domain-thread"; attribute :>> kind="native"; attribute :>> path="vendor/gambit/lib/os_thread.c"; attribute :>> scope="checked-native-domain-registration"; ref :>> owner = threadOwner; }
part need3:NeedRow { attribute :>> key="Domain-return"; attribute :>> kind="native"; attribute :>> path="vendor/gambit/lib/_kernel.scm"; attribute :>> scope="stack-extent-and-return-issuer"; ref :>> owner = returnOwner; }
part need4:NeedRow { attribute :>> key="Domain-guard"; attribute :>> kind="native"; attribute :>> path="vendor/gambit/include/_gambit/foreign_conversion.h.in"; attribute :>> scope="all-entry-completion-guard"; ref :>> owner = controlOwner; }
part need5:NeedRow { attribute :>> key="Domain-roots"; attribute :>> kind="native"; attribute :>> path="vendor/gambit/lib/_mem/root-origins.inc"; attribute :>> scope="vm-guard-root-enumeration"; ref :>> owner = rootsOwner; }
part need6:NeedRow { attribute :>> key="Domain-retire"; attribute :>> kind="native"; attribute :>> path="vendor/gambit/lib/setup.c"; attribute :>> scope="stack-thread-root-code-product"; ref :>> owner = threadOwner; }
part need7:NeedRow { attribute :>> key="Domain-lowering"; attribute :>> kind="native"; attribute :>> path="vendor/gambit/gsc/_t-c-1.scm"; attribute :>> scope="native-entry-spec-lowering"; ref :>> owner = controlOwner; }
part def BindingRow { attribute actionName:String; attribute lemma:String; }
part binding0:BindingRow { attribute :>> actionName="native_return_domains.enterGuard"; attribute :>> lemma="NativeReturn.enterGuardPreserves"; }
part binding1:BindingRow { attribute :>> actionName="native_return_domains.captureScheme"; attribute :>> lemma="NativeReturn.captureSchemePreserves"; }
part binding2:BindingRow { attribute :>> actionName="native_return_domains.leaveActivation"; attribute :>> lemma="NativeReturn.leaveActivationPreserves"; }
part binding3:BindingRow { attribute :>> actionName="native_return_domains.resumeFirst"; attribute :>> lemma="NativeReturn.resumeFirstPreserves"; }
part binding4:BindingRow { attribute :>> actionName="native_return_domains.settleFirst"; attribute :>> lemma="NativeReturn.settleFirstPreserves"; }
part binding5:BindingRow { attribute :>> actionName="native_return_domains.physicalReturn"; attribute :>> lemma="NativeReturn.physicalReturnPreserves"; }
part binding6:BindingRow { attribute :>> actionName="native_return_domains.resumeSecond"; attribute :>> lemma="NativeReturn.resumeSecondPreserves"; }
part binding7:BindingRow { attribute :>> actionName="native_return_domains.rejectStaleReturn"; attribute :>> lemma="NativeReturn.rejectStaleReturnPreserves"; }
part binding8:BindingRow { attribute :>> actionName="native_return_domains.settleSecond"; attribute :>> lemma="NativeReturn.settleSecondPreserves"; }
part binding9:BindingRow { attribute :>> actionName="native_return_domains.closeCapture"; attribute :>> lemma="NativeReturn.closeCapturePreserves"; }
part binding10:BindingRow { attribute :>> actionName="native_return_domains.scanGrace"; attribute :>> lemma="NativeReturn.scanGracePreserves"; }
part binding11:BindingRow { attribute :>> actionName="native_return_domains.retireRoots"; attribute :>> lemma="NativeReturn.retireRootsPreserves"; }
part binding12:BindingRow { attribute :>> actionName="native_return_domains.detachThread"; attribute :>> lemma="NativeReturn.detachThreadPreserves"; }
part binding13:BindingRow { attribute :>> actionName="native_return_domains.unknownExit"; attribute :>> lemma="NativeReturn.unknownExitPreserves"; }
part binding14:BindingRow { attribute :>> actionName="native_return_domains.rejectWrongOwner"; attribute :>> lemma="NativeReturn.rejectWrongOwnerPreserves"; }
part binding15:BindingRow { attribute :>> actionName="native_return_domains.settleRejectedOwner"; attribute :>> lemma="NativeReturn.settleRejectedOwnerPreserves"; }
part binding16:BindingRow { attribute :>> actionName="native_return_domains.earlyPhysicalReturn"; attribute :>> lemma="NativeReturn.earlyPhysicalReturnPreserves"; }
part binding17:BindingRow { attribute :>> actionName="native_return_domains.resumeAfterReturn"; attribute :>> lemma="NativeReturn.resumeAfterReturnPreserves"; }
part binding18:BindingRow { attribute :>> actionName="native_return_domains.settleAfterReturn"; attribute :>> lemma="NativeReturn.settleAfterReturnPreserves"; }
part binding19:BindingRow { attribute :>> actionName="native_return_domains.resumeAgainLive"; attribute :>> lemma="NativeReturn.resumeAgainLivePreserves"; }
part binding20:BindingRow { attribute :>> actionName="native_return_domains.settleAgainLive"; attribute :>> lemma="NativeReturn.settleAgainLivePreserves"; }
part binding21:BindingRow { attribute :>> actionName="native_return_domains.returnAfterTwo"; attribute :>> lemma="NativeReturn.returnAfterTwoPreserves"; }
part def RouteRow { attribute component:String; attribute actionName:String; attribute lemma:String; attribute producerAnchor:String; attribute obligationId:String; }
part route0:RouteRow { attribute :>> component="control"; attribute :>> actionName="native_return_domains.enterGuard"; attribute :>> lemma="NativeReturn.enterGuardPreserves"; attribute :>> producerAnchor="continuation-closure"; attribute :>> obligationId="Domain-guard"; }
part route1:RouteRow { attribute :>> component="control"; attribute :>> actionName="native_return_domains.captureScheme"; attribute :>> lemma="NativeReturn.captureSchemePreserves"; attribute :>> producerAnchor="continuation-closure"; attribute :>> obligationId="Domain-guard"; }
part route2:RouteRow { attribute :>> component="control"; attribute :>> actionName="native_return_domains.leaveActivation"; attribute :>> lemma="NativeReturn.leaveActivationPreserves"; attribute :>> producerAnchor="continuation-closure"; attribute :>> obligationId="Domain-guard"; }
part route3:RouteRow { attribute :>> component="control"; attribute :>> actionName="native_return_domains.resumeFirst"; attribute :>> lemma="NativeReturn.resumeFirstPreserves"; attribute :>> producerAnchor="continuation-closure"; attribute :>> obligationId="Domain-guard"; }
part route4:RouteRow { attribute :>> component="control"; attribute :>> actionName="native_return_domains.settleFirst"; attribute :>> lemma="NativeReturn.settleFirstPreserves"; attribute :>> producerAnchor="continuation-closure"; attribute :>> obligationId="Domain-guard"; }
part route5:RouteRow { attribute :>> component="return"; attribute :>> actionName="native_return_domains.physicalReturn"; attribute :>> lemma="NativeReturn.physicalReturnPreserves"; attribute :>> producerAnchor="return-stale"; attribute :>> obligationId="Domain-return"; }
part route6:RouteRow { attribute :>> component="control"; attribute :>> actionName="native_return_domains.resumeSecond"; attribute :>> lemma="NativeReturn.resumeSecondPreserves"; attribute :>> producerAnchor="continuation-closure"; attribute :>> obligationId="Domain-guard"; }
part route7:RouteRow { attribute :>> component="return"; attribute :>> actionName="native_return_domains.rejectStaleReturn"; attribute :>> lemma="NativeReturn.rejectStaleReturnPreserves"; attribute :>> producerAnchor="return-stale"; attribute :>> obligationId="Domain-return"; }
part route8:RouteRow { attribute :>> component="control"; attribute :>> actionName="native_return_domains.settleSecond"; attribute :>> lemma="NativeReturn.settleSecondPreserves"; attribute :>> producerAnchor="continuation-closure"; attribute :>> obligationId="Domain-guard"; }
part route9:RouteRow { attribute :>> component="control"; attribute :>> actionName="native_return_domains.closeCapture"; attribute :>> lemma="NativeReturn.closeCapturePreserves"; attribute :>> producerAnchor="continuation-closure"; attribute :>> obligationId="Domain-guard"; }
part route10:RouteRow { attribute :>> component="roots"; attribute :>> actionName="native_return_domains.scanGrace"; attribute :>> lemma="NativeReturn.scanGracePreserves"; attribute :>> producerAnchor="entry-root"; attribute :>> obligationId="Domain-roots"; }
part route11:RouteRow { attribute :>> component="roots"; attribute :>> actionName="native_return_domains.retireRoots"; attribute :>> lemma="NativeReturn.retireRootsPreserves"; attribute :>> producerAnchor="entry-root"; attribute :>> obligationId="Domain-roots"; }
part route12:RouteRow { attribute :>> component="thread"; attribute :>> actionName="native_return_domains.detachThread"; attribute :>> lemma="NativeReturn.detachThreadPreserves"; attribute :>> producerAnchor="thread-id"; attribute :>> obligationId="Domain-retire"; }
part route13:RouteRow { attribute :>> component="control"; attribute :>> actionName="native_return_domains.unknownExit"; attribute :>> lemma="NativeReturn.unknownExitPreserves"; attribute :>> producerAnchor="continuation-closure"; attribute :>> obligationId="Domain-guard"; }
part route14:RouteRow { attribute :>> component="return"; attribute :>> actionName="native_return_domains.rejectWrongOwner"; attribute :>> lemma="NativeReturn.rejectWrongOwnerPreserves"; attribute :>> producerAnchor="return-stale"; attribute :>> obligationId="Domain-return"; }
part route15:RouteRow { attribute :>> component="control"; attribute :>> actionName="native_return_domains.settleRejectedOwner"; attribute :>> lemma="NativeReturn.settleRejectedOwnerPreserves"; attribute :>> producerAnchor="continuation-closure"; attribute :>> obligationId="Domain-guard"; }
part route16:RouteRow { attribute :>> component="return"; attribute :>> actionName="native_return_domains.earlyPhysicalReturn"; attribute :>> lemma="NativeReturn.earlyPhysicalReturnPreserves"; attribute :>> producerAnchor="return-stale"; attribute :>> obligationId="Domain-return"; }
part route17:RouteRow { attribute :>> component="return"; attribute :>> actionName="native_return_domains.resumeAfterReturn"; attribute :>> lemma="NativeReturn.resumeAfterReturnPreserves"; attribute :>> producerAnchor="return-stale"; attribute :>> obligationId="Domain-return"; }
part route18:RouteRow { attribute :>> component="return"; attribute :>> actionName="native_return_domains.settleAfterReturn"; attribute :>> lemma="NativeReturn.settleAfterReturnPreserves"; attribute :>> producerAnchor="return-stale"; attribute :>> obligationId="Domain-return"; }
part route19:RouteRow { attribute :>> component="control"; attribute :>> actionName="native_return_domains.resumeAgainLive"; attribute :>> lemma="NativeReturn.resumeAgainLivePreserves"; attribute :>> producerAnchor="continuation-closure"; attribute :>> obligationId="Domain-guard"; }
part route20:RouteRow { attribute :>> component="control"; attribute :>> actionName="native_return_domains.settleAgainLive"; attribute :>> lemma="NativeReturn.settleAgainLivePreserves"; attribute :>> producerAnchor="continuation-closure"; attribute :>> obligationId="Domain-guard"; }
part route21:RouteRow { attribute :>> component="control"; attribute :>> actionName="native_return_domains.returnAfterTwo"; attribute :>> lemma="NativeReturn.returnAfterTwoPreserves"; attribute :>> producerAnchor="continuation-closure"; attribute :>> obligationId="Domain-guard"; }
part def ProofRow { attribute key:String; attribute lemma:String; }
part proof0:ProofRow { attribute :>> key="initialSafe"; attribute :>> lemma="NativeReturn.initialSafe"; }
part proof1:ProofRow { attribute :>> key="stepPreserves"; attribute :>> lemma="NativeReturn.stepPreserves"; }
part proof2:ProofRow { attribute :>> key="reachableSafe"; attribute :>> lemma="NativeReturn.reachableSafe"; }
part proof3:ProofRow { attribute :>> key="guardRootCoverage"; attribute :>> lemma="NativeReturn.guardRootCoverage"; }
part proof4:ProofRow { attribute :>> key="returnNeedsLiveStack"; attribute :>> lemma="NativeReturn.returnNeedsLiveStack"; }
part proof5:ProofRow { attribute :>> key="freshSecondTicket"; attribute :>> lemma="NativeReturn.freshSecondTicket"; }
part proof6:ProofRow { attribute :>> key="unknownRetainsCustody"; attribute :>> lemma="NativeReturn.unknownRetainsCustody"; }
part proof7:ProofRow { attribute :>> key="retirementCut"; attribute :>> lemma="NativeReturn.retirementCut"; }
part proof8:ProofRow { attribute :>> key="staleReturnDoesNotRevive"; attribute :>> lemma="NativeReturn.staleReturnDoesNotRevive"; }
part proof9:ProofRow { attribute :>> key="threadExitCut"; attribute :>> lemma="NativeReturn.threadExitCut"; }
part def PaperRow { attribute key:String; attribute title:String; attribute url:String; attribute section:String; attribute basis:String; attribute boundary:String; }
part paper0:PaperRow { attribute :>> key="gambit-pvm"; attribute :>> title="Feeley and Miller: A parallel virtual machine for efficient Scheme compilation"; attribute :>> url="https://www.iro.umontreal.ca/~feeley/papers/FeeleyMillerLFP90.pdf"; attribute :>> section="2"; attribute :>> basis="Front/back-end contract carries machine-specific facts"; attribute :>> boundary="Historical PVM is not a current C23 ABI proof"; }
part paper1:PaperRow { attribute :>> key="gambit-c-segments"; attribute :>> title="Feeley: Portable first-class continuations with C"; attribute :>> url="https://www.schemeworkshop.org/2000/feeley.ps"; attribute :>> section="1-5"; attribute :>> basis="Unlimited Scheme extent differs from dynamic C extent; independent native segments proposed"; attribute :>> boundary="Section 5 says not implemented then; preserve arbitrary C local state; no historical timings transferred"; }
part paper2:PaperRow { attribute :>> key="ocaml-effects"; attribute :>> title="Retrofitting Effect Handlers onto OCaml"; attribute :>> url="https://anil.recoil.org/papers/2021-pldi-retroeff.pdf"; attribute :>> section="3.1 and 5.3"; attribute :>> basis="Separate system/fiber stacks and explicit callback transitions"; attribute :>> boundary="One-shot effects do not cross C frames; neither restriction is silently applied to Gambit"; }
part paper3:PaperRow { attribute :>> key="c23-draft"; attribute :>> title="WG14 N3096 C23 working draft"; attribute :>> url="https://www.open-std.org/jtc1/sc22/wg14/www/docs/n3096.pdf"; attribute :>> section="5.1.2.4; 7.13.2.1"; attribute :>> basis="Release/acquire publication; longjmp requires same thread and live setjmp invocation"; attribute :>> boundary="Working draft, not purchased final ISO text; atomics do not extend C automatic lifetime"; }
part def GroundingRow { attribute component:String; attribute producerAnchor:String; attribute paperKey:String; attribute obligationId:String; }
part grounding0:GroundingRow { attribute :>> component="return"; attribute :>> producerAnchor="return-stale"; attribute :>> paperKey="gambit-c-segments"; attribute :>> obligationId="Domain-return"; }
part grounding1:GroundingRow { attribute :>> component="control"; attribute :>> producerAnchor="continuation-closure"; attribute :>> paperKey="gambit-pvm"; attribute :>> obligationId="Domain-guard"; }
part grounding2:GroundingRow { attribute :>> component="thread"; attribute :>> producerAnchor="thread-id"; attribute :>> paperKey="ocaml-effects"; attribute :>> obligationId="Domain-thread"; }
part grounding3:GroundingRow { attribute :>> component="control"; attribute :>> producerAnchor="catcher-local"; attribute :>> paperKey="c23-draft"; attribute :>> obligationId="Domain-guard"; }
part def GainRow { attribute key:String; attribute avoided:String; attribute added:String; attribute condition:String; }
part gain0:GainRow { attribute :>> key="G1"; attribute :>> avoided="No current C-stack-copying work removed; zero-copying constraint retained"; attribute :>> added="Pinned native carrier and explicit segment registry"; attribute :>> condition="No arbitrary C-stack copying; thread-affine libraries remain on owner"; }
part gain1:GainRow { attribute :>> key="G2"; attribute :>> avoided="No current thread-count saving established; avoid an N-thread-per-resumption redesign"; attribute :>> added="N fresh resumption guards/tickets plus initial entry; active segments K, receipt history Q and pinned time"; attribute :>> condition="Sharing is by live native segment, not by continuation shot; pool reuse only after full native exit"; }
part gain2:GainRow { attribute :>> key="G3"; attribute :>> avoided="No existing conservative C-stack scanning saving established; account actual root slots"; attribute :>> added="Registered mutable root slots; per-round S visits plus descriptor pins"; attribute :>> condition="All foreign Scheme references are declared; raw aliases reject managed qualification"; }
part gain3:GainRow { attribute :>> key="G4"; attribute :>> avoided="Potential independent Scheme scheduling through isolated native ownership"; attribute :>> added="Per-domain serialization; no global registry CAS required by design"; attribute :>> condition="Pure Scheme scheduler remains free; live native return paths stay thread-bound"; }
part gain4:GainRow { attribute :>> key="G5"; attribute :>> avoided="Proposed per-ticket settlement rejects duplicate completion; no measured baseline saving"; attribute :>> added="Stable receipt storage and replay retention"; attribute :>> condition="Delivery retry uses same ticket; a genuine continuation resumption receives a new ticket"; }
part gain5:GainRow { attribute :>> key="G6"; attribute :>> avoided="Legacy marker-as-lifetime-proxy responsibility can retire"; attribute :>> added="NativeEntrySpec lowering and ModuleSpec/FrameSpec leases"; attribute :>> condition="Only after every SFUN/run/generated entry and FFI alias is covered"; }
part gain6:GainRow { attribute :>> key="G7"; attribute :>> avoided="Zig required language/runtime supports eliminated: none proven"; attribute :>> added="Zig would still need the same root, stack and return contracts"; attribute :>> condition="C23 is baseline; no incremental semantic gain from language substitution established"; }
part gain7:GainRow { attribute :>> key="G8"; attribute :>> avoided="Unknown outcomes never authorize eager free"; attribute :>> added="Retained bytes and blocked retirement may be unbounded"; attribute :>> condition="Correctness gain only; requires observable reconciliation before a liveness or memory bound claim"; }
part def MemoryRow { attribute key:String; attribute publication:String; attribute observation:String; attribute obligation:String; }
part memory0:MemoryRow { attribute :>> key="registry"; attribute :>> publication="Initialize stable domain then release-publish generation/state"; attribute :>> observation="Acquire+pin before dereferencing"; attribute :>> obligation="Lookup load alone is not lifetime protection; close admission and drain readers"; }
part memory1:MemoryRow { attribute :>> key="return-lease"; attribute :>> publication="Owner-serialized live-to-claimed transition; pin native owner"; attribute :>> observation="Acquire observes segment generation and catcher validity"; attribute :>> obligation="CAS claim alone is not physical return receipt; unknown remains owned"; }
part memory2:MemoryRow { attribute :>> key="root-transfer"; attribute :>> publication="Publish target slots release; GC acquire snapshot and updates"; attribute :>> observation="Collector round acknowledgement before source slot release"; attribute :>> obligation="Atomic pointer publication is not GC root registration; moving collector rewrites actual slot"; }
part memory3:MemoryRow { attribute :>> key="settlement"; attribute :>> publication="Ticket-scoped completion state acq_rel"; attribute :>> observation="Duplicate observation uses acquire and exact activation incarnation"; attribute :>> obligation="Captured guard cannot settle newer activation; no winding-only release"; }
part memory4:MemoryRow { attribute :>> key="retirement"; attribute :>> publication="Close gates acq_rel then drain pins/GC/code readers"; attribute :>> observation="Acquire observes last release and known native exit"; attribute :>> obligation="A zero counter alone does not imply no late entrant; atomic lock-free support not assumed"; }
part def ContractRow { attribute fromNode:String; attribute toNode:String; attribute custody:String; }
part contract0:ContractRow { attribute :>> fromNode="Scheme_GVM"; attribute :>> toNode="NativeEntrySpec"; attribute :>> custody="semantic intent and FrameSpec roots"; }
part contract1:ContractRow { attribute :>> fromNode="NativeEntrySpec"; attribute :>> toNode="StableGuard"; attribute :>> custody="fresh activation TicketId"; }
part contract2:ContractRow { attribute :>> fromNode="NativeEntrySpec"; attribute :>> toNode="NativeThreadDomain"; attribute :>> custody="checked native owner binding"; }
part contract3:ContractRow { attribute :>> fromNode="NativeThreadDomain"; attribute :>> toNode="NativeReturnDomain"; attribute :>> custody="live C segment and catcher extent"; }
part contract4:ContractRow { attribute :>> fromNode="NativeReturnDomain"; attribute :>> toNode="ReturnCheck"; attribute :>> custody="owner and generation; one physical return"; }
part contract5:ContractRow { attribute :>> fromNode="StableGuard"; attribute :>> toNode="RootBundle"; attribute :>> custody="registered mutable GC slots"; }
part contract6:ContractRow { attribute :>> fromNode="RootBundle"; attribute :>> toNode="GC_Round"; attribute :>> custody="source held until acknowledged"; }
part contract7:ContractRow { attribute :>> fromNode="Scheme_GVM"; attribute :>> toNode="CapturedContinuation"; attribute :>> custody="multi-shot Scheme frames and descriptor leases"; }
part contract8:ContractRow { attribute :>> fromNode="CapturedContinuation"; attribute :>> toNode="FreshResumption"; attribute :>> custody="new ticket; never revive dead C frame"; }
part contract9:ContractRow { attribute :>> fromNode="FreshResumption"; attribute :>> toNode="ReturnCheck"; attribute :>> custody="stale native target raises; Scheme work still possible"; }
part contract10:ContractRow { attribute :>> fromNode="ReturnCheck"; attribute :>> toNode="KnownNativeExit"; attribute :>> custody="normal return or qualified unwind"; }
part contract11:ContractRow { attribute :>> fromNode="KnownNativeExit"; attribute :>> toNode="RetirementJoin"; attribute :>> custody="native pins and readers drained"; }
part contract12:ContractRow { attribute :>> fromNode="GC_Round"; attribute :>> toNode="RetirementJoin"; attribute :>> custody="root grace and descriptor-reader drain"; }
part contract13:ContractRow { attribute :>> fromNode="StableGuard"; attribute :>> toNode="UnknownCustody"; attribute :>> custody="nonreturn or lost reply retains owner"; }
part contract14:ContractRow { attribute :>> fromNode="UnknownCustody"; attribute :>> toNode="ReconciliationRequired"; attribute :>> custody="no expiry-based stack or root free"; }
part contract15:ContractRow { attribute :>> fromNode="RetirementJoin"; attribute :>> toNode="ReusePermit"; attribute :>> custody="closed capture and no live native obligations"; }

part def RoleRow { attribute key:String; attribute identity:String; attribute retirement:String; attribute boundary:String; }
part role0:RoleRow { attribute :>> key="NativeThreadDomain"; attribute :>> identity="Native thread incarnation, checked TLS, owner dispatcher"; attribute :>> retirement="Admission closed, all attached segments/readers drained, known native exit and TLS detach"; attribute :>> boundary="Not equivalent to processor ID"; }
part role1:RoleRow { attribute :>> key="NativeReturnDomain"; attribute :>> identity="Segment generation, native return target, live local catcher extent"; attribute :>> retirement="Known return/unwind consumes return permission and invalidates affected extents"; attribute :>> boundary="OS thread alive does not mean returned invocation alive"; }
part role2:RoleRow { attribute :>> key="StableGuard"; attribute :>> identity="Activation TicketId, rooted arguments and completion custody"; attribute :>> retirement="Exact activation settled, entry closed, scanner and code readers drained"; attribute :>> boundary="Guard persistence does not extend local jmp_buf lifetime"; }
part role3:RoleRow { attribute :>> key="CapturedContinuation"; attribute :>> identity="Scheme frames, denv and descriptor leases"; attribute :>> retirement="All reachable holders and in-flight restorations relinquished"; attribute :>> boundary="A restoration does not recreate expired native return authority"; }
part role4:RoleRow { attribute :>> key="RootBundle"; attribute :>> identity="Actual GC-updatable slots and owner generation"; attribute :>> retirement="Transfer acknowledged, borrowers drained and collector grace"; attribute :>> boundary="Native pointer pin alone is not a registered Scheme root"; }

part proof10:ProofRow { attribute :>> key="consumedReturnNeverRevives"; attribute :>> lemma="NativeReturn.consumedReturnNeverRevives"; }

part proof11:ProofRow { attribute :>> key="newShotGetsFreshTicket"; attribute :>> lemma="NativeReturn.newShotGetsFreshTicket"; }
}
