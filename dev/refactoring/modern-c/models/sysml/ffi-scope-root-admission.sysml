package GambitFfiScopeRootAdmission { private import ScalarValues::*;
part def Route { attribute key:String; attribute sourcePath:String; attribute needle:String; attribute obligation:String; }
part route0:Route { attribute :>> key="marker-before-arguments"; attribute :>> sourcePath="vendor/gambit/include/gambit.h.in"; attribute :>> needle="#define ___BEGIN_SFUN(proc,decl)"; attribute :>> obligation="Root bundle must precede marker allocation and parameter conversion"; }
part route1:Route { attribute :>> key="compiler-sfun-emitter"; attribute :>> sourcePath="vendor/gambit/gsc/_ptree2.scm"; attribute :>> needle="(define (c-function param-typs result-typ proc-name c-defined? scope)"; attribute :>> obligation="Generator owns entry RootSpec and conversion cleanup manifest"; }
part route2:Route { attribute :>> key="marker-protection-gap"; attribute :>> sourcePath="vendor/gambit/lib/c_intf.c"; attribute :>> needle="proc_or_false may have been GC'd"; attribute :>> obligation="Protect moving procedure and direct Scheme arguments before fallible marker allocation"; }
part route3:Route { attribute :>> key="rc-scan-owner"; attribute :>> sourcePath="vendor/gambit/lib/mem.c"; attribute :>> needle="mark_rc (___PSPNC);"; attribute :>> obligation="Current processor-zero RC scanning is insufficient as all-processor entry root directory proof"; }
part route4:Route { attribute :>> key="sfun-error-reentry"; attribute :>> sourcePath="vendor/gambit/include/gambit.h.in"; attribute :>> needle="#define ___SFUN_ERROR while"; attribute :>> obligation="Conversion handler can reenter call; root guard remains until result and cleanup are settled"; }
part route5:Route { attribute :>> key="call-frame-marker"; attribute :>> sourcePath="vendor/gambit/lib/setup.c"; attribute :>> needle="___fp[-2] = stack_marker;"; attribute :>> obligation="Marker becomes continuation frame data; native guard cannot replace frame/root contract"; }
part route6:Route { attribute :>> key="return-multiple"; attribute :>> sourcePath="vendor/gambit/lib/_kernel.scm"; attribute :>> needle="___COVER_RETURN_TO_C_HANDLER_MULTIPLE_RETURN;"; attribute :>> obligation="Multiple C return is diagnosed; old completion cannot release a new generation"; }
part route7:Route { attribute :>> key="tcl-scheme-entry"; attribute :>> sourcePath="vendor/gambit/examples/tcltk/tcltk.scm"; attribute :>> needle="(c-define (##tcltk-call vect args)"; attribute :>> obligation="Actual generated native callback has a Scheme-object argument and string-list conversion"; }
part route8:Route { attribute :>> key="tcl-delete-owner"; attribute :>> sourcePath="vendor/gambit/examples/tcltk/tcltk.scm"; attribute :>> needle="___EXT(___release_scmobj) (___EXT(___data_rc)"; attribute :>> obligation="Delete release and nested callback drain must meet foreign endorsement"; }
part route9:Route { attribute :>> key="tcl-result-destructor"; attribute :>> sourcePath="vendor/gambit/examples/tcltk/tcltk.scm"; attribute :>> needle="___CAST(Tcl_FreeProc*,___EXT(___release_string))"; attribute :>> obligation="Result bytes are not enough if destructor entry still depends on retiring code"; }
part route10:Route { attribute :>> key="scope-last-use"; attribute :>> sourcePath="vendor/gambit/lib/write_authority.c"; attribute :>> needle="Only the producer, AFTER its last actual write/borrow"; attribute :>> obligation="Scope release must follow marker invalidation and old PSTATE last use"; }
part route11:Route { attribute :>> key="json-environment"; attribute :>> sourcePath="dev/refactoring/modern-c/models/lean/PinRosterDetachment.lean"; attribute :>> needle="theorem environmentExactDomain"; attribute :>> obligation="Compose existing exact-domain theorem without claiming parser verification"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule6; ref part :>> counterpart=GambitRuntimeComposition::blueprintModule3; attribute :>> key="entry-root-bundle"; attribute :>> owner="foreign/roots"; attribute :>> actionName="registerGuard acquireScope publishRoots"; attribute :>> invariant="Protected caller carrier before guard admission; transfer entry roots before marker allocation"; attribute :>> gap="Raw stale SCMOBJ cannot be repaired at entry; all-processor carrier and converter closure required"; }
part contract1:Contract { ref part :>> accountable=GambitRuntimeComposition::blueprintModule3; ref part :>> counterpart=GambitRuntimeComposition::blueprintModule0; attribute :>> key="marker-and-reload"; attribute :>> owner="roots/semantic"; attribute :>> actionName="allocateMarker collect reloadRoot initializeMarker"; attribute :>> invariant="GC may update the root slot; initialize marker from reloaded value"; attribute :>> gap="No reuse of pre-allocation C local; all supported conversion paths remain to refine"; }
part contract2:Contract { ref part :>> accountable=GambitRuntimeComposition::blueprintModule7; ref part :>> counterpart=GambitRuntimeComposition::blueprintModule5; attribute :>> key="stable-completion"; attribute :>> owner="release/control"; attribute :>> actionName="throwExit settleException invalidateMarker releaseScope"; attribute :>> invariant="Unknown exit retains guard root permit and VM borrow; marker invalid before permit release"; attribute :>> gap="No longjmp-dependent automatic cleanup state; task receipt must be stable"; }
part contract3:Contract { ref part :>> accountable=GambitRuntimeComposition::blueprintModule1; ref part :>> counterpart=GambitRuntimeComposition::blueprintModule4; attribute :>> key="publication-cut"; attribute :>> owner="native/collector"; attribute :>> actionName="prepare publish admit observe withdraw"; attribute :>> invariant="One roster admission cut excludes withdrawal; matched release/acquire publishes immutable metadata"; attribute :>> gap="C11 HB embedding and existing compiler-specific atomic backends remain distinct"; }
part contract4:Contract { ref part :>> accountable=GambitRuntimeComposition::blueprintModule7; ref part :>> counterpart=GambitRuntimeComposition::blueprintModule6; attribute :>> key="real-endorsement"; attribute :>> owner="release/foreign"; attribute :>> actionName="endorseSemantic endorseForeign endorseResident issue"; attribute :>> invariant="Root/frame owner callback owner and resident result owner independently attest exact task and source"; attribute :>> gap="Tcl record still carries Scheme procedure callback and release capability; current certificate blocked"; }
part contract5:Contract { ref part :>> accountable=GambitRuntimeComposition::blueprintModule8; ref part :>> counterpart=GambitRuntimeComposition::blueprintModule0; attribute :>> key="json-admission"; attribute :>> owner="build/semantic"; attribute :>> actionName="registerGuard publishRoots releaseScope"; attribute :>> invariant="Actual typed-IR guard/update certificates plus finite JSON environment"; attribute :>> gap="Parser emitter field identity and full source simulation remain open"; }
part def Obligation { attribute key:String; attribute status:String; attribute scope:String; attribute counterexample:String; }
part obligation0:Obligation { attribute :>> key="preallocation-roots"; attribute :>> status="bounded-checked"; attribute :>> scope="One root bundle and one bounded moving collection before entry"; attribute :>> counterexample="Protecting only marker or proc misses direct Scheme parameters"; }
part obligation1:Obligation { attribute :>> key="publication-lifetime"; attribute :>> status="bounded-checked"; attribute :>> scope="One roster lease scanner and immutable publication"; attribute :>> counterexample="Acquire does not create a slot storage lease"; }
part obligation2:Obligation { attribute :>> key="release-guards"; attribute :>> status="conditional-proved"; attribute :>> scope="Marker active and unknown states reject permit release"; attribute :>> counterexample="Normal-return epilogue is not nonlocal completion proof"; }
part obligation3:Obligation { attribute :>> key="hb-embedding"; attribute :>> status="conditional-proved"; attribute :>> scope="Event-order arithmetic given actual synchronizes-with and stable cut premises"; attribute :>> counterexample="Atomic flag alone cannot publish earlier non-atomic data without matching acquire"; }
part obligation4:Obligation { attribute :>> key="actual-expressions"; attribute :>> status="conditional-proved"; attribute :>> scope="Three actual FFI admission action guard/update expressions"; attribute :>> counterexample="AST certificate is local meaning not whole C11 or collector proof"; }
part obligation5:Obligation { attribute :>> key="actual-source-c11"; attribute :>> status="open"; attribute :>> scope="All argument converters nonzero processor roots stable exception custody actual backend proof"; attribute :>> counterexample="Current write_authority integration and three endorsements not implemented"; }
part obligation6:Obligation { attribute :>> key="json-environment"; attribute :>> status="partially-proved"; attribute :>> scope="91-row exact-domain proof and strict projection controls"; attribute :>> counterexample="JSON parser and independent source-to-IR extraction remain trusted"; }
part def Gain { attribute key:String; attribute avoided:String; attribute added:String; attribute condition:String; }
part gain0:Gain { attribute :>> key="entry-root-bundle"; attribute :>> avoided="Scattered ad hoc protection per generated FFI argument"; attribute :>> added="O(A) root locations and post-allocation reloads for A live Scheme inputs"; attribute :>> condition="One generated RootSpec replaces duplicated cases only after every converter adopts it"; }
part gain1:Gain { attribute :>> key="stable-guard"; attribute :>> avoided="Repeated ambiguous cleanup and unsafe scope release on exception"; attribute :>> added="One stable per-activation record plus root and VM borrow; nested callbacks need distinct records"; attribute :>> condition="Unknown results retain memory; no bounded-retention claim"; }
part gain2:Gain { attribute :>> key="shared-roster"; attribute :>> avoided="Per-entry global serialization when qualified admission protocol is used"; attribute :>> added="O(P) registered root scans and admission synchronization"; attribute :>> condition="Benefit requires reduced serialization exceeding publication and scan work"; }
part gain3:Gain { attribute :>> key="terminal-detachment"; attribute :>> avoided="C bytes of old code retained solely for late terminal result queries"; attribute :>> added="B copied bytes plus E directory endorsements resident codec and destructor storage"; attribute :>> condition="C > B + E; no outstanding Scheme callback continuation or old destructor capability"; }
part gain4:Gain { attribute :>> key="modern-c-baseline"; attribute :>> avoided="A second runtime language is unnecessary for these mechanisms"; attribute :>> added="Generated C entry ABI atomics root metadata and exception custody proofs"; attribute :>> condition="Zig must independently demonstrate benefit beyond the same required contracts"; }
part def Binding { attribute key:String; attribute qntAction:String; attribute leanLemma:String; attribute refinement:String; attribute guardLemma:String; attribute updateLemma:String; }
part binding0:Binding { attribute :>> key="guard"; attribute :>> qntAction="registerGuard"; attribute :>> leanLemma="noBorrowRejectsGuard"; attribute :>> refinement="Actual selected guard and update meanings checked; source and C11 relation open"; attribute :>> guardLemma="registerGuardGuardMeaning"; attribute :>> updateLemma="registerGuardNextMeaning"; }
part binding1:Binding { attribute :>> key="roots"; attribute :>> qntAction="publishRoots"; attribute :>> leanLemma="noGuardRejectsRoots"; attribute :>> refinement="Actual selected guard and update meanings checked; source and C11 relation open"; attribute :>> guardLemma="publishRootsGuardMeaning"; attribute :>> updateLemma="publishRootsNextMeaning"; }
part binding2:Binding { attribute :>> key="release"; attribute :>> qntAction="releaseScope"; attribute :>> leanLemma="markerBlocksRelease"; attribute :>> refinement="Actual selected guard and update meanings checked; source and C11 relation open"; attribute :>> guardLemma="releaseScopeGuardMeaning"; attribute :>> updateLemma="releaseScopeNextMeaning"; }
part def Flow { attribute fromNode:String; attribute toNode:String; attribute reason:String; }
part flow0:Flow { attribute :>> fromNode="c0"; attribute :>> toNode="c1"; attribute :>> reason="Protected source carrier transfers to entry roots"; }
part flow1:Flow { attribute :>> fromNode="c1"; attribute :>> toNode="c2"; attribute :>> reason="Marker roots survive through result and error conversion"; }
part flow2:Flow { attribute :>> fromNode="c2"; attribute :>> toNode="c4"; attribute :>> reason="Settled custody is required before endorsements"; }
part flow3:Flow { attribute :>> fromNode="c0"; attribute :>> toNode="c3"; attribute :>> reason="Root admission needs a stable roster cut"; }
part flow4:Flow { attribute :>> fromNode="c3"; attribute :>> toNode="c2"; attribute :>> reason="Maintenance scan lease survives external close"; }
part flow5:Flow { attribute :>> fromNode="c4"; attribute :>> toNode="o5"; attribute :>> reason="Actual endorsers still need caller closure"; }
part flow6:Flow { attribute :>> fromNode="c0"; attribute :>> toNode="o0"; attribute :>> reason="Incoming values are protected before registration"; }
part flow7:Flow { attribute :>> fromNode="c1"; attribute :>> toNode="o0"; attribute :>> reason="GC movement requires slot reload"; }
part flow8:Flow { attribute :>> fromNode="c2"; attribute :>> toNode="o2"; attribute :>> reason="Marker and unknown states block release"; }
part flow9:Flow { attribute :>> fromNode="c3"; attribute :>> toNode="o1"; attribute :>> reason="Immutable metadata and storage leases"; }
part flow10:Flow { attribute :>> fromNode="c3"; attribute :>> toNode="o3"; attribute :>> reason="Actual release-acquire HB embedding required"; }
part flow11:Flow { attribute :>> fromNode="c5"; attribute :>> toNode="o4"; attribute :>> reason="Selected typed-IR guard and update meanings"; }
part history:GambitAssuranceRouting::ModelNeed { ref part :>> owner=GambitBuildAssurance::planner.component; attribute :>> obligationId="FA-H"; attribute :>> kind="interleaving"; attribute :>> subjectPath="dev/refactoring/modern-c/models/quint/ffi_root_admission.qnt"; attribute :>> subjectScope="Protected incoming carrier transfer entry root bundle moving marker allocation stable guard and exceptional custody"; attribute :>> premise="Bounded models and restricted algebra only; no runtime implementation or native acceptance"; }
part shards:GambitAssuranceRouting::ModelNeed { ref part :>> owner=GambitBuildAssurance::planner.component; attribute :>> obligationId="FA-B"; attribute :>> kind="interleaving"; attribute :>> subjectPath="dev/refactoring/modern-c/models/quint/ffi_publication_cut.qnt"; attribute :>> subjectScope="Reference release-acquire publication with serialized roster lease and maintenance scan cut"; attribute :>> premise="Bounded models and restricted algebra only; no runtime implementation or native acceptance"; }
part induction:GambitAssuranceRouting::ModelNeed { ref part :>> owner=GambitBuildAssurance::planner.component; attribute :>> obligationId="FA-I"; attribute :>> kind="induction"; attribute :>> subjectPath="dev/refactoring/modern-c/models/lean/FfiScopeRootAdmission.lean"; attribute :>> subjectScope="Root and release guard exclusions plus conditional HB event-order lemmas"; attribute :>> premise="Bounded models and restricted algebra only; no runtime implementation or native acceptance"; }
part expression:GambitAssuranceRouting::ModelNeed { ref part :>> owner=GambitBuildAssurance::planner.component; attribute :>> obligationId="FA-X"; attribute :>> kind="induction"; attribute :>> subjectPath="dev/refactoring/modern-c/models/lean/FfiScopeRootAst.lean"; attribute :>> subjectScope="Actual registerGuard publishRoots releaseScope meanings and finite JSON reference domain"; attribute :>> premise="Bounded models and restricted algebra only; no runtime implementation or native acceptance"; }
part source:GambitAssuranceRouting::ModelNeed { ref part :>> owner=GambitBuildAssurance::planner.component; attribute :>> obligationId="FA-S"; attribute :>> kind="source-refinement"; attribute :>> subjectPath="dev/refactoring/modern-c/ffi-scope-root-admission-design.org"; attribute :>> subjectScope="Actual FFI converters callback deletion continuation and all processor roots OPEN"; attribute :>> premise="Bounded models and restricted algebra only; no runtime implementation or native acceptance"; }
part platform:GambitAssuranceRouting::ModelNeed { ref part :>> owner=GambitBuildAssurance::planner.component; attribute :>> obligationId="FA-E"; attribute :>> kind="environment-refinement"; attribute :>> subjectPath="dev/refactoring/modern-c/ffi-scope-root-admission-design.org"; attribute :>> subjectScope="C11 stable registration matched publication nonlocal jumps and backend refinement OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitPinRosterDetachment::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; attribute sourcePath:String; attribute needle:String; }
part endorsement0:Endorsement { attribute :>> roleName="semantic"; attribute :>> scope="Root bundle frame return and multi-shot closure for exact activation"; attribute :>> issuer="Generated SFUN and return-to-C root/frame owner"; attribute :>> sourcePath="vendor/gambit/lib/_kernel.scm"; attribute :>> needle="___COVER_RETURN_TO_C_HANDLER_MULTIPLE_RETURN;"; }
part endorsement1:Endorsement { attribute :>> roleName="foreign"; attribute :>> scope="Command ingress closed all callbacks and deletion effects drained"; attribute :>> issuer="Tcl command adapter owner"; attribute :>> sourcePath="vendor/gambit/examples/tcltk/tcltk.scm"; attribute :>> needle="___HIDDEN void scheme_delete_cmd"; }
part endorsement2:Endorsement { attribute :>> roleName="resident"; attribute :>> scope="Immutable result and resident decoder error and destructor closure"; attribute :>> issuer="Tcl result adapter and resident codec owner"; attribute :>> sourcePath="vendor/gambit/examples/tcltk/tcltk.scm"; attribute :>> needle="___CAST(Tcl_FreeProc*,___EXT(___release_string))"; }
part flow12:Flow { attribute :>> fromNode="c5"; attribute :>> toNode="o6"; attribute :>> reason="Exact finite reference domain"; }
part flow13:Flow { attribute :>> fromNode="o4"; attribute :>> toNode="o5"; attribute :>> reason="Local syntax certificate does not prove source simulation"; }
part flow14:Flow { attribute :>> fromNode="c4"; attribute :>> toNode="c5"; attribute :>> reason="Source identity binds endorsement admission"; }
part flow15:Flow { attribute :>> fromNode="c2"; attribute :>> toNode="o5"; attribute :>> reason="All catcher and restoration paths remain to refine"; }
}
