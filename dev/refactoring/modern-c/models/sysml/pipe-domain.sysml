package GambitPipeDomain {
 private import ScalarValues::*;
 attribute stage:String="pipe-domain-owner";
 attribute baseline:String="b299e26768bcdf22a6be5fbf7e05868ef0108eed";
 attribute scope:String="One peer-shared ownership domain for vector/string/u8 pipe construction, FIFO/buffer cursors, close publication, condition waits/reacquisition and exception exit. Existing Scheme names and ordinary standalone port ownership remain; word-atomic fallback and scheduler redesign are separate owners.";
 attribute formalDuty:String="pipe_domain.qnt owns only shared-domain mutual exclusion, FIFO conservation, release-before-wait, close wake and hook-exit interleavings. Existing root/GC models retain collector duties. No new Lean arithmetic/stack/address law is introduced; do not repeat a lifecycle proof or claim exhaustive native weak-memory verification.";
 attribute sourceCases:String="domain-construction;writer-coverage;wait-reentry;construction-exit;gc-roots;generation-closure";
 attribute requiredCases:String="production-pbt;nonzero;exception;official-io;existing-consumers;model;cost;source-custody";
 part def Component { attribute source:String; attribute owns:String; attribute contract:String; }
 part factory:Component {
  attribute :>> source="vendor/gambit/lib/_io.scm: ##make-vect-pipe-port, ##make-vector-port, ##make-string-port, ##make-u8vector-port; vendor/gambit/lib/_io#.scm: define-type port";
  attribute :>> owns="Allocate one Scheme mutex before either endpoint, pass it into both actual constructors, then wire peer buffers and return the pair. Existing four-argument standalone constructors retain a nonallocating optional sentinel and allocate their own mutex at the original body position after FIFO formation.";
  attribute :>> contract="The two endpoints and all aliased FIFO/cursor/close fields share one mutex. No endpoint is returned before both peer links are installed. Optional-argument binding itself does not allocate or move original standalone allocation before the completed body root view. Partial construction is Scheme-owned/unpublished and collectible, not native resource escrow. Arbitrary private fifth-argument misuse is outside the admitted producer.";
 }
 part service:Component {
  attribute :>> source="vendor/gambit/lib/_io.scm: define-vect-port-methods, vect-rbuf-fill, vect-wbuf-drain, force-output, close, set-rtimeout, set-wtimeout";
  attribute :>> owns="Existing port methods now guard actual peer-shared state with the same mutex rather than per-endpoint guards. Keep independent read/write condition variables, buffering and scheduling policy.";
  attribute :>> contract="Single-processor exclusive fast paths or acquired shared domain authorize mutations. Wait atomically releases the domain before parking; normal retry reacquires it before rereading predicates. Timeout hook exception exits while released. Close signals peer waiters under the shared domain; no second peer lock or nested recursive lock is introduced.";
 }
 part generation:Component {
  attribute :>> source="vendor/gambit/lib/_io.scm; vendor/gambit/lib/_io.c; existing lib/gsi/gsc Make generation/link recipes";
  attribute :>> owns="Explicit IO Scheme demand plus full five-linker-unit dependency closure, then generation-disabled native phase3/phase4 in the same cache and C23 profile.";
  attribute :>> contract="Completed IO output/object is reused after a failed downstream attempt. Unchanged link bytes still need completed dependency timestamps before Make can consider them current. Preserve failed attempts and immutable seed; no source clone, profile change, larger budget or hand-edited generated C.";
 }
 part broaderValidation:Component {
  attribute status:String="UNRESOLVED_NO_WHOLE_SMP_ADMISSION";
  attribute :>> source="evidence/research/retained/modern-c/pipe-domain/qualification.json";
  attribute :>> owns="Separate default compiler/whole-population GC and wall-regression attribution.";
  attribute :>> contract="Default GSC11/34 versus baseline compiler14/34 with different failure sets; candidate whole408 attempts timeout120s versus exact baseline392/40896.841s. Preserve all negatives. Production p1 compiler34/34 plus GSI34/34 qualify only the declared IO owner, not these broader modes or release.";
 }
 attribute refinements:String="constructionMap;serviceMap;waitMap";
 part def Refinement { attribute actions:String; attribute source:String; attribute guard:String; attribute obligation:String; attribute quint:String; attribute leanDuty:String default="No new numeric/address law. Lean has no duplicate pipe state-machine duty."; }
 part constructionMap:Refinement { attribute :>> actions="init;lock"; attribute :>> source="##make-vect-pipe-port allocates mutex once, all three constructor families receive it before peer publication"; attribute :>> guard="QNT endpoints map to actual ports and the same mutex identity. Baseline split identity is a real native witness, not a hypothetical model state."; attribute :>> obligation="PIPE-OWNER"; attribute :>> quint="dev/refactoring/modern-c/models/quint/pipe_domain.qnt"; }
 part serviceMap:Refinement { attribute :>> actions="lock;write;read;unlock;close"; attribute :>> source="vect-rbuf-fill / vect-wbuf-drain / force-output / close"; attribute :>> guard="Actual FIFO and peer cursors have a single source domain. C/Scheme mutex publication is an existing premise; this change does not modify the atomic fallback or prove the whole scheduler."; attribute :>> obligation="PIPE-WRITERS"; attribute :>> quint="dev/refactoring/modern-c/models/quint/pipe_domain.qnt"; }
 part waitMap:Refinement { attribute :>> actions="wait;reacquire;exceptionInWaitHook;exceptionalReturn;finish"; attribute :>> source="##mutex-signal-and-condvar-wait!, timeout hooks and macro-port-mutex-lock! retry"; attribute :>> guard="Waiting relinquishes domain ownership; signal is a hint to recheck actual state, not transfer of a stale cursor. Timeout hook exceptions are tested through public API; asynchronous thread death and all fairness claims remain outside."; attribute :>> obligation="PIPE-WAIT"; attribute :>> quint="dev/refactoring/modern-c/models/quint/pipe_domain.qnt"; }
 part def Obligation { attribute id:String; attribute status:String; attribute premise:String; }
 attribute obligations:String="owner;writers;waitProof;exitProof;roots;generationProof;costProof";
 part owner:Obligation { attribute :>> id="PIPE-OWNER"; attribute :>> status="CLOSED"; attribute :>> premise="Actual two endpoint mutex identities coincide for all three families; ordinary independent ports retain independent ownership."; }
 part writers:Obligation { attribute :>> id="PIPE-WRITERS"; attribute :>> status="CLOSED"; attribute :>> premise="All peer FIFO/cursor/close/wait predicate access follows shared-domain construction; actual source consumers audited, no second peer lock."; }
 part waitProof:Obligation { attribute :>> id="PIPE-WAIT"; attribute :>> status="CLOSED"; attribute :>> premise="Release/wait/reacquire and close/wake preserve domain ownership. Bounded QNT checks and pinned native producer are observations, not fairness proof."; }
 part exitProof:Obligation { attribute :>> id="PIPE-EXIT"; attribute :>> status="CLOSED"; attribute :>> premise="Unpublished Scheme construction and timeout-hook nonlocal exits retain managed roots; six actual reader/writer hook failures permit subsequent I/O. Native OOM/owner-death recovery not claimed."; }
 part roots:Obligation { attribute :>> id="PIPE-ROOTS"; attribute :>> status="CLOSED"; attribute :>> premise="Existing Scheme frame/port tracing owns the common mutex and pending values through actual GC; multiple continuation restoration consumers remain unchanged. No new native roots or untraced pointer cache."; }
 part generationProof:Obligation { attribute :>> id="PIPE-GENERATION"; attribute :>> status="CLOSED"; attribute :>> premise="Exact module/recipe/seed/profile identities and full downstream linker closure; one changed C artifact and50 unchanged generated artifacts. Original consumers and negative failures retained."; }
 part costProof:Obligation { attribute :>> id="PIPE-COST"; attribute :>> status="CLOSED"; attribute :>> premise="One fewer Scheme mutex per pair is a source count, not peak-memory proof. Matched native measurements and predecessor regression attribution remain explicit; no speedup inferred from fewer locks or finite samples."; }
 part submission:GambitCommitGates::SubmissionUnit { attribute :>> kind="integration"; attribute :>> result="pipe-domain-owner"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="PIPE-TESTS"; attribute :>> method="native"; attribute :>> artifact="evidence/research/retained/modern-c/pipe-domain/qualification.json"; attribute :>> scope="Actual public I/O, pinned processor1, GC, replay/shrink, existing port/root/frame consumers and full original population with explicit baseline boundary."; }
 part learning:Need { ref part :>> gate=GambitCommitGates::learning; attribute :>> id="PIPE-LEARNING"; attribute :>> method="source-analysis"; attribute :>> artifact="dev/refactoring/modern-c/pipe-domain.org"; attribute :>> scope="Mutex belongs to shared state domain, not presentation endpoint; source preservation and explicit generation completion are separate responsibilities."; }
 part process:Need { ref part :>> gate=GambitCommitGates::process; attribute :>> id="PIPE-PROCESS"; attribute :>> method="source-analysis"; attribute :>> artifact="dev/refactoring/modern-c/pipe-domain.org"; attribute :>> scope="One complete pipe domain owner; remaining word-arithmetic/thread/build/layout proposals stay separately owned. Independent SMP progress unchanged."; }
 part models:Need { ref part :>> gate=GambitCommitGates::models; attribute :>> id="PIPE-MODELS"; attribute :>> method="native"; attribute :>> artifact="evidence/research/retained/modern-c/pipe-domain/qualification.json"; attribute :>> scope="Native SysML SDK drives ASCENT obligations and source adapters; QNT covers pipe interleavings only, no duplicate Lean protocol."; }
 part questions:Need { ref part :>> gate=GambitCommitGates::questions; attribute :>> id="PIPE-QUESTIONS"; attribute :>> method="source-analysis"; attribute :>> artifact="dev/refactoring/modern-c/pipe-domain.org"; attribute :>> scope="All three families, aliases, exception cleanup, old public API and exact generation/cost limits; no inferred whole-VM or whole-SMP performance gain."; }
}
