package GambitCIForensics {
 private import ScalarValues::*;
 attribute scope:String="Support correction only: immutable historical source references and exact conservative finalization failure evidence. Existing CI tests, time and heap limits remain. No runtime or architecture-progress admission.";
 attribute stage:String="Architecture remains locally3/4; SMP remains1/12. Source-core STALE and hosted macOS attribution remain open until new observations. This diagnostic support is prerequisite evidence, not fourth integration.";
 attribute formalDuty:String="SysML selects five support gates; ASCENT rejects missing evidence. No runtime state transition changed; existing QNT and Lean obligations are not duplicated.";
 part def Need { attribute id:String; ref part gate:GambitCommitGates::Gate; attribute method:String; attribute artifact:String; attribute scope:String; }
 part tests:Need { attribute :>> id="CI-TESTS"; ref part :>> gate=GambitCommitGates::tests; attribute :>> method="native"; attribute :>> artifact="evidence/research/retained/modern-c/ci-forensics/receipt.json"; attribute :>> scope="Complete declared source cut; no whole-CI or runtime admission"; }
 part learning:Need { attribute :>> id="CI-LEARNING"; ref part :>> gate=GambitCommitGates::learning; attribute :>> method="source-analysis"; attribute :>> artifact="evidence/research/retained/modern-c/ci-forensics/receipt.json"; attribute :>> scope="Complete declared source cut; no whole-CI or runtime admission"; }
 part process:Need { attribute :>> id="CI-PROCESS"; ref part :>> gate=GambitCommitGates::process; attribute :>> method="source-analysis"; attribute :>> artifact="evidence/research/retained/modern-c/ci-forensics/receipt.json"; attribute :>> scope="Complete declared source cut; no whole-CI or runtime admission"; }
 part models:Need { attribute :>> id="CI-MODELS"; ref part :>> gate=GambitCommitGates::models; attribute :>> method="source-analysis"; attribute :>> artifact="evidence/research/retained/modern-c/ci-forensics/receipt.json"; attribute :>> scope="Complete declared source cut; no whole-CI or runtime admission"; }
 part questions:Need { attribute :>> id="CI-QUESTIONS"; ref part :>> gate=GambitCommitGates::questions; attribute :>> method="source-analysis"; attribute :>> artifact="evidence/research/retained/modern-c/ci-forensics/receipt.json"; attribute :>> scope="Complete declared source cut; no whole-CI or runtime admission"; }
 part submission:GambitCommitGates::SubmissionUnit { attribute :>> kind="support"; attribute :>> result=""; attribute :>> progressDelta=0; attribute :>> supportPaths="src/gambit_smp/recipes.py;src/gambit_smp/research_audit.py;tests/test_recipes.py;evidence/research-audit.json;evidence/research/retained/modern-c/owned-lifetime/historical-header.json;dev/refactoring/modern-c/models/sysml/ci-forensics.sysml;dev/refactoring/modern-c/ci-forensics.org;evidence/research/retained/modern-c/ci-forensics/receipt.json"; attribute :>> testModules="tests/test_recipes.py"; }
}
