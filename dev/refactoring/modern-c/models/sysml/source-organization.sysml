package GambitSourceOrganization {
  private import ScalarValues::*;
  ref part delivery = GambitRuntimeRoleRealization::organization;
  ref part headerPartition = GambitHeaderOrganization::h_platform;
  ref part memoryPartition = GambitMemoryOrganization::m0;
  attribute baseRevision:String="8d2b40341a80083ba90e3f8e77d256d49b3e257a";
  attribute candidateTree:String="df434be1261f13ba139ce965caca57055abd39de";
  attribute evidence:String="evidence/research/source-organization/results.json";
  attribute scope:String="Lossless organization of the existing HEAD:41 private header templates and25 private memory fragments; five existing source/build files updated plus the shipped configure mapping, native frame consumer,78 native OS helper accesses and nine matching default generated accesses. The complete temporary-root family must finish HEAD's existing move to context->saved; otherwise generated kernel C accesses a removed PSTATE field. No new collector, FFI service, scheduler or namespace is introduced.";
  attribute excluded:String="The149-path mixed research candidate remains uncommitted working source. Later role/round/lifecycle/foreign/generational changes are not part of this75-path submission. Existing native_scope identifiers in HEAD are neither renamed nor given parallel aliases in this mechanical cut.";
  attribute formalDuty:String="Native SysML owns partition/consumer scope; ASCENT joins actual source-bound observations to five gates. Exact memory reconstruction and header reconstruction against the declared12-access root migration check deterministic refinement. All six save/restore macros address the same context bank scanned by mark_execution_roots. No new concurrency transition or algebraic law is introduced; QNT and Lean are not duplicated or required to repeat byte comparisons.";
  attribute benefit:String="Replace two monolithic maintenance locations with responsibility modules, one flat public header and one memory translation unit; preserve declared include/macro/function order and original memory diagnostic coordinates. No throughput, RSS or full-SMP benefit is claimed.";
  attribute cost:String="66 private source files, ordered inventories, distribution paths and rebuild edges. Configured consumers still read one public header; runtime object count and memory layout are unchanged. More source files alone are not a runtime performance gain.";
  attribute status:String="RETAINED-ROLE-PROTOTYPE; NOT-FIRST-DELIVERY; BOOTSTRAP-FAILED; NOT-ADMITTED";
  part def Need { ref part gate:GambitCommitGates::Gate; attribute id:String; attribute method:String; attribute artifact:String; attribute scope:String; }
  part bytes:Need { ref part :>> gate=GambitCommitGates::tests; attribute :>> id="S-BYTES"; attribute :>> method="source-refinement"; attribute :>> artifact="evidence/research/source-organization/candidate-tree.json"; attribute :>> scope="exact-HEAD-memory-and-declared12-access-root-migrated-header-reconstruction-with-complete-build-publication"; }
  part configuration:Need { ref part :>> gate=GambitCommitGates::tests; attribute :>> id="S-CONFIG"; attribute :>> method="native"; attribute :>> artifact="vendor/gambit/configure.ac"; attribute :>> scope="existing-Bazel-profile-and-byte-equal-flat-header-from-monolith-and-fragments"; }
  part consumers:Need { ref part :>> gate=GambitCommitGates::tests; attribute :>> id="S-CONSUMERS"; attribute :>> method="native"; attribute :>> artifact="vendor/gambit/lib/mem.c"; attribute :>> scope="GCC-Clang-release-debug-preprocessing-release-MachO-object-and-C23-frame-consumers"; }
  part dependencies:Need { ref part :>> gate=GambitCommitGates::tests; attribute :>> id="S-DEPENDENCIES"; attribute :>> method="native"; attribute :>> artifact="vendor/gambit/lib/makefile.in"; attribute :>> scope="all66-fragment-rebuild-edges-and-preserved-relative-distribution-paths"; }
  part bootstrap:Need { ref part :>> gate=GambitCommitGates::tests; attribute :>> id="S-BOOTSTRAP"; attribute :>> method="native"; attribute :>> artifact="vendor/gambit/makefile.in"; attribute :>> scope="exact-submission-full-two-pass-bootstrap-within600-same-owned-SDK-existing-profile"; }
  part semantics:Need { ref part :>> gate=GambitCommitGates::tests; attribute :>> id="S-SEMANTICS"; attribute :>> method="native"; attribute :>> artifact="vendor/gambit/tests/frame-continuation.scm"; attribute :>> scope="existing-real-map-multishot-continuation-GC-on-rebuilt-cohort-no-twelve-SMP-claim"; }
  part roots:Need { ref part :>> gate=GambitCommitGates::tests; attribute :>> id="S-ROOTS"; attribute :>> method="source-and-native"; attribute :>> artifact="vendor/gambit/tests/frame-contract.c"; attribute :>> scope="all99-legacy-accesses-migrated-macro-value-single-evaluation-relocation-readback-clear-native-OS-producer-closure-no-independent-context-migration"; }
  part lesson:Need { ref part :>> gate=GambitCommitGates::learning; attribute :>> id="S-LESSON"; attribute :>> method="source-analysis"; attribute :>> artifact="dev/refactoring/modern-c/source-organization.org"; attribute :>> scope="actual-source-responsibility-benefit-added-maintenance-and-no-inferred-runtime-speedup"; }
  part process:Need { ref part :>> gate=GambitCommitGates::process; attribute :>> id="S-PROCESS"; attribute :>> method="source-analysis"; attribute :>> artifact="dev/refactoring/modern-c/models/sysml/source-organization.sysml"; attribute :>> scope="exact75-path-first-cut-exclusions-and-dependent-next-role-cut"; }
  part models:Need { ref part :>> gate=GambitCommitGates::models; attribute :>> id="S-MODELS"; attribute :>> method="native-model-projection"; attribute :>> artifact="dev/refactoring/modern-c/models/sysml/source-organization.sysml"; attribute :>> scope="native-partition-projection-actual-ASCENT-and-negative-source-evidence-controls-no-duplicate-QNT-Lean"; }
  part questions:Need { ref part :>> gate=GambitCommitGates::questions; attribute :>> id="S-QUESTIONS"; attribute :>> method="source-analysis"; attribute :>> artifact="dev/refactoring/modern-c/source-organization.org"; attribute :>> scope="Gambit-C-portability-and-multishot-invariants-source-versus-runtime-benefit-limits-and-retired-monolith-locations"; }
}
