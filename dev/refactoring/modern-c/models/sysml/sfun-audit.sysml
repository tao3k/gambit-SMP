package GambitSfunAudit {
 private import ScalarValues::*;
 attribute scope:String="Complete SFUN source refinement, model and retained native evidence companion. Unchanged published framework sources only; no runtime or independent SMP progress from this companion.";
 attribute stage:String="sfun-entry-audit";
 attribute formalDuty:String="Native SysML/ASCENT binds nine obligations and six C adapters. Existing QNT owns interleavings; five Lean root-span size/address laws are disjoint. Framework tests do not prove C semantics.";
 part submission:GambitCommitGates::SubmissionUnit {
 attribute :>> kind="support"; attribute :>> result=""; attribute :>> progressDelta=0;
 attribute :>> supportPaths="dev/modeling/ascent/binding-activation.rules.scm;dev/refactoring/modern-c/diagrams/sfun-entry.d2;dev/refactoring/modern-c/diagrams/sfun-entry.svg;dev/refactoring/modern-c/index.org;dev/refactoring/modern-c/models/lean/RootSpan.lean;dev/refactoring/modern-c/models/quint/native_entry_admission.qnt;dev/refactoring/modern-c/models/sysml/delivery-outcomes.sysml;dev/refactoring/modern-c/models/sysml/pending-cuts.sysml;dev/refactoring/modern-c/models/sysml/sfun-audit.sysml;dev/refactoring/modern-c/models/sysml/sfun-entry.sysml;dev/refactoring/modern-c/revision-checklist.org;dev/refactoring/modern-c/sfun-entry.org;evidence/research/retained/modern-c/sfun-entry/ascent-observation.json;evidence/research/retained/modern-c/sfun-entry/before-complete-ascent-observation.json;evidence/research/retained/modern-c/sfun-entry/before-complete-model-binding.json;evidence/research/retained/modern-c/sfun-entry/counterexamples/premature-marker-release.inc;evidence/research/retained/modern-c/sfun-entry/delivery.json;evidence/research/retained/modern-c/sfun-entry/framework-submission/review.json;evidence/research/retained/modern-c/sfun-entry/framework-submission/validation.json;evidence/research/retained/modern-c/sfun-entry/metrics.json;evidence/research/retained/modern-c/sfun-entry/model-binding.json;evidence/research/retained/modern-c/sfun-entry/model-snapshots/dev/modeling/models/sysml/commit-gates.sysml;evidence/research/retained/modern-c/sfun-entry/model-snapshots/dev/refactoring/modern-c/models/sysml/binding-activation.sysml;evidence/research/retained/modern-c/sfun-entry/model-snapshots/dev/refactoring/modern-c/models/sysml/delivery-outcomes.sysml;evidence/research/retained/modern-c/sfun-entry/model-snapshots/dev/refactoring/modern-c/models/sysml/delivery-plan.sysml;evidence/research/retained/modern-c/sfun-entry/model-snapshots/dev/refactoring/modern-c/models/sysml/header-organization.sysml;evidence/research/retained/modern-c/sfun-entry/model-snapshots/dev/refactoring/modern-c/models/sysml/pending-cuts.sysml;evidence/research/retained/modern-c/sfun-entry/model-snapshots/dev/refactoring/modern-c/models/sysml/request-product.sysml;evidence/research/retained/modern-c/sfun-entry/model-snapshots/dev/refactoring/modern-c/models/sysml/revision-delivery.sysml;evidence/research/retained/modern-c/sfun-entry/model-snapshots/dev/refactoring/modern-c/models/sysml/sfun-entry.sysml;evidence/research/retained/modern-c/sfun-entry/official-attribution.json;evidence/research/retained/modern-c/sfun-entry/pending-after.json;evidence/research/retained/modern-c/sfun-entry/pending-inventory.json;evidence/research/retained/modern-c/sfun-entry/post-ascent-observation.json;evidence/research/retained/modern-c/sfun-entry/post-model-binding.json;evidence/research/retained/modern-c/sfun-entry/pre-publication-ascent-observation.json;evidence/research/retained/modern-c/sfun-entry/pre-publication-model-binding.json;evidence/research/retained/modern-c/sfun-entry/pre-publication-pending-inventory.json;evidence/research/retained/modern-c/sfun-entry/pre-staging-custody.json;evidence/research/retained/modern-c/sfun-entry/qualification.json;evidence/research/retained/modern-c/sfun-entry/runs/sfun-entry-accept-3.json;evidence/research/retained/modern-c/sfun-entry/runs/sfun-entry-accept-7.json;evidence/research/retained/modern-c/sfun-entry/runs/sfun-entry-accept-8.json;evidence/research/retained/modern-c/sfun-entry/runs/sfun-entry-consumers-final.json;evidence/research/retained/modern-c/sfun-entry/runs/sfun-entry-cost-2.json;evidence/research/retained/modern-c/sfun-entry/runs/sfun-entry-cost-final.json;evidence/research/retained/modern-c/sfun-entry/runs/sfun-entry-final-population.json;evidence/research/retained/modern-c/sfun-entry/runs/sfun-entry-native-1.json;evidence/research/retained/modern-c/sfun-entry/runs/sfun-entry-native-2.json;evidence/research/retained/modern-c/sfun-entry/runs/sfun-entry-native-3.json;evidence/research/retained/modern-c/sfun-entry/runs/sfun-entry-native-4.json;evidence/research/retained/modern-c/sfun-entry/runs/sfun-entry-official-repeat.json;evidence/research/retained/modern-c/sfun-entry/runs/sfun-entry-revoke-before.json;evidence/research/retained/modern-c/sfun-entry/sfun-entry-observation-control.trace;evidence/research/retained/modern-c/sfun-entry/sfun-entry-production.trace;evidence/research/retained/modern-c/sfun-entry/source-manifest.json;evidence/research/retained/modern-c/sfun-entry/source-refinement.json;evidence/research/retained/modern-c/sfun-entry/submission/admission.json;evidence/research/retained/modern-c/sfun-entry/submission/comment.json;evidence/research/retained/modern-c/sfun-entry/submission/model-contract.json;evidence/research/retained/modern-c/sfun-entry/submission/revision.json;evidence/research/retained/modern-c/sfun-entry/submission/source-manifest.json;evidence/research/retained/modern-c/sfun-entry/submission/source.json;src/gambit_smp/native_development.py;src/gambit_smp/runtime_binding.py;tests/test_native_development.py;tests/test_runtime_binding.py";
 attribute :>> testModules="tests/test_native_development.py;tests/test_runtime_binding.py";
 }
 part def Need { ref part gate:GambitCommitGates::Gate; attribute id:String; attribute method:String; attribute artifact:String; attribute scope:String; }
 part tests:Need { ref part :>> gate=GambitCommitGates::tests; attribute :>> id="SFUN-AUDIT-TESTS"; attribute :>> method="native"; attribute :>> artifact="evidence/research/retained/modern-c/sfun-entry/framework-submission/validation.json"; attribute :>> scope="37 unchanged published-source framework tests pass. Complete runtime tests have independent vendor five-gate admission."; }
 part learning:Need { ref part :>> gate=GambitCommitGates::learning; attribute :>> id="SFUN-AUDIT-LEARNING"; attribute :>> method="source-analysis"; attribute :>> artifact="dev/refactoring/modern-c/sfun-entry.org"; attribute :>> scope="Revoking return permission is not physical C quiescence; conditional allocation saving and measured single-input regression remain explicit."; }
 part process:Need { ref part :>> gate=GambitCommitGates::process; attribute :>> id="SFUN-AUDIT-PROCESS"; attribute :>> method="source-analysis"; attribute :>> artifact="dev/refactoring/modern-c/sfun-entry.org"; attribute :>> scope="One whole19-file owner, original51 pending paths preserved; foundation4/4 and SMP1/12 unchanged."; }
 part models:Need { ref part :>> gate=GambitCommitGates::models; attribute :>> id="SFUN-AUDIT-MODELS"; attribute :>> method="native"; attribute :>> artifact="evidence/research/retained/modern-c/sfun-entry/framework-submission/review.json"; attribute :>> scope="Native SDK9 obligations and6 source adapters, missing/stale controls, vendor47 rejection controls; QNT interleavings and Lean layout arithmetic are distinct."; }
 part questions:Need { ref part :>> gate=GambitCommitGates::questions; attribute :>> id="SFUN-AUDIT-QUESTIONS"; attribute :>> method="source-analysis"; attribute :>> artifact="dev/refactoring/modern-c/sfun-entry.org"; attribute :>> scope="Actual roots, scan/census, marker, frame and last-use custody; original failures and timeouts preserved; no universal speedup or native closure-trampoline claim."; }
}
