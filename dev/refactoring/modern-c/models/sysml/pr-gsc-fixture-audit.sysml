package GambitPrGscFixtureAudit {
 private import ScalarValues::*;
 attribute scope:String="Complete fifth-family compiled PR qualification and explicit interruption-test lifetime ownership. Preserve all original computations and assertions, exact source/profile and original guards. No scheduler/runtime reconstruction or efficiency-upgrade claim.";
 attribute stage:String="complete-pr-gsc";
 attribute formalDuty:String="The strict installed OpenSysML SDK owns the eight fixtures and actual p1/p2 contract. Existing ASCENT prefix and five-gate rules bind native execution, source refinement, exact test consumers and historical model/code periods. Existing QNT temporal ownership and Lean frame/range duties remain distinct and unchanged.";
 part submission:GambitCommitGates::SubmissionUnit {
  attribute :>> kind="support"; attribute :>> result=""; attribute :>> progressDelta=0;
  attribute :>> supportPaths="tests/unit-tests/06-thread/thread_interrupt.scm";
  attribute :>> testModules="";
 }
 part def Need { ref part gate:GambitCommitGates::Gate; attribute id:String; attribute method:String; attribute artifact:String; attribute scope:String; }
 part tests:Need { ref part :>> gate=GambitCommitGates::tests; attribute :>> id="GAMBITPRGSCFIXTUREAUDIT-TESTS"; attribute :>> method="native"; attribute :>> artifact="evidence/research/retained/modern-c/pr-gsc/qualified-native.json"; attribute :>> scope="One complete compiled campaign: eight cases in each actual p1/p2 population, exact GSC commands, natural completion and quiescent restoration. Preserve original failed campaign and unchanged300/295-second limits. Companion framework qualifies complete affected test modules and all rejection controls."; }
 part learning:Need { ref part :>> gate=GambitCommitGates::learning; attribute :>> id="GAMBITPRGSCFIXTUREAUDIT-LEARNING"; attribute :>> method="source-analysis"; attribute :>> artifact="dev/refactoring/modern-c/pr-gsc.org"; attribute :>> scope="Finite computation ratios cannot own thread lifetime. Explicit receive/send/join preserves every original test and keeps missing interruption a failure; one extra assertion. Distinguish native qualification from a runtime modernization or speedup claim."; }
 part process:Need { ref part :>> gate=GambitCommitGates::process; attribute :>> id="GAMBITPRGSCFIXTUREAUDIT-PROCESS"; attribute :>> method="source-analysis"; attribute :>> artifact="evidence/research/retained/modern-c/pr-gsc/acceptance.json"; attribute :>> scope="Extend only the same canonical producer/profile prefix from4/12 to5/12, with seven later families open. Preserve the historical4/12 ledger and all counterexamples. Existing PR branches only; no unrelated Changes, larger heap or wait."; }
 part models:Need { ref part :>> gate=GambitCommitGates::models; attribute :>> id="GAMBITPRGSCFIXTUREAUDIT-MODELS"; attribute :>> method="native"; attribute :>> artifact="evidence/research/retained/modern-c/pr-gsc/model-binding.json"; attribute :>> scope="The strict pinned OpenSysML Python SDK resolves all eight fixture symbols and complete original resource/population contract. Existing ASCENT prefix and five-gate rejection controls; no duplicate QNT/Lean."; }
 part questions:Need { ref part :>> gate=GambitCommitGates::questions; attribute :>> id="GAMBITPRGSCFIXTUREAUDIT-QUESTIONS"; attribute :>> method="source-analysis"; attribute :>> artifact="dev/refactoring/modern-c/pr-gsc.org"; attribute :>> scope="Explain legal inactive-target exception, retained assertions, source-refinement and historical source/model binding, actual compile/load mode, net functional benefit, added handshake costs and unmeasured pause/throughput/RSS. Remote CI remains separate."; }
}
