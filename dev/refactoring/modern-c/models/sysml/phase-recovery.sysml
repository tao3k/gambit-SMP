package GambitPhaseRecovery {
 private import ScalarValues::*;
 attribute scope:String="Phase-recovery controller interruption at child release, not at birth custody. Gambit modern-c remains the primary runtime line; repair-source CI and framework acceptance are independent cohorts.";
 attribute stage:String="Support correction on7c68d161, progressDelta0. Fifteen complete-module cases; existing modern-c root/lifecycle targets re-executed without compilation. Architecture3/4 and independent SMP1/12 unchanged.";
 attribute formalDuty:String="Native SysML defines cut/source/cohort duties; existing ASCENT owns five-gate submission admission. QNT schedule and Lean algebra duties unchanged; neither is duplicated for a test interruption cut. LLM review does not prove hosted equivalence.";
 attribute birthRule:String="launch-owner records durable birth before parent permission and environment delivery. Suspending the parent here may prevent the child target from starting. Keep early birth custody for real cancellation/recovery; do not move production started publication.";
 attribute releaseRule:String="Observe exec-intent from the exact planned spawn directory with matching token and complete birth identity before pausing the parent. Intent establishes complete environment delivery, not successful exec. Keep real stage bytes, child exit/quiescence and checkpoint reuse assertions.";
 attribute limitsRule:String="Unchanged120s supervisor,60s sealed domain,20s fixture deadline,15s recipe and10s launch handshake. Host birth-control module needs real host tools and is run separately; a sealed provider without lsof is not a valid environment for it.";
 attribute cohortRule:String="Framework tests qualify research transport only. SMP upstream/numeric jobs use the locked repair-source cohort, not vendor modern-c. Their failures remain required CI evidence but confer no modern-c regression/pass inference. modern-c3d42 native artifacts and source are explicitly matched; hosted candidate/baseline remain queued.";
 attribute fourthRule:String="Request-product remains OPEN. Stable request service activation, actual waiting/FIFO ownership and complete matched product/release obligations are the next whole runtime responsibility. Do not turn framework failure repair into architecture progress, frontend optimization or generic scheduler repair.";
 attribute diagram:String="direction: right\nbirth: Birth custody published\npermission: Full environment delivered to child\nintent: Matching exec intent\nphase: Real phase bytes and exit\nresume: Checkpoint reuse without evaluation\nbirth -> permission: parent must remain runnable\npermission -> intent\nintent -> phase: parent may now be paused\nphase -> resume\nframework: Framework cohort\nrepair: Locked repair-source CI\nmodern: Gambit modern-c runtime\nmac: Matched hosted macOS unresolved\nframework -> resume: test protocol only\nrepair -> modern: no acceptance transfer { style.stroke-dash: 4 }\nmodern -> mac: independent evidence required\n";
 part def Role { attribute source:String; attribute duty:String; }
 part launch:Role { attribute :>> source="src/gambit_smp/spawn_protocol.py::launch;child"; attribute :>> duty="Keep durable birth before release; token/birth matched exec-intent after full payload validation."; }
 part checkpoint:Role { attribute :>> source="tests/test_sealed_checkpoint_recovery.py"; attribute :>> duty="Suspend only after exact child release witness; preserve original phase, reuse and quiescence checks."; }
 part cancellation:Role { attribute :>> source="tests/test_spawn_birth_recovery.py"; attribute :>> duty="Actual pre-permission SIGKILL/EOF negative control proves that birth does not imply released target; permission and intent must both be absent."; }
 part def Need { attribute id:String; ref part gate:GambitCommitGates::Gate; attribute method:String; attribute artifact:String; attribute scope:String; }
 part tests:Need { attribute :>> id="PHASE-RECOVERY-TESTS"; ref part :>> gate=GambitCommitGates::tests; attribute :>> method="native"; attribute :>> artifact="evidence/research/retained/modern-c/phase-recovery/receipt.json"; attribute :>> scope="Focused phase recovery support, no whole CI or runtime integration credit"; }
 part learning:Need { attribute :>> id="PHASE-RECOVERY-LEARNING"; ref part :>> gate=GambitCommitGates::learning; attribute :>> method="source-refinement"; attribute :>> artifact="evidence/research/retained/modern-c/phase-recovery/receipt.json"; attribute :>> scope="Focused phase recovery support, no whole CI or runtime integration credit"; }
 part process:Need { attribute :>> id="PHASE-RECOVERY-PROCESS"; ref part :>> gate=GambitCommitGates::process; attribute :>> method="source-refinement"; attribute :>> artifact="evidence/research/retained/modern-c/phase-recovery/receipt.json"; attribute :>> scope="Focused phase recovery support, no whole CI or runtime integration credit"; }
 part models:Need { attribute :>> id="PHASE-RECOVERY-MODELS"; ref part :>> gate=GambitCommitGates::models; attribute :>> method="source-refinement"; attribute :>> artifact="evidence/research/retained/modern-c/phase-recovery/receipt.json"; attribute :>> scope="Focused phase recovery support, no whole CI or runtime integration credit"; }
 part questions:Need { attribute :>> id="PHASE-RECOVERY-QUESTIONS"; ref part :>> gate=GambitCommitGates::questions; attribute :>> method="source-refinement"; attribute :>> artifact="evidence/research/retained/modern-c/phase-recovery/receipt.json"; attribute :>> scope="Focused phase recovery support, no whole CI or runtime integration credit"; }
 part submission:GambitCommitGates::SubmissionUnit { attribute :>> kind="support"; attribute :>> result=""; attribute :>> progressDelta=0; attribute :>> supportPaths="tests/test_sealed_checkpoint_recovery.py;tests/test_spawn_birth_recovery.py;dev/refactoring/modern-c/models/sysml/phase-recovery.sysml;dev/refactoring/modern-c/phase-recovery.org;dev/refactoring/modern-c/branch-checklist.org;dev/refactoring/modern-c/diagrams/phase-recovery.d2;dev/refactoring/modern-c/diagrams/phase-recovery.svg;evidence/research/retained/modern-c/phase-recovery/receipt.json;evidence/research/retained/modern-c/phase-recovery/mainline.json;evidence/research/retained/modern-c/phase-recovery/counterexample.json;evidence/research/retained/modern-c/phase-recovery/remote.json"; attribute :>> testModules="tests/test_sealed_checkpoint_recovery.py;tests/test_spawn_birth_recovery.py"; }
}
