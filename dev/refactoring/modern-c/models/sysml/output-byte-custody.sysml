package GambitOutputByteCustody {
 private import ScalarValues::*;
 attribute scope:String="Complete existing review-output byte delivery: original Git archival sources, existing publication registry, raw byte borrowing, archive/causal/environment callers and real sealed policy. No new registry, executor, runtime path or SDK workspace.";
 attribute stage:String="Support only, progressDelta0. Architecture3/4, independent SMP1/12. Full framework71 failure/error events,11 missing expected IDs and2 skips remain unqualified; hosted macOS queue is not execution.";
 attribute sourceRule:String="21 exact path/digest bindings retain all original observation fields. Actual Git source bytes, SHA and count are verified. A bare published observation cannot satisfy the byte requirement. No transcript file, reconstructed text or raw-log wrapper is published.";
 attribute archivalLimit:String="These are the exact declared archival bytes, including historical redaction. Original-parent/log binding gaps and non-admitted archive status are unchanged; immutable Git custody does not create native execution or retry applicability.";
 attribute leaseRule:String="Borrow once per exact path/digest within one review; bind the unchanged publication JSON before and after actual bytes and existing final native inference checks. Physical drift never falls back to Git. Missing/ambiguous origins, unknown objects, Cache identities and wrong path/blob/count refuse.";
 attribute callerClosure:String="native_review.bind_log_bytes supplies historical_observation, project_review raw entry/claim references and environment_change controls. All other JSON/source/budget/campaign predicates and native policy stay mandatory.";
 attribute nativeBoundary:String="83 scoped complete tests, including68 actual sealed-domain cases. Never load editable code as a sealed provider: the observed origin denial is retained and the candidate uses the existing immutable seal/domain interfaces. Exact unchanged native domain receipt reused only after engine, source, test, child result, queue and owner checks.";
 attribute retainedFailure:String="Unchanged complete3-case local linker module fails identically on6fa and candidate. Failed case calls unchanged native_capabilities.host_tools and compiler driver, expecting/usr/bin/ld while Darwin resolves the Xcode ld. Exact source/input evidence is retained; no hosted issue216 attribution or full-platform waiver.";
 attribute formalDuty:String="Existing QNT owns schedule/epoch properties; Lean conditional algebra. Git/file/byte and actual policy execution are source/native refinement premises, not duplicated QNT/Lean claims. Existing tests and all full CI populations remain.";
 attribute diagram:String="direction: right\nold: Original committed archival bytes\nregistry: Existing publication identity and per-origin Git sources\nborrow: Exact byte borrow\nverify: Commit + blob + SHA + byte count\nreview: Existing archive / causal / environment consumers\npolicy: Real sealed ASCENT conditional policy\nrun: Actual runtime result still required\nrefuse: Missing object / summary only / drift refused\npending: Full framework and hosted macOS remain open\nold -> registry: symbolic identity only\nregistry -> borrow\nborrow -> verify\nverify -> review: memory only; no transcript file\nreview -> policy: original budgets and failures retained\npolicy -> run: eligibility is not execution\nverify -> refuse: invalid or unknown\nrun -> pending: independent product gates\n";
 part def ByteRole { attribute path:String; attribute anchor:String; attribute obligation:String; }
 part producer:ByteRole { attribute :>> path="evidence/published-inputs.json"; attribute :>> anchor="observations.sources"; attribute :>> obligation="Per-origin Git descriptor only; preserve every old digest, byte count, origin and failed observation. Ambiguous origins remain unresolved; never mint text or a native result."; }
 part reader:ByteRole { attribute :>> path="src/gambit_smp/output_observations.py"; attribute :>> anchor="read_bytes"; attribute :>> obligation="PHYSICAL or GIT byte source must verify identity; a physical mismatch refuses, not fallbacks. Registry changes invalidate an in-memory Git borrow. Return only bytes plus regular input bindings."; }
 part consumer:ByteRole { attribute :>> path="src/gambit_smp/native_review.py"; attribute :>> anchor="bind_log_bytes;project_review;historical_observation;environment_change"; attribute :>> obligation="One review owns repeated byte borrows until its original final input checks; preserve archive membership, causal claims, candidate/source identities, budgets and conditional policy. Eligibility grants neither execution nor native admission."; }
 part def RemoteFamily { attribute id:String; attribute cases:Integer; attribute obligation:String; attribute status:String="OPEN"; attribute evidence:String="evidence/research/retained/modern-c/output-byte-custody/framework-ledger.json"; }
 part repositories:RemoteFamily { attribute :>> id="F-GIT-IDENTITY"; attribute :>> cases=16; attribute :>> obligation="Construct real isolated source repositories and exact locked gitlink state; keep wrong-repository and wrong-lock refusal controls."; }
 part authors:RemoteFamily { attribute :>> id="F-GIT-AUTHOR"; attribute :>> cases=4; attribute :>> obligation="Fixture-local explicit Git author; no global Git settings and no weaker source commit checks."; }
 part epochs:RemoteFamily { attribute :>> id="F-SOURCE-EPOCH"; attribute :>> cases=12; attribute :>> obligation="Separate immutable historical projections from actual current modular translation units; preserve source proof intent instead of refreshing hashes."; }
 part transcripts:RemoteFamily { attribute :>> id="F-TRANSCRIPT"; attribute :>> cases=7; attribute :>> obligation="Audit all remaining direct byte readers and model-native prerequisites; a scoped review fix does not close their assertions automatically."; }
 part tools:RemoteFamily { attribute :>> id="F-PLATFORM-TOOLS"; attribute :>> cases=6; attribute :>> obligation="Qualify required native SysML and host-specific tools with actual supported inputs; do not invent outputs or skip qualification."; }
 part contracts:RemoteFamily { attribute :>> id="F-OTHER-CONTRACTS"; attribute :>> cases=26; attribute :>> obligation="Trace each remaining test to actual producer/consumer semantics and baseline; no name-only exemptions or assertion weakening."; }
 part def Need { attribute id:String; ref part gate:GambitCommitGates::Gate; attribute method:String; attribute artifact:String; attribute scope:String; }
 part tests:Need { attribute :>> id="OUTPUT-BYTES-TESTS"; ref part :>> gate=GambitCommitGates::tests; attribute :>> method="native"; attribute :>> artifact="evidence/research/retained/modern-c/output-byte-custody/receipt.json"; attribute :>> scope="Actual archival byte custody only; historical failure and full CI/platform gates retained"; }
 part learning:Need { attribute :>> id="OUTPUT-BYTES-LEARNING"; ref part :>> gate=GambitCommitGates::learning; attribute :>> method="source-refinement"; attribute :>> artifact="evidence/research/retained/modern-c/output-byte-custody/receipt.json"; attribute :>> scope="Actual archival byte custody only; historical failure and full CI/platform gates retained"; }
 part process:Need { attribute :>> id="OUTPUT-BYTES-PROCESS"; ref part :>> gate=GambitCommitGates::process; attribute :>> method="source-refinement"; attribute :>> artifact="evidence/research/retained/modern-c/output-byte-custody/receipt.json"; attribute :>> scope="Actual archival byte custody only; historical failure and full CI/platform gates retained"; }
 part models:Need { attribute :>> id="OUTPUT-BYTES-MODELS"; ref part :>> gate=GambitCommitGates::models; attribute :>> method="source-refinement"; attribute :>> artifact="evidence/research/retained/modern-c/output-byte-custody/receipt.json"; attribute :>> scope="Actual archival byte custody only; historical failure and full CI/platform gates retained"; }
 part questions:Need { attribute :>> id="OUTPUT-BYTES-QUESTIONS"; ref part :>> gate=GambitCommitGates::questions; attribute :>> method="source-refinement"; attribute :>> artifact="evidence/research/retained/modern-c/output-byte-custody/receipt.json"; attribute :>> scope="Actual archival byte custody only; historical failure and full CI/platform gates retained"; }
 part submission:GambitCommitGates::SubmissionUnit { attribute :>> kind="support"; attribute :>> result=""; attribute :>> progressDelta=0; attribute :>> supportPaths="src/gambit_smp/output_observations.py;src/gambit_smp/native_review.py;evidence/published-inputs.json;tests/test_output_observations.py;tests/test_native_retry_review.py;tests/test_source_identity.py;dev/refactoring/modern-c/models/sysml/output-byte-custody.sysml;dev/refactoring/modern-c/output-byte-custody.org;dev/refactoring/modern-c/branch-checklist.org;dev/refactoring/modern-c/diagrams/output-byte-custody.d2;dev/refactoring/modern-c/diagrams/output-byte-custody.svg;evidence/research/retained/modern-c/output-byte-custody/receipt.json;evidence/research/retained/modern-c/output-byte-custody/native-domain.json;evidence/research/retained/modern-c/output-byte-custody/retained-linker-failure.json;evidence/research/retained/modern-c/output-byte-custody/framework-ledger.json;evidence/research/retained/modern-c/output-byte-custody/remote.json"; attribute :>> testModules="tests/test_source_identity.py;tests/test_output_observations.py;tests/test_native_retry_review.py"; }
}
