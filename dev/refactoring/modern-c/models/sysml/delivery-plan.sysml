package GambitModernCDeliveryPlan {
  private import ScalarValues::*;
  attribute base:String="043a9341168645caa1fc8f13cb586ef63a352dcc";
  attribute policy:String="The13 stages are a responsibility catalogue, not a completed-progress denominator. GambitModernCOutcomes owns four complete integration results; internal source leaves and15 review units are not delivered SMP outcomes. Preserve historical scoped evidence without promoting it into a complete result.";
  attribute immediate:String="Three local managed C-target results are qualified. Next deliver explicit request/message ownership and stable service activation with full original/native/Gerbil products and matched performance populations. Read independent SMP progress from the accepted ledger and its exact-source receipts.";
  attribute commitRule:String="A bounded REV needs exact source/ABI consumers, actual required tests, learning/benefit/cost, process and model/question closure under shared five ASCENT gates. Missing tests or unexplained affected failures block it. Broader failures must have explicit applicability/disposition; scoped gate readiness never means whole branch admission.";
  attribute nextSource:String="GambitModernCOutcomes::execution owns the fourth whole result. Replace waiting/service-activation and shared FIFO lifetime responsibilities; retain the qualified root, physical copy/restore and lifecycle contracts. Do not turn tfib or every CFFI feature into another stopgap batch.";
  attribute nextAcceptance:String="On the final source run complete interpreted/compiled, PR/stress and Gerbil manifests under fixed resource limits. Trace actual request/FIFO ownership and repeated service continuation work; collect matched performance populations. Keep all root/collector/lifecycle regressions and explicit baseline failures. Three predecessor results grant no SMP family credit.";
  attribute nextExclusions:String="Do not absorb generic Tcl/CFFI semantics, unrelated header extraction, Darwin frontend tuning or LLVM/MLIR into request-service delivery. Preserve official entrypoints and the one cache/profile; no heap/deadline inflation.";
  attribute supportPolicy:String="Header modularization, C23/toolchain admission, generated products/build invalidation and vendor CI remain separate support lanes. They join a runtime REV only for its actual source/ABI dependency closure. Preserve existing Bazel/configure/Make and official test names. A mechanically moved header must prove losslessness independently from semantic field changes; generated C must bind one source/features/compiler cohort; CI follows qualified source/tests.";
  attribute closurePolicy:String="Official test8/test9 are known repaired behavior on the repair line, not Repair9 or acceptance families8/9. Reconstruct and qualify the foundation on modern-c before the coupled Repair9 work. A checklist is a falsifiable architecture-coverage argument: source mechanism retired, owning contract, dependency, counterexample and native acceptance; it is never a claim that planning or finite model success already solves9-12. Whole acceptance is the conjunction on one final source, not the sum of local REVs.";
  attribute capacityPolicy:String="Repair9 correctness and capacity are separate: at minimum count accepted/claimed/completed/abandoned work, live request roots, captured versus materialized frames, copied/scanned bytes, waiting/service time and retained peak. Finite safety cannot prove a deadline. Unbounded arrival or an indefinitely retained user multi-shot continuation precludes a universal constant-memory/latency claim. No pooling or one-shot restriction is imposed to manufacture a gain.";
  attribute coveragePolicy:String="ROOTS has six responsibility coverage groups, not six predetermined REVs or six SMP acceptance families. SCOPED_CLOSED means only the listed leaf contract has native publication evidence. QUALIFYING and OPEN count as remaining. A complete caller/lifetime census and composed acceptance are necessary to close the ROOTS stage. Counts are derived from these records; no test/commit-count percentage is permitted.";
  attribute auditPolicy:String="GambitModernCOutcomes owns main integration progress; the13 numbered items are an architecture responsibility catalogue. Report qualified integration results and independent full native families first. Dotted children, scoped leaves and support/documentation REVs are audit references, never a progress numerator. A complete responsibility tree needs actual source/native evidence and explicit retirement; no repair-line credit transfers.";
  attribute acceptancePolicy:String="The separate SMP table retains twelve equal-weight evidence families. Exact source/profile and complete actual manifests are required; refactoring stages and repair-line aggregates never substitute. A source/profile-bound unresolved-failure veto takes precedence over a later pass. Therefore the phase-result candidate can have a completed scoped original recheck while its GSI family stays open after the retained same-image thread failure. Stale-tree/profile blockers do not veto a different source. Bootstrap pass alone is not whole SMP stability or an effort percentage.";
  part def RootCoverage {
    attribute ordinal:String;
    attribute id:String; attribute status:String; attribute scope:String;
    attribute evidence:String; attribute remaining:String;
  }
  part namedRoots:RootCoverage {
    attribute :>> ordinal="3.1";
    attribute :>> id="ROOT-NAMED"; attribute :>> status="SCOPED_CLOSED";
    attribute :>> scope="Named RC, VM, bank, stack/continuation, symkey anchor and globals RootOrigin adapters with task leases";
    attribute :>> evidence="branch-checklist.org; individual root-task publication packets";
    attribute :>> remaining="No total writer/caller census, independent-worker or whole-root closure follows";
  }
  part globalsPrefix:RootCoverage {
    attribute :>> ordinal="3.2";
    attribute :>> id="ROOT-GLOBALS"; attribute :>> status="SCOPED_CLOSED";
    attribute :>> scope="Common globals extent and admitted registration transaction";
    attribute :>> evidence="globals-snapshot-result.org; publication7abe6770";
    attribute :>> remaining="Arbitrary value writers and raw cross-VM stores remain separate";
  }
  part symkeyPublish:RootCoverage {
    attribute :>> ordinal="3.3";
    attribute :>> id="ROOT-SYMKEY"; attribute :>> status="SCOPED_CLOSED";
    attribute :>> scope="Native canonical interning, rehash publication and GC anchor handoff as one service responsibility";
    attribute :>> evidence="symkey-publication-result.org; publication92d70198, five gates/21 controls and exact-source original/native consumers";
    attribute :>> remaining="Scope excludes raw Scheme views/mutation, optional debug-GC diagnostics, arbitrary reentry or moving publishers and complete lifetime census";
  }
  part rootViews:RootCoverage {
    attribute :>> ordinal="3.4";
    attribute :>> id="ROOT-VIEWS"; attribute :>> status="SCOPED_CLOSED";
    attribute :>> scope="C-target managed folds/owned getters and direct callers, plus source admission for the locked1778-file Gerbil cohort and declared default build/load roots";
    attribute :>> evidence="symkey-views-result.org;3.4.1 da5651af. symkey-getters-result.org;3.4.2 ae19f986. external-views.org;3.4.3 exact1778-file cohort,185 bootstrap modules,zero active raw readers,two explicitly excluded TODO functions,six rejection controls and actual native getter/GC isolation probe";
    attribute :>> remaining="Scoped to the recorded cohort and default build-source/load premises, not all Gerbil execution. Changed source, custom load/init paths, aliases or extensions invalidate the source-admission receipt and require a new census/migration; no runtime sandbox or raw getter fallback. Native debug/reflection, complete writers and lifetime union remain3.5/3.6 obligations";
  }
  part rootWriters:RootCoverage {
    attribute :>> ordinal="3.5";
    attribute :>> id="ROOT-WRITERS"; attribute :>> status="OPEN";
    attribute :>> scope="Remaining primitive, raw, FFI and cross-VM value writers";
    attribute :>> evidence="Published3.5.1 REV8ee204fc: RC write authority,400 actions and predecessor13-to1 replay. Published3.5.2.1 REV920cf0c7: tcl-command-result.org, construction root/returned ownership,300 real actions,13-to1 rejection replay and configured Make prefix consumers. Published3.5.2.2 REVe6a80bcb: marker-input-result.org, explicit marker lifetime classes,295 real actions and13-to1 replay. Published3.5.2.3 REV4b9d8656: symkey-callback-result.org, checked permanent native identity snapshot, unlock-before-callback and real TTY refusal,313 actions/13-to1 replay; parent3.5.2 and3.5 remain OPEN. Published3.5.2.4 REV043a9341: tcl-callback-result.org, stable native identity/post-conversion reload, active-owner pin and complete paired baseline disposition. Parent3.5.2/3.5/3.6 remain open. Repair evidence is reference only";
    attribute :>> remaining="RC3.5.1 is one bounded leaf, not complete3.5. Raw data_rc snapshots around allocation, globals/raw FFI/primitive value writers, native debug/reflection and their composed source freeze/borrow lifetimes remain open";
  }
  part rootCensus:RootCoverage {
    attribute :>> ordinal="3.6";
    attribute :>> id="ROOT-CENSUS"; attribute :>> status="OPEN";
    attribute :>> scope="Composed caller/lifetime census and frozen root union before worker handoff";
    attribute :>> evidence="Existing root_dispatch temporal contract and conditional Lean cell laws";
    attribute :>> remaining="Actual-source coverage, resource lifetime and task-union refinement; local leaf names cannot discharge this group";
  }
  part def Stage {
    attribute ordinal:Integer;
    attribute lane:String default = "runtime";
    ref part owner:GambitRevisionDelivery::Revision;
    attribute id:String; attribute title:String; attribute status:String;
    attribute scope:String; attribute retire:String; attribute validation:String;
    attribute benefit:String; attribute excluded:String; attribute modelDuty:String;
  }
  part inventory:Stage {
    attribute :>> ordinal=1;
    ref part :>> owner=GambitRevisionDelivery::runtime;
    attribute :>> id="inventory"; attribute :>> title="Bind pending changes and responsibility owners";
    attribute :>> status="REVIEWED_PLAN_ONLY";
    attribute :>> scope="Separate committed source, index prototypes, working-only deltas and generated output; bind exact HEAD/path hashes and map every pending path to an existing owner";
    attribute :>> retire="No runtime retirement at this stage; eliminate ambiguous submission scope";
    attribute :>> validation="Stable read-only Git census; complete group coverage and acyclic typed stage links; no source/artifact mutation";
    attribute :>> benefit="Every candidate has a review boundary; published leaves cannot qualify the dirty working tree";
    attribute :>> excluded="Classification does not validate a hunk, ABI or runtime";
    attribute :>> modelDuty="Native SysML drives ASCENT coverage/dependency checks; no new behavioural QNT or Lean model";
  }
  part startup:Stage {
    attribute :>> ordinal=2;
    ref part :>> owner=GambitRevisionDelivery::vmMembership;
    attribute :>> id="startup"; attribute :>> title="Startup preparation and member publication";
    attribute :>> status="PUBLISHED_SCOPED";
    attribute :>> scope="test8 actual setup/resize chain: rooted request, target resource census, concrete disjoint stack/heap grants, per-slot initialization, OS creation/entry gate and one member-publication authority";
    attribute :>> retire="Count-only sufficiency followed by incidental section allocation; member publication before created native custody; rollback through an unrelated slot; pre-marker root receipt lost with a C activation";
    attribute :>> validation="Original test8 must succeed unchanged in the existing profile; feasible grow/shrink/reuse, allocation/partial-create failure and unknown outcome keep exact source roots, grants and members; bootstrap and affected original GC/FFI consumers";
    attribute :>> benefit="Requested topology has real backing before visibility; failure has one resource/root custodian, without changing min/max heap or waits";
    attribute :>> excluded="Recoverable refusal alone is not test8 PASS. No full collector packing, all CFFI or universal join recovery in this cut. Earlier Heap-overflow diagnosis is not a fresh diagnosis of every exit70";
    attribute :>> modelDuty="Reuse vm_resize_transaction.qnt for request/reserve/create/commit/unknown histories; RoundCapacity.lean owns conditional interval arithmetic only. Derive actual allocator bounds and source adapter; do not copy a finite capacity constant into C";
  }
  part roots:Stage {
    attribute :>> ordinal=3;
    ref part :>> owner=GambitRevisionDelivery::rootDispatch;
    attribute :>> id="roots"; attribute :>> title="Close the complete frozen root population";
    attribute :>> status="QUALIFIED_C_TARGET_UNION";
    attribute :>> scope="Common globals prefix and admitted registry registration published7abe6770; remaining symbol/keyword publication, raw/cross-VM value writers, complete RootOrigin caller/lifetime census and relocation/reload";
    attribute :>> retire="Per-scanner count authority retired7abe6770; next retire remaining unowned write/lifetime authority only after all selected callers migrate";
    attribute :>> validation="Preserve actual common-prefix/C4-step replay and nonzero RC/map multi-shot roots; add the next selected source's late writer/failed transfer histories using existing PBT";
    attribute :>> benefit="One frozen source population defines scan work and moving-cell updates";
    attribute :>> excluded="Named root tasks alone are not total census, independent workers or arbitrary raw FFI coverage";
    attribute :>> modelDuty="Existing root-dispatch QNT owns task histories; existing root coverage laws own distinct conditional cell/partition arithmetic; source completeness remains source evidence";
  }
  part workers:Stage {
    attribute :>> ordinal=4;
    ref part :>> owner=GambitRevisionDelivery::workerMemory;
    attribute :>> id="workers"; attribute :>> title="Worker arenas, unique copy work and context restoration";
    attribute :>> status="PLANNED";
    attribute :>> scope="W workers consume R frozen root domains; worker owns copy/scan/Tail and contiguous grants; each context receives its restoration space and owner-affine cleanup independently";
    attribute :>> retire="Collector cursors, refill and restoration inferred from carrier indexes; unowned claimed/private work";
    attribute :>> validation="W<R, exact moving roots, forwarding/CAS loss, claimed chunks/Tail, restore all R contexts, partial failure and original topology; same heap policy and measured physical peak";
    attribute :>> benefit="Useful collector work need not equal execution carrier population; no hidden work disappears at an idle decrement";
    attribute :>> excluded="Changing worker counts alone, larger heap or extra checks do not qualify this stage";
    attribute :>> modelDuty="Existing work/copy QNT models own histories; existing accounting/packing Lean laws own conditional bounds. Full C producer census, C23 ordering and physical layout remain explicit refinements";
  }
  part scheduling:Stage {
    attribute :>> ordinal=5;
    ref part :>> owner=GambitRevisionDelivery::publication;
    attribute :>> id="scheduling"; attribute :>> title="Request ownership, wait state and service activation";
    attribute :>> status="IN_PROGRESS_UNQUALIFIED";
    attribute :>> scope="One request ownership chain through publish/claim/execute/result/abandonment; durable runnable/park handoff; waiting state and service activation retain distinct roots and outcomes";
    attribute :>> retire="Processor routing treated as semantic request ownership; wake treated as completion; repeated state rebuilding only where actual source/cost evidence permits";
    attribute :>> validation="Real mailbox/migration/block/GC and exception/multi-shot histories, PBT replay/shrink, native wait failure and original pressure; per-target progress and actual allocation/materialization attribution";
    attribute :>> benefit="Remove redundant routing/capture/retention work while preserving synchronous Scheme result and supported control semantics";
    attribute :>> excluded="repair9 is one failure corpus, not the programme. No deletion of catchers absent from this branch; no pooling/coalescing arbitrary thunks or one-shot restriction on user continuations";
    attribute :>> modelDuty="Reuse existing delivery/wait temporal models; source/effect/GC map equivalence and native cost are separate. No duplicate Lean temporal machine";
  }
  part entries:Stage {
    attribute :>> ordinal=6;
    ref part :>> owner=GambitRevisionDelivery::entryRoots;
    attribute :>> id="entries"; attribute :>> title="Generated entry and acquired-effect exit custody";
    attribute :>> status="PLANNED_BOUNDED_CALLERS";
    attribute :>> scope="Root before marker/conversion allocation, writer permits, callback origin, nonlocal escape and exactly matched physical cleanup for selected real callers";
    attribute :>> retire="Parallel native_scope naming and manual entry/root/cleanup authority only after every selected consumer migrates";
    attribute :>> validation="Both run origins, actual SFUN/CFUN generator paths, nested callbacks and exceptional/nonlocal cleanup with moving roots; official embedding/FFI tests";
    attribute :>> benefit="Generated contracts cover hidden collecting calls and acquired effects, preserving C portability";
    attribute :>> excluded="Do not fold every Tcl/service redesign into a root or startup REV; unknown native writes retain explicit restrictions";
    attribute :>> modelDuty="Existing host-root/unwind models retain distinct protocol and acquired-effect duties; source caller completeness and native execution cannot be replaced by model references";
  }
  part retirement:Stage {
    attribute :>> ordinal=7;
    ref part :>> owner=GambitRevisionDelivery::vmMembership;
    attribute :>> id="retirement"; attribute :>> title="Participant removal and resource-specific retirement";
    attribute :>> status="PLANNED";
    attribute :>> scope="Execution exit, GC participation, native return, pending work and final resource reclamation have separate completion owners; unknown join isolates one VM while healthy VM still collects";
    attribute :>> retire="Global reclaim inferred from one VM, ignored join status and destructive reset of still-owned state";
    attribute :>> validation="Actual partial creation/join failure/unknown result, late callbacks/producers, repeated setup/cleanup and healthy-VM GC; no forced zero counters";
    attribute :>> benefit="Failures preserve one legal custodian without making all VM GC depend on an unresolved owner";
    attribute :>> excluded="No safe takeover without physical writer closure/stop evidence; quarantine is not successful reclamation";
    attribute :>> modelDuty="Reuse existing retirement/unknown-outcome protocols and separate conditional ownership accounting laws; native stop/join and callback affinity need their own observations";
  }
  part generations:Stage {
    attribute :>> ordinal=8;
    ref part :>> owner=GambitRevisionDelivery::runtime;
    attribute :>> id="generations"; attribute :>> title="Generational allocation and remembered roots";
    attribute :>> status="RESEARCH_AFTER_FOUNDATION";
    attribute :>> scope="Young allocation, promotion reserve, noncollecting barriers, continuation/denv/FFI remembered writes and a sound major/fallback path";
    attribute :>> retire="Repeated mature graph traversal only for writer-complete admitted classes";
    attribute :>> validation="Promotion/overflow/failure/epoch handoff, true writers and multi-shot shared frames; saved scanning versus barrier, copying and peak costs on one producer";
    attribute :>> benefit="Skip proven unchanged mature work while preserving shared Scheme semantics";
    attribute :>> excluded="Copying is not generational collection. No OCaml algorithm copy or assumed speedup; a later algorithm invalidates affected acceptance";
    attribute :>> modelDuty="Existing generational QNT owns store/epoch/failure histories; conditional root/packing laws remain distinct from actual writer census";
  }
  part qualification:Stage {
    attribute :>> ordinal=9;
    ref part :>> owner=GambitRevisionDelivery::testInventory;
    attribute :>> id="qualification"; attribute :>> title="Same-source whole-runtime acceptance";
    attribute :>> status="BLOCKED";
    attribute :>> scope="Bind complete branch-specific GSI/GSC, additional PR, stress, registry, rollback, GC/FFI, Gerbil and release-cost inventories to the final selected source/profile/limits";
    attribute :>> retire="Cross-credit from old repair images, a focused PBT suite or one local REV";
    attribute :>> validation="All required actual cases/markers, original populations, natural exits and same-producer receipts; remote CI separately observed";
    attribute :>> benefit="A reproducible whole-runtime decision instead of a misleading local-REV numerator";
    attribute :>> excluded="repair8/12 is not this branch. Generational changes require new affected qualification even after an earlier stable SMP baseline";
    attribute :>> modelDuty="SysML routes scope/needs to ASCENT; QNT/Lean retain their algorithm-specific duties and cannot certify native performance or missing inventories";
  }
  part headerStage:Stage {
    attribute :>> ordinal=10; attribute :>> lane="engineering";
    ref part :>> owner=GambitRevisionDelivery::headerSource;
    attribute :>> id="headers"; attribute :>> title="Public headers and explicit layout contracts";
    attribute :>> status="PARTIAL_EVIDENCE";
    attribute :>> scope="Lossless ordered gambit.h modules and actual PSTATE/FrameSpec/ModuleSpec consumers; preserve public C names and bind every layout reader to its generating contract";
    attribute :>> retire="Monolithic header emission and independent numeric layout authority only after each real consumer migrates";
    attribute :>> validation="Byte-equivalent header assembly where mechanical,290 layout assertions and old-module refusal where semantic, low-level backend offsets and original bootstrap/consumers on one source";
    attribute :>> benefit="One auditable layout/namespace authority and smaller maintenance boundaries; no preprocessing speedup assumed";
    attribute :>> excluded="Existing execution-context layout REVs do not qualify all44 pending header paths or a whole FrameSpec/ModuleSpec redesign";
    attribute :>> modelDuty="Native SysML maps actual layout writers/readers and ABI premises; existing source-equivalence/layout laws and C assertions have distinct scopes";
  }
  part toolchain:Stage {
    attribute :>> ordinal=11; attribute :>> lane="engineering";
    ref part :>> owner=GambitRevisionDelivery::c23Support;
    attribute :>> id="toolchain"; attribute :>> title="C23 and Darwin toolchain/configuration refinement";
    attribute :>> status="PARTIAL_EVIDENCE";
    attribute :>> scope="Mandatory C23 baseline, actual compiler capabilities, existing configure/Make mode and argv equivalence, Darwin macro costs and environment-resolved tools";
    attribute :>> retire="Repeated string reinterpretation, implicit dialect/tool assumptions and redundant work only after exact source/configuration equivalence";
    attribute :>> validation="Existing Bazel profile, current compiler/flags, actual compile/link modes and independent negative controls; separate platform/configuration and performance evidence";
    attribute :>> benefit="Explicit supported native contract with preserved C portability; remove only measured/redundant Darwin work";
    attribute :>> excluded="Darwin/GCC C23 evidence does not qualify every compiler/platform or establish a preprocessing speedup; no new profile/executor or forced upstream name changes";
    attribute :>> modelDuty="Existing configuration/argv models own decoding/equivalence obligations; source mappings and actual toolchain acceptance remain separate";
  }
  part buildGraph:Stage {
    attribute :>> ordinal=12; attribute :>> lane="engineering";
    ref part :>> owner=GambitRevisionDelivery::buildResources;
    attribute :>> id="build-graph"; attribute :>> title="Incremental build and generated-artifact ownership";
    attribute :>> status="PARTIAL_EVIDENCE";
    attribute :>> scope="Scheme generation, native compilation and linking have separate dependency/identity cuts; one persistent task workspace, bounded parallel Make and exact source/configuration/tool/cwd/runtime reuse";
    attribute :>> retire="Per-run source clones, unnecessary reconfigure/regeneration/compilation and nested processor multiplication only where the corresponding identities are unchanged";
    attribute :>> validation="Two no-change builds, C-only change/restoration, macro/dependency invalidation, complete bootstrap within600 seconds, prior seed custody and actual generated/distribution cohort equality";
    attribute :>> benefit="Avoid actual repeated work rather than cache an unchecked claim; preserve existing Bazel/configure/Make ownership";
    attribute :>> excluded="A successful focused reuse or source bootstrap does not qualify every incremental/dynamic-dependency route or a mixed generated distribution cohort";
    attribute :>> modelDuty="Existing incremental QNT owns invalidation/snapshot schedules; existing Lean owns distinct dependency/encoding laws; source/native refinement and measured phase cost remain necessary";
  }
  part assurance:Stage {
    attribute :>> ordinal=13; attribute :>> lane="engineering";
    ref part :>> owner=GambitRevisionDelivery::ci;
    attribute :>> id="assurance"; attribute :>> title="CI, model/evidence and per-REV audit chain";
    attribute :>> status="PARTIAL_EVIDENCE";
    attribute :>> scope="SysML drives ASCENT, typed domain PBT executes real implementation with replay/shrink, and each bounded REV binds source/profile, tests, learning, process, models/questions and reviewed commit comment";
    attribute :>> retire="File-association-only closure, duplicate QNT/Lean duties, unbound evidence and parallel test/configuration frameworks; reuse official tests and names";
    attribute :>> validation="Actual five gates/21 rejection controls per REV, model/native/CI separation, exact-head vendor GitHub actions and full manifest case execution; no changed timeout/heap or hidden failure";
    attribute :>> benefit="User can audit every responsibility replacement and remaining boundary; negative controls reject missing/stale proof packets";
    attribute :>> excluded="Local admission and earlier remote CI do not establish current-head CI or whole SMP acceptance. LLM is the ambient reviewer, not a proof oracle";
    attribute :>> modelDuty="One native SysML source, concrete ASCENT DSL and exact receipts; QNT competing histories, Lean distinct conditional laws, native tests implementation behavior and CI actual remote portability";
  }
  // Separate equal-weight SMP acceptance taxonomy, not refactoring ordinals.
  part def AcceptanceFamily {
    attribute ordinal:Integer; attribute id:String;
    attribute evidenceKind:String; attribute criterion:String;
  }
  part a1:AcceptanceFamily { attribute :>> ordinal=1; attribute :>> id="bootstrap"; attribute :>> evidenceKind="complete-source-producer"; attribute :>> criterion="Two complete phase1--4 source bootstrap passes plus stock core, exact source/configuration/tool/artifact cohort and unchanged600-second producer budget"; }
  part a2:AcceptanceFamily { attribute :>> ordinal=2; attribute :>> id="gsi"; attribute :>> evidenceKind="complete-original-gsi"; attribute :>> criterion="Every current non-stress upstream unit in the source manifest interpreted by the same producer, original assertions, natural completion and unchanged domain limits"; }
  part a3:AcceptanceFamily { attribute :>> ordinal=3; attribute :>> id="gsc"; attribute :>> evidenceKind="complete-original-gsc"; attribute :>> criterion="Compile and execute every current upstream unit with actual original assertions and natural completion; focused Make/C fixtures are insufficient"; }
  part a4:AcceptanceFamily { attribute :>> ordinal=4; attribute :>> id="pr-gsi"; attribute :>> evidenceKind="complete-pr-gsi"; attribute :>> criterion="Complete declared additional PR-regression interpreted manifest on the current producer"; }
  part a5:AcceptanceFamily { attribute :>> ordinal=5; attribute :>> id="pr-gsc"; attribute :>> evidenceKind="complete-pr-gsc"; attribute :>> criterion="Complete declared additional PR-regression compiled manifest on the current producer"; }
  part a6:AcceptanceFamily { attribute :>> ordinal=6; attribute :>> id="stress-gsi"; attribute :>> evidenceKind="complete-stress-gsi"; attribute :>> criterion="Unchanged full original interpreted stress populations and assertions, real progress attribution and natural exits"; }
  part a7:AcceptanceFamily { attribute :>> ordinal=7; attribute :>> id="stress-gsc"; attribute :>> evidenceKind="complete-stress-gsc"; attribute :>> criterion="Unchanged full original compiled stress populations and assertions, real progress attribution and natural exits"; }
  part a8:AcceptanceFamily { attribute :>> ordinal=8; attribute :>> id="registry"; attribute :>> evidenceKind="complete-registry-lifetime"; attribute :>> criterion="Composed current-source shared-registry resize/reuse/readers/retirement manifest; a local root/interner/view leaf does not close it"; }
  part a9:AcceptanceFamily { attribute :>> ordinal=9; attribute :>> id="lifecycle"; attribute :>> evidenceKind="complete-lifecycle-faults"; attribute :>> criterion="Complete constructor/partial-create/rollback/retry/join-failure and unknown-result custody manifest, with healthy-VM progress where required"; }
  part a10:AcceptanceFamily { attribute :>> ordinal=10; attribute :>> id="gc-ffi"; attribute :>> evidenceKind="complete-gc-ffi"; attribute :>> criterion="Complete current-source GC/FFI inventory and writer/root/lifetime composition; original test7/test8/test9 and local PBT alone are insufficient"; }
  part a11:AcceptanceFamily { attribute :>> ordinal=11; attribute :>> id="gerbil"; attribute :>> evidenceKind="complete-gerbil-correctness"; attribute :>> criterion="Complete Gerbil build and correctness manifest consuming the exact current native producer"; }
  part a12:AcceptanceFamily { attribute :>> ordinal=12; attribute :>> id="release"; attribute :>> evidenceKind="complete-release-cost"; attribute :>> criterion="Matched full latency/throughput/peak and downstream build populations on one source with unchanged negative controls and resource gates"; }
  part def AcceptanceHold { ref part family:AcceptanceFamily; attribute tree:String; attribute profile:String; attribute reason:String; attribute evidence:String; }
  part def AcceptanceRun {
    attribute tree:String; attribute profile:String;
    attribute bootstrapEvidence:String; attribute gsiEvidence:String; attribute gscEvidence:String;
  }
  part cfgPlacementRun:AcceptanceRun {
    attribute :>> tree="8490662c5f312bf6df0bbffda085401ee0687e49";
    attribute :>> profile="884fa4a48e7550e2e9e1ddc62ec575927b37a5d81716d45d4a5684731d6b7f69";
    attribute :>> bootstrapEvidence="evidence/research/retained/modern-c/frozen-568e0276-smp/cfg-placement-bootstrap.json";
    attribute :>> gsiEvidence="evidence/research/retained/modern-c/frozen-568e0276-smp/cfg-placement-gsi.json";
    attribute :>> gscEvidence="evidence/research/retained/modern-c/frozen-568e0276-smp/cfg-placement-gsc.json";
  }
  part dominantHostRun:AcceptanceRun {
    attribute :>> tree="106d9cc24c7f9f9f9194014970da24d27706fad2";
    attribute :>> profile="884fa4a48e7550e2e9e1ddc62ec575927b37a5d81716d45d4a5684731d6b7f69";
    attribute :>> bootstrapEvidence="evidence/research/retained/modern-c/frozen-568e0276-smp/dominant-host-bootstrap.json";
    attribute :>> gsiEvidence="evidence/research/retained/modern-c/frozen-568e0276-smp/dominant-host-gsi.json";
    attribute :>> gscEvidence="evidence/research/retained/modern-c/frozen-568e0276-smp/dominant-host-gsc.json";
  }
  part dominantHostCapacityWindow:AcceptanceRun {
    attribute :>> tree="106d9cc24c7f9f9f9194014970da24d27706fad2";
    attribute :>> profile="884fa4a48e7550e2e9e1ddc62ec575927b37a5d81716d45d4a5684731d6b7f69";
    attribute :>> bootstrapEvidence="evidence/research/retained/modern-c/frozen-568e0276-smp/dominant-host-bootstrap.json";
    attribute :>> gsiEvidence="evidence/research/retained/modern-c/frozen-568e0276-smp/dominant-host-gsi.json";
    attribute :>> gscEvidence="evidence/research/retained/modern-c/frozen-568e0276-smp/dominant-host-gsc-capacity-window.json";
  }
  part dominantHostFamilyWindow:AcceptanceRun {
    attribute :>> tree="106d9cc24c7f9f9f9194014970da24d27706fad2";
    attribute :>> profile="884fa4a48e7550e2e9e1ddc62ec575927b37a5d81716d45d4a5684731d6b7f69";
    attribute :>> bootstrapEvidence="evidence/research/retained/modern-c/frozen-568e0276-smp/dominant-host-bootstrap.json";
    attribute :>> gsiEvidence="evidence/research/retained/modern-c/frozen-568e0276-smp/dominant-host-gsi.json";
    attribute :>> gscEvidence="evidence/research/retained/modern-c/frozen-568e0276-smp/dominant-host-gsc-family-window.json";
  }
  part dominantHostWeightedWindow:AcceptanceRun {
    attribute :>> tree="106d9cc24c7f9f9f9194014970da24d27706fad2";
    attribute :>> profile="884fa4a48e7550e2e9e1ddc62ec575927b37a5d81716d45d4a5684731d6b7f69";
    attribute :>> bootstrapEvidence="evidence/research/retained/modern-c/frozen-568e0276-smp/dominant-host-bootstrap.json";
    attribute :>> gsiEvidence="evidence/research/retained/modern-c/frozen-568e0276-smp/dominant-host-gsi.json";
    attribute :>> gscEvidence="evidence/research/retained/modern-c/frozen-568e0276-smp/dominant-host-gsc-weighted-window.json";
  }
  part sharedProcedureDispatchRun:AcceptanceRun {
    attribute :>> tree="65a4a2e265ef337239b09088486a2684bafa7362";
    attribute :>> profile="884fa4a48e7550e2e9e1ddc62ec575927b37a5d81716d45d4a5684731d6b7f69";
    attribute :>> bootstrapEvidence="evidence/research/retained/modern-c/frozen-568e0276-smp/shared-procedure-dispatch-bootstrap.json";
    attribute :>> gsiEvidence="evidence/research/retained/modern-c/frozen-568e0276-smp/shared-procedure-dispatch-gsi.json";
    attribute :>> gscEvidence="evidence/research/retained/modern-c/frozen-568e0276-smp/shared-procedure-dispatch-gsc.json";
  }
  part sharedProcedureDispatchRebalancedRun:AcceptanceRun {
    attribute :>> tree="65a4a2e265ef337239b09088486a2684bafa7362";
    attribute :>> profile="884fa4a48e7550e2e9e1ddc62ec575927b37a5d81716d45d4a5684731d6b7f69";
    attribute :>> bootstrapEvidence="evidence/research/retained/modern-c/frozen-568e0276-smp/shared-procedure-dispatch-bootstrap.json";
    attribute :>> gsiEvidence="evidence/research/retained/modern-c/frozen-568e0276-smp/shared-procedure-dispatch-gsi.json";
    attribute :>> gscEvidence="evidence/research/retained/modern-c/frozen-568e0276-smp/shared-procedure-dispatch-rebalanced-gsc.json";
  }
  part sharedProcedureDispatchPackedRun:AcceptanceRun {
    attribute :>> tree="65a4a2e265ef337239b09088486a2684bafa7362";
    attribute :>> profile="884fa4a48e7550e2e9e1ddc62ec575927b37a5d81716d45d4a5684731d6b7f69";
    attribute :>> bootstrapEvidence="evidence/research/retained/modern-c/frozen-568e0276-smp/shared-procedure-dispatch-bootstrap.json";
    attribute :>> gsiEvidence="evidence/research/retained/modern-c/frozen-568e0276-smp/shared-procedure-dispatch-gsi.json";
    attribute :>> gscEvidence="evidence/research/retained/modern-c/frozen-568e0276-smp/shared-procedure-dispatch-packed-gsc.json";
    attribute numericSupplyEvidence:String="evidence/research/retained/modern-c/frozen-568e0276-smp/shared-procedure-dispatch-numeric-supply-comparison.json";
  }
  part sharedProcedureDispatchWindowRun:AcceptanceRun {
    attribute :>> tree="65a4a2e265ef337239b09088486a2684bafa7362";
    attribute :>> profile="884fa4a48e7550e2e9e1ddc62ec575927b37a5d81716d45d4a5684731d6b7f69";
    attribute :>> bootstrapEvidence="evidence/research/retained/modern-c/frozen-568e0276-smp/shared-procedure-dispatch-bootstrap.json";
    attribute :>> gsiEvidence="evidence/research/retained/modern-c/frozen-568e0276-smp/shared-procedure-dispatch-gsi.json";
    attribute :>> gscEvidence="evidence/research/retained/modern-c/frozen-568e0276-smp/shared-procedure-dispatch-window-gsc.json";
    attribute ordinaryTailEvidence:String="evidence/research/retained/modern-c/frozen-568e0276-smp/shared-procedure-dispatch-window-tail-census.json";
    attribute assertionHelperEvidence:String="evidence/research/retained/modern-c/frozen-568e0276-smp/shared-assertion-helper-native-comparison.json";
    attribute assertionHelperUnresolvedPairs:String="evidence/research/retained/modern-c/frozen-568e0276-smp/shared-assertion-helper-unresolved-pairs.json";
    attribute assertionRuntimeEvidence:String="evidence/research/retained/modern-c/frozen-568e0276-smp/assertion-runtime-sharing.json";
    attribute assertionRuntimeCompositionEvidence:String="evidence/research/retained/modern-c/frozen-568e0276-smp/assertion-runtime-composition.json";
    attribute assertionRuntimeCampaignEvidence:String="evidence/research/retained/modern-c/frozen-568e0276-smp/assertion-runtime-gsc.json";
    attribute assertionRuntimePolicy:String="Fixture owns failure state, exit installation and late tested-procs access. The provider owns shared code and creates a fresh captured exit closure when each fixture calls its installer. Preserve the continuation-creator identity in call-thunk. Retain the failed direct-global access probe. The original numeric harness remains outside this provider overlay. Five-slot AB/BA costs permit one original campaign with build and actual loads charged, preserving the earlier timing variability. Only complete natural exits of all 408 cases close GSC.";
    attribute assertionHelperBudgetPolicy:String="Charge the one-time build and each real provider load. Scoped semantic parity or a scoped net gain cannot supply a complete GSC receipt. Require a credible fit under the original whole deadline before scheduling the full campaign.";
    attribute assertionBuildCompositionEvidence:String="evidence/research/retained/modern-c/frozen-568e0276-smp/shared-assertion-gambuild-composition.json";
    attribute safepointTailEvidence:String="evidence/research/retained/modern-c/frozen-568e0276-smp/shared-safepoint-tail-composition.json";
    attribute generatedHostIpaEvidence:String="evidence/research/retained/modern-c/frozen-568e0276-smp/generated-host-ipa-attribution.json";
    attribute originalEmissionCensusEvidence:String="evidence/research/retained/modern-c/frozen-568e0276-smp/original-gsc-emission-census.json";
  }
  part sharedAssertionRuntimeRun:AcceptanceRun {
    attribute :>> tree="65a4a2e265ef337239b09088486a2684bafa7362";
    attribute :>> profile="884fa4a48e7550e2e9e1ddc62ec575927b37a5d81716d45d4a5684731d6b7f69";
    attribute :>> bootstrapEvidence="evidence/research/retained/modern-c/frozen-568e0276-smp/shared-procedure-dispatch-bootstrap.json";
    attribute :>> gsiEvidence="evidence/research/retained/modern-c/frozen-568e0276-smp/shared-procedure-dispatch-gsi.json";
    attribute :>> gscEvidence="evidence/research/retained/modern-c/frozen-568e0276-smp/assertion-runtime-framework-gsc.json";
    attribute firstCompleteCampaign:String="evidence/research/retained/modern-c/frozen-568e0276-smp/assertion-runtime-gsc.json";
    attribute acceptedModelSnapshot:String="evidence/research/retained/modern-c/frozen-568e0276-smp/assertion-runtime-model-inputs.json";
    attribute implementation:String="src/gambit_smp/assertion_runtime.py";
    attribute policy:String="Original fixture assertions, original numeric harness and file cap90, shared whole deadline295, five fixed workers, one provider build and actual per-fixture loads. Typed request declares the numeric driver input and disjoint group/file budgets. Numeric may run after the ordinary group that releases its slot. Source views restore only after actual process settlement.";
  }
  part indexedProcedureLabelsRun:AcceptanceRun {
    attribute :>> tree="bb19c9c696f6b50b709483646ce19357a0312f4b";
    attribute :>> profile="884fa4a48e7550e2e9e1ddc62ec575927b37a5d81716d45d4a5684731d6b7f69";
    attribute :>> bootstrapEvidence="evidence/research/retained/modern-c/frozen-568e0276-smp/indexed-procedure-labels-bootstrap.json";
    attribute :>> gsiEvidence="evidence/research/retained/modern-c/frozen-568e0276-smp/indexed-procedure-labels-gsi.json";
    attribute :>> gscEvidence="evidence/research/retained/modern-c/frozen-568e0276-smp/indexed-procedure-labels-gsc.json";
  }
  part indexedProcedureLabelsCapacityRun:AcceptanceRun {
    attribute :>> tree="bb19c9c696f6b50b709483646ce19357a0312f4b";
    attribute :>> profile="884fa4a48e7550e2e9e1ddc62ec575927b37a5d81716d45d4a5684731d6b7f69";
    attribute :>> bootstrapEvidence="evidence/research/retained/modern-c/frozen-568e0276-smp/indexed-procedure-labels-bootstrap.json";
    attribute :>> gsiEvidence="evidence/research/retained/modern-c/frozen-568e0276-smp/indexed-procedure-labels-gsi.json";
    attribute :>> gscEvidence="evidence/research/retained/modern-c/frozen-568e0276-smp/indexed-procedure-labels-gsc-capacity.json";
  }
  part indexedProcedureLabelsRecoveryRun:AcceptanceRun {
    attribute :>> tree="bb19c9c696f6b50b709483646ce19357a0312f4b";
    attribute :>> profile="884fa4a48e7550e2e9e1ddc62ec575927b37a5d81716d45d4a5684731d6b7f69";
    attribute :>> bootstrapEvidence="evidence/research/retained/modern-c/frozen-568e0276-smp/indexed-procedure-labels-bootstrap.json";
    attribute :>> gsiEvidence="evidence/research/retained/modern-c/frozen-568e0276-smp/indexed-procedure-labels-gsi.json";
    attribute :>> gscEvidence="evidence/research/retained/modern-c/frozen-568e0276-smp/indexed-procedure-labels-gsc-recovery-window.json";
    attribute capacityReplayEvidence:String="evidence/research/retained/modern-c/frozen-568e0276-smp/gsc-recovery-window-capacity-replay.json";
    attribute predecessorActivationEvidence:String="evidence/research/retained/modern-c/frozen-568e0276-smp/shared-procedure-dispatch-same-cache-activation.json";
  }
  part restoredOpaqueGscHold:AcceptanceHold {
    ref part :>> family=a3;
    attribute :>> tree="d1466a0d341853df6c2d3556a1e31c265539e811";
    attribute :>> profile="884fa4a48e7550e2e9e1ddc62ec575927b37a5d81716d45d4a5684731d6b7f69";
    attribute :>> reason="Exact producer restored. The shared-input campaign selected all408 original cases. The numeric group passed within90 seconds. Five ordinary groups timed out within the original300-second campaign, leaving169 cases unresolved after239 observed passes. Opt-in indexed placement reduced native compilation cost in scoped controls. The ca_dr assertions remain unexecuted in its scoped30-second indexed attempt. The scoped controls supply no additional family credit.";
    attribute :>> evidence="evidence/research/retained/modern-c/frozen-568e0276-smp/opaque-gsc-shared-campaign.json";
  }
  part originalThreadHold:AcceptanceHold {
    ref part :>> family=a2;
    attribute :>> tree="626c9f19d86060d4ad7e48785c50c4a59c9cdd2b";
    attribute :>> profile="884fa4a48e7550e2e9e1ddc62ec575927b37a5d81716d45d4a5684731d6b7f69";
    attribute :>> reason="Carried through043a9341 despite the latest paired baseline/candidate408/408 passes. Earlier baseline and candidate thread_interrupt.scm:41 HI70/LO0 failures remain failed. The thirteen-field source-disjoint baseline boundary qualifies only3.5.2.4; it neither retires scheduler/interrupt ownership nor changes whole-family acceptance. New/related or unclassified failures still block source admission.";
    attribute :>> evidence="evidence/research/retained/modern-c/tcl-callback/scoped-receipt.json";
  }
  part frozenIssue216Hold:AcceptanceHold {
    ref part :>> family=a2;
    attribute :>> tree="30ce83fcd546febe6eb425e04697c9339c59bf29";
    attribute :>> profile="884fa4a48e7550e2e9e1ddc62ec575927b37a5d81716d45d4a5684731d6b7f69";
    attribute :>> reason="Matched historical test11 completed the 408-case inventory with 407 passes and one failure: issue_216.scm line 37, inactive target, HI=70 LO=0. The older thread_interrupt.scm failure did not recur in this observation.";
    attribute :>> evidence="evidence/research/retained/modern-c/frozen-568e0276-smp/gsi-blocker.json";
  }
  part frozenCompiledHold:AcceptanceHold {
    ref part :>> family=a3;
    attribute :>> tree="30ce83fcd546febe6eb425e04697c9339c59bf29";
    attribute :>> profile="884fa4a48e7550e2e9e1ddc62ec575927b37a5d81716d45d4a5684731d6b7f69";
    attribute :>> reason="Matched original compiled suite reproduces the historical fxmul.scm line 30 assertion failure. The isolated numeric group is censored under its unchanged 90-second cap.";
    attribute :>> evidence="evidence/research/retained/modern-c/frozen-568e0276-smp/gsc-blockers.json";
  }
  part plannerBootstrapHold:AcceptanceHold {
    ref part :>> family=a1;
    attribute :>> tree="55f594055f012e7385e7b78448da1f9b612324e0";
    attribute :>> profile="884fa4a48e7550e2e9e1ddc62ec575927b37a5d81716d45d4a5684731d6b7f69";
    attribute :>> reason="The exact candidate's 600-second run stopped in second-pass phase three. Supervisor teardown reaped the registered groups. No terminal native producer receipt or stock core invocation exists.";
    attribute :>> evidence="evidence/research/retained/modern-c/frozen-568e0276-smp/block-owner-planner-bootstrap-timeout.json";
  }
  part interPassNativeObject {
    ref part acceptanceFamily=a1;
    attribute producer:String="Both original Scheme-to-C passes remain mandatory. Only a completed native action may supply an object to the next pass.";
    attribute identity:String="Bind object bytes, exact argv, cwd, compiler and subordinate tools, effective profile, resolved input contents and volatile preprocessor or assembler inputs. GCC dependency discovery supplies include evidence; it does not certify every possible tool read.";
    attribute failure:String="An invoked compiler may leave a zero-length or partial object. No natural success receipt, input drift or unknown termination refuses handoff. Rebuild only through the original Make owner.";
    attribute evidence:String="evidence/research/retained/modern-c/frozen-568e0276-smp/block-owner-planner-native-object-census.json";
    attribute handoffEvidence:String="evidence/research/retained/modern-c/frozen-568e0276-smp/block-owner-planner-native-object-handoff.json";
    attribute handoffStatus:String="A leased single-object control reached the actual Make archive consumer with 25 identical ordered object members. The same Make target also treated the interrupted empty object as up to date. Completion custody is separate from Make freshness; integration before second-pass native compilation is open.";
    attribute pilotEvidence:String="evidence/research/retained/modern-c/frozen-568e0276-smp/block-owner-planner-interpass-timeout.json";
    attribute pilotStatus:String="The phased pilot restored the numeric object before second-pass native compilation. It exhausted the whole 600-second budget with second-pass phase three still unobserved. The stricter before/after input check is locally tested; exact native admission remains open.";
    attribute nativeReuseAdmitted:Boolean=false;
  }
  part plannerGsiHold:AcceptanceHold {
    ref part :>> family=a2;
    attribute :>> tree="55f594055f012e7385e7b78448da1f9b612324e0";
    attribute :>> profile="884fa4a48e7550e2e9e1ddc62ec575927b37a5d81716d45d4a5684731d6b7f69";
    attribute :>> reason="The original GSI family did not start because the exact candidate producer did not complete.";
    attribute :>> evidence="evidence/research/retained/modern-c/frozen-568e0276-smp/block-owner-planner-bootstrap-timeout.json";
  }
  part plannerNumericHold:AcceptanceHold {
    ref part :>> family=a3;
    attribute :>> tree="55f594055f012e7385e7b78448da1f9b612324e0";
    attribute :>> profile="884fa4a48e7550e2e9e1ddc62ec575927b37a5d81716d45d4a5684731d6b7f69";
    attribute :>> reason="A sequential numeric control generated identical C and identical ordered original-form manifests. The candidate native phase reached the shared 90-second deadline before the original assertion execution. No whole GSC result or positive cost claim follows.";
    attribute :>> evidence="evidence/research/retained/modern-c/frozen-568e0276-smp/block-owner-planner-numeric-pair.json";
  }
  part charsetBootstrapHold:AcceptanceHold {
    ref part :>> family=a1;
    attribute :>> tree="70a0bf1b3e86cb8b5cbd9b6dd49765a6dba16a58";
    attribute :>> profile="884fa4a48e7550e2e9e1ddc62ec575927b37a5d81716d45d4a5684731d6b7f69";
    attribute :>> reason="The char-set type split emits byte-identical _system C and installs all eight character module inputs. The bounded _std control reached Parsing and exhausted its deadline before Compiling. The complete two-pass and stock-core producer remains open.";
    attribute :>> evidence="evidence/research/retained/modern-c/frozen-568e0276-smp/system-charset-std-install.json";
  }
  part charsetGsiHold:AcceptanceHold {
    ref part :>> family=a2;
    attribute :>> tree="70a0bf1b3e86cb8b5cbd9b6dd49765a6dba16a58";
    attribute :>> profile="884fa4a48e7550e2e9e1ddc62ec575927b37a5d81716d45d4a5684731d6b7f69";
    attribute :>> reason="The full original GSI inventory has no exact producer for this candidate.";
    attribute :>> evidence="evidence/research/retained/modern-c/frozen-568e0276-smp/system-charset-generation.json";
  }
  part charsetGscHold:AcceptanceHold {
    ref part :>> family=a3;
    attribute :>> tree="70a0bf1b3e86cb8b5cbd9b6dd49765a6dba16a58";
    attribute :>> profile="884fa4a48e7550e2e9e1ddc62ec575927b37a5d81716d45d4a5684731d6b7f69";
    attribute :>> reason="The _system generation control grants no numeric or original GSC family admission for this candidate.";
    attribute :>> evidence="evidence/research/retained/modern-c/frozen-568e0276-smp/system-charset-generation.json";
  }
  part indexedEnvBootstrapHold:AcceptanceHold {
    ref part :>> family=a1;
    attribute :>> tree="9d96c8791cfdb3e511a49a92df21374be45181a5";
    attribute :>> profile="884fa4a48e7550e2e9e1ddc62ec575927b37a5d81716d45d4a5684731d6b7f69";
    attribute :>> reason="Bounded diagnostic generation timed out in parsing. The observed Unicode expander consumed CPU before any stock-core binding; the probe supplies no two-pass producer.";
    attribute :>> evidence="evidence/research/retained/modern-c/frozen-568e0276-smp/std-phase-observation.json";
  }
  part indexedEnvGsiHold:AcceptanceHold {
    ref part :>> family=a2;
    attribute :>> tree="9d96c8791cfdb3e511a49a92df21374be45181a5";
    attribute :>> profile="884fa4a48e7550e2e9e1ddc62ec575927b37a5d81716d45d4a5684731d6b7f69";
    attribute :>> reason="No original 408-case GSI result is bound to an admitted producer of this tree.";
    attribute :>> evidence="evidence/research/retained/modern-c/frozen-568e0276-smp/env-index-control.json";
  }
  part indexedEnvGscHold:AcceptanceHold {
    ref part :>> family=a3;
    attribute :>> tree="9d96c8791cfdb3e511a49a92df21374be45181a5";
    attribute :>> profile="884fa4a48e7550e2e9e1ddc62ec575927b37a5d81716d45d4a5684731d6b7f69";
    attribute :>> reason="The compiler relink and standard-library generation controls do not exercise the full original GSC inventory or its numeric execution.";
    attribute :>> evidence="evidence/research/retained/modern-c/frozen-568e0276-smp/env-index-control.json";
  }
  part def Dependency { ref part predecessor:Stage; ref part successor:Stage; attribute kind:String; }
  part def Closure {
    ref part stage:Stage;
    attribute id:String; attribute factor:String; attribute replacement:String;
    attribute premise:String; attribute falsifier:String; attribute acceptance:String;
    attribute saving:String; attribute overhead:String; attribute closureStatus:String;
  }
  part foundationClosure:Closure {
    ref part :>> stage=startup; attribute :>> id="foundation";
    attribute :>> factor="Repair-line test8/test9 pass is reference evidence; modern-c must own correct embedding startup and original GC/dynamic-module consumers";
    attribute :>> replacement="Rooted request, complete physical grants, initialized/created slots and single member commit replace incidental allocation and count-before-create";
    attribute :>> premise="Every origin root survives GC; grants are disjoint actual intervals; abort refunds only known joined actors";
    attribute :>> falsifier="One unrooted losing resize request, overlapping pair, child entering after ABORT, or successful membership without a real child";
    attribute :>> acceptance="Unchanged official test8 and test9 on the selected source/profile; root reload, partial create, metadata failure, unknown join and rollback controls";
    attribute :>> saving="Remove repeated per-slot sufficiency guesses and fatal partial startup; no claimed repair9 throughput gain";
    attribute :>> overhead="One bounded VM ledger/gate plus traced request/child cells and derived physical resume allowance";
    attribute :>> closureStatus="PUBLISHED_SCOPED_FF44E8F8; TEST8_TEST9_AND_EARLY_ROOT_DRAIN; NO_WHOLE_CREDIT";
  }
  part rootClosure:Closure {
    ref part :>> stage=roots; attribute :>> id="roots";
    attribute :>> factor="Independent globals extent retired7abe; native interning/GC anchor authority retired92d; callback-held intrusive fold traversal retired da5651af; two raw getter escape sites/four in-tree intrusive readers retired ae19f986. External default-build disposition is scoped closed; remaining writers and complete lifetimes still prevent a total moving-root census";
    attribute :>> replacement="Published common globals snapshot, native canonical service/GC anchor handoff, managed fold and owned getters/all in-tree direct consumers; locked external source admission complete; complete writer migration and RootOrigin/RootTask source/lifetime union still required";
    attribute :>> premise="Complete producer/writer/alias census, stable revision independent of GC address, write closure and post-GC reload";
    attribute :>> falsifier="A legal writer or borrowed cell omitted from census, different shard counts, relocation treated as logical mutation, or duplicate scan ownership";
    attribute :>> acceptance="Keep ae19f986322-action view/getter/multi-shot/GC histories, actual old getter/fold13-to1 controls and consumer AST execution; retain92d interner and7abe prefix/capacity controls. Add external private-reader disposition, remaining nonzero/value-writer/failed-transfer histories on exact C";
    attribute :>> saving="One source census and unique task responsibility; avoid redundant scans only where source uniqueness is proved";
    attribute :>> overhead="Previous globals/interner costs remain. symkey-getters-result.org: each getter replaces O(1) alias with O(bucket+N) capture and N managed words/header, plus retry/retained-view storage and ordinary GC scanning.6301 identities/64bit means50408 payload bytes, not physical peak. Zero new mutex/native buffer/manual root; contention and whole-round peak unmeasured";
    attribute :>> closureStatus="FOUR_SCOPED_ROOT_GROUPS_CLOSED_TWO_REMAIN; EXACT_GERBIL_SOURCE_ADMISSION_ONLY; TOTAL_WRITERS_AND_LIFETIME_CENSUS_OPEN";
  }
  part workerClosure:Closure {
    ref part :>> stage=workers; attribute :>> id="workers";
    attribute :>> factor="Execution-carrier identity currently couples GC root ownership, private copy/scan work and restoration space";
    attribute :>> replacement="W WorkerArenas consume R RootTasks; unique copy/Tail custody and separate R restoration grants replace carrier-index inference";
    attribute :>> premise="Complete pre-copy source/frame bound, contiguous placement and all hidden producers/claimed chunks covered through close";
    attribute :>> falsifier="Forwarding visible without initialized-copy custodian, missed Tail/claimed chunk, lost CAS grant or one unrestored context when W<R";
    attribute :>> acceptance="Actual W<R and W=R histories, multi-shot map/GC, native capacity/failure controls and original stress with unchanged resource limits";
    attribute :>> saving="No duplicate destination reservation, independent collector scheduling and less unnecessary worker participation when justified";
    attribute :>> overhead="Explicit work records, physical packing/restore planning and synchronization; no assumed speedup";
    attribute :>> closureStatus="DESIGN_AND_PROTOTYPES; COMPLETE_REPLACEMENT_OPEN";
  }
  part serviceClosure:Closure {
    ref part :>> stage=scheduling; attribute :>> id="service";
    attribute :>> factor="Repair9 crosses request ownership, target lifetime, wait/service control, continuation retention and collective GC; focused reply success does not establish original-load capacity";
    attribute :>> replacement="One publish/claim/execute/result-or-abandon owner chain, durable runnable/park handshake, waiting-state roots separate from request service activation";
    attribute :>> premise="Exactly-once invocation/outcome under supported migration and nonlocal control; unchanged multi-shot Scheme continuation and dynamic-wind semantics";
    attribute :>> falsifier="Inactive target acknowledged as serviced, lost runnable notification, double execution/result, control suffix omitted, or stable backlog with growing retained graph";
    attribute :>> acceptance="Real request/migration/interrupt/GC PBT and shrink; original interpreted and compiled stress with per-target counts, natural exits and source-bound cost attribution";
    attribute :>> saving="Retire duplicate routing and unnecessary private capture/materialization only where present in modern-c; preserve user captures";
    attribute :>> overhead="Authoritative request/outcome state and queue synchronization; accepted backlog still consumes real memory and service";
    attribute :>> closureStatus="FOUNDATION_DEPENDENT; FULL_REPAIR9_NOT_CLOSED";
  }
  part exitClosure:Closure {
    ref part :>> stage=retirement; attribute :>> id="exit";
    attribute :>> factor="A zero counter, native return or failed join is not proof that roots, callbacks and descendant cleanup have no remaining user";
    attribute :>> replacement="Per-resource completion/last-user custody and VM-local unknown isolation replace monolithic destructive cleanup";
    attribute :>> premise="Physical writer closure, known actor identity, all resource readers/producers and owner-affine effects discharged or transferred";
    attribute :>> falsifier="Late callback writes reclaimed state, cleanup waits on its own GC participant, unknown join storage reused, or unrelated healthy VM cannot collect";
    attribute :>> acceptance="Actual late callback/partial failure/unknown join, healthy-VM GC, repeated setup/cleanup and original lifecycle inventory";
    attribute :>> saving="Remove global failure coupling and retention without a resource owner; successful reclamation still requires real reconciliation";
    attribute :>> overhead="Resource custody records, delayed release and bounded-admission refusal; unknown retention is not a memory saving";
    attribute :>> closureStatus="ROOT_LEAVES_ONLY; COMPOSED_EXIT_OPEN";
  }
  part wholeClosure:Closure {
    ref part :>> stage=qualification; attribute :>> id="whole";
    attribute :>> factor="Repair9 label, official test9 and ordinal acceptance9 are different identities; old8/12 and local REVs cannot be added";
    attribute :>> replacement="One final source/profile/inventory/limit identity composes architecture contracts and all actual acceptance receipts";
    attribute :>> premise="All applicable source refinements closed, mandatory native cases natural-complete, failures retained, release evidence matched";
    attribute :>> falsifier="Any stale generated/header/native product, omitted mandatory test, changed population/cap, unresolved lifecycle error or performance regression";
    attribute :>> acceptance="Twelve existing named families: complete GSI/GSC/PR/stress, registry, faults, GC/FFI, Gerbil and release; remote CI observed separately";
    attribute :>> saving="Reproducible claims, precise reuse and auditable incremental progress; no invented speedup or9-12 guarantee";
    attribute :>> overhead="Real whole-inventory and matched cost qualification after each affected architectural change";
    attribute :>> closureStatus="OPEN; NO_MODERN_C_NUMERATOR";
  }
  part d0:Dependency { ref part :>> predecessor=inventory; ref part :>> successor=startup; attribute :>> kind="review-before-selection"; }
  part d1:Dependency { ref part :>> predecessor=startup; ref part :>> successor=roots; attribute :>> kind="current-delivery-priority"; }
  part d2:Dependency { ref part :>> predecessor=startup; ref part :>> successor=workers; attribute :>> kind="resource-contract"; }
  part d3:Dependency { ref part :>> predecessor=roots; ref part :>> successor=workers; attribute :>> kind="frozen-population-contract"; }
  part d4:Dependency { ref part :>> predecessor=roots; ref part :>> successor=scheduling; attribute :>> kind="moving-root-contract"; }
  part d5:Dependency { ref part :>> predecessor=startup; ref part :>> successor=scheduling; attribute :>> kind="current-delivery-priority"; }
  part d6:Dependency { ref part :>> predecessor=roots; ref part :>> successor=entries; attribute :>> kind="root-lifetime-contract"; }
  part d7:Dependency { ref part :>> predecessor=workers; ref part :>> successor=retirement; attribute :>> kind="private-work-last-user"; }
  part d8:Dependency { ref part :>> predecessor=scheduling; ref part :>> successor=retirement; attribute :>> kind="request-last-user"; }
  part d9:Dependency { ref part :>> predecessor=entries; ref part :>> successor=retirement; attribute :>> kind="native-last-user"; }
  part d10:Dependency { ref part :>> predecessor=workers; ref part :>> successor=generations; attribute :>> kind="physical-copy-contract"; }
  part d11:Dependency { ref part :>> predecessor=entries; ref part :>> successor=generations; attribute :>> kind="writer-coverage-contract"; }
  part d12:Dependency { ref part :>> predecessor=retirement; ref part :>> successor=qualification; attribute :>> kind="whole-runtime-lifecycle"; }
  part d13:Dependency { ref part :>> predecessor=scheduling; ref part :>> successor=qualification; attribute :>> kind="whole-runtime-control"; }
  part d14:Dependency { ref part :>> predecessor=headerStage; ref part :>> successor=qualification; attribute :>> kind="actual-layout-consumer-closure"; }
  part d15:Dependency { ref part :>> predecessor=toolchain; ref part :>> successor=qualification; attribute :>> kind="supported-native-configuration"; }
  part d16:Dependency { ref part :>> predecessor=buildGraph; ref part :>> successor=qualification; attribute :>> kind="exact-generated-producer-identity"; }
  part d17:Dependency { ref part :>> predecessor=assurance; ref part :>> successor=qualification; attribute :>> kind="source-bound-whole-manifest-and-CI"; }
  part def ChangeGroup {
    ref part owner:GambitRevisionDelivery::Revision;
    attribute id:String; attribute patterns:String; attribute disposition:String;
  }
  part generated:ChangeGroup { ref part :>> owner=GambitRevisionDelivery::generatedProducts; attribute :>> id="generated"; attribute :>> patterns="gsc/_*.c;gsi/_*.c;lib/_*.c"; attribute :>> disposition="Producer-derived output; bind generating Scheme/features/compiler and affected ABI before selecting. Never hand-edit or bulk publish mixed profiles."; }
  part headers:ChangeGroup { ref part :>> owner=GambitRevisionDelivery::headerSource; attribute :>> id="headers"; attribute :>> patterns="include/*"; attribute :>> disposition="Separate byte-preserving header extraction from context/worker/layout semantics and C23 admission. Any ABI-changing hunk needs all real layout consumers in one buildable cut."; }
  part build:ChangeGroup { ref part :>> owner=GambitRevisionDelivery::build; attribute :>> id="build"; attribute :>> patterns="bin/makefile.in;configure.ac;gsc/igsc.scm;gsc/makefile.in;gsi/makefile.in;lib/makefile.in;makefile.in;tests/run-unit-tests.scm"; attribute :>> disposition="Support current required source closure using existing Bazel/configure/Make; keep unrelated cleanup, phase and frontend tuning parked. Do not introduce another profile/executor."; }
  part membership:ChangeGroup { ref part :>> owner=GambitRevisionDelivery::vmMembership; attribute :>> id="membership"; attribute :>> patterns="lib/setup.c;lib/_setup/*"; attribute :>> disposition="Select startup preparation/publication subset first; broader registry/cleanup/unknown join stays a separate later responsibility. A path includes multiple cuts."; }
  part collector:ChangeGroup { ref part :>> owner=GambitRevisionDelivery::workerMemory; attribute :>> id="collector"; attribute :>> patterns="lib/_mem/*;lib/root.h;lib/mem.c;lib/mem.h"; attribute :>> disposition="Separate source-coordinate noise, root census, startup grants, copy ownership and independent arenas. Existing unqualified prototype is not a tested successor."; }
  part entryChanges:ChangeGroup { ref part :>> owner=GambitRevisionDelivery::entryRoots; attribute :>> id="entries"; attribute :>> patterns="lib/c_intf.c;lib/c_intf.h;lib/native_scope.c;lib/native_scope.h;lib/write_authority.c;lib/write_authority.h;lib/os_dyn.c;lib/os_setup.c;lib/_kernel.scm;lib/_system.scm;lib/_num.scm;examples/tcltk/tcltk.scm;examples/tcltk/command.h"; attribute :>> disposition="Distinguish writer-authority rename from semantic entry/root/exception changes. Only startup-required entry effects belong in the next cut; broad CFFI/Tcl remains separate."; }
  part scheduleChanges:ChangeGroup { ref part :>> owner=GambitRevisionDelivery::publication; attribute :>> id="scheduling"; attribute :>> patterns="lib/_thread.scm;lib/_fifo#.scm;lib/_io.scm;lib/os_thread.c"; attribute :>> disposition="Published mutex cut is not these remaining hunks. Separate FIFO/mailbox/atomic publication from future wait/service architecture and measure real source costs first."; }
  part testChanges:ChangeGroup { ref part :>> owner=GambitRevisionDelivery::testInventory; attribute :>> id="tests"; attribute :>> patterns="tests/frame*;tests/root-task.scm;tests/gc-root-task.c;tests/makefile.in;tests/native-scope.c;tests/ordered-sync.c;tests/rc-root-origin.scm;tests/runtime-roles.c;tests/sfun-exit.scm;tests/smp/*;tests/write-authority.c"; attribute :>> disposition="Tests accompany their actual implementation owner; preserve official cases and failure evidence. Index deletion plus same-name untracked file requires explicit custody, not bulk staging."; }
  part ciChanges:ChangeGroup { ref part :>> owner=GambitRevisionDelivery::ci; attribute :>> id="ci"; attribute :>> patterns=".github/workflows/smp.yml"; attribute :>> disposition="Gambit repository only; publish after required implementation/source distribution and actual tests qualify. Preserve official Build/Test commands and remote-state distinction."; }
}
