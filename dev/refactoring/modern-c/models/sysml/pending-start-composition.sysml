package GambitPendingStartComposition { private import ScalarValues::*;
part def Route { attribute key:String; attribute sourcePath:String; attribute needle:String; attribute obligation:String; }
part route0:Route { attribute :>> key="real-root-consumer"; attribute :>> sourcePath="vendor/gambit/lib/mem.c"; attribute :>> needle="mark_execution_roots (work,"; attribute :>> obligation="Insert frozen pending-provider scan before strong reachability closure; no fake context"; }
part route1:Route { attribute :>> key="slot-relocation"; attribute :>> sourcePath="vendor/gambit/lib/mem.c"; attribute :>> needle="mark_array (work, &h->data, 1);"; attribute :>> obligation="Use same updateable-slot marking primitive with VM-owned startup storage"; }
part route2:Route { attribute :>> key="frozen-origin"; attribute :>> sourcePath="vendor/gambit/lib/mem.c"; attribute :>> needle="participant->context = ___ps->context;"; attribute :>> obligation="Freeze execution providers and startup directory as one manifest publication"; }
part route3:Route { attribute :>> key="strong-closure"; attribute :>> sourcePath="vendor/gambit/lib/mem.c"; attribute :>> needle="mark_reachable_from_marked (work);"; attribute :>> obligation="Pending roots must be introduced before termination of strong marking"; }
part route4:Route { attribute :>> key="old-worker-drain"; attribute :>> sourcePath="vendor/gambit/lib/mem.c"; attribute :>> needle="BARRIER(); /* no worker may retain a stopped root view past this cut */"; attribute :>> obligation="Adoption source release and rollback wait until old views drain"; }
part route5:Route { attribute :>> key="current-context-scan"; attribute :>> sourcePath="vendor/gambit/lib/mem.c"; attribute :>> needle="mark_rc (work, context);"; attribute :>> obligation="Context scan origin is distinct from worker copy-space ownership"; }
part route6:Route { attribute :>> key="published-count"; attribute :>> sourcePath="vendor/gambit/lib/setup.c"; attribute :>> needle="sop.op = OP_SET_PROCESSOR_COUNT;"; attribute :>> obligation="Existing resize publishes barrier membership before all OS launches succeed"; }
part route7:Route { attribute :>> key="batch-launch-loop"; attribute :>> sourcePath="vendor/gambit/lib/setup.c"; attribute :>> needle="t->start_fn = start_processor_execution;"; attribute :>> obligation="Each member needs separate root launch readiness and failure record"; }
part route8:Route { attribute :>> key="fatal-create-failure"; attribute :>> sourcePath="vendor/gambit/lib/setup.c"; attribute :>> needle="static char *msgs[] = { \"Could not create OS thread\", NULL };"; attribute :>> obligation="Current fatal path is not a partial failure rollback protocol"; }
part route9:Route { attribute :>> key="ignored-join-result"; attribute :>> sourcePath="vendor/gambit/lib/setup.c"; attribute :>> needle="___thread_join (t); /* ignore error */"; attribute :>> obligation="Unknown stop/join cannot authorize freeing another live member"; }
part route10:Route { attribute :>> key="context-cleanup"; attribute :>> sourcePath="vendor/gambit/lib/setup.c"; attribute :>> needle="___EXP_FUNC(void,___cleanup_pstate)"; attribute :>> obligation="Context retirement must await adopted provider and worker-view leases"; }
part route11:Route { attribute :>> key="exact-startup-model"; attribute :>> sourcePath="dev/refactoring/modern-c/models/quint/thread_thunk_root.qnt"; attribute :>> needle="action enterFromHandle="; attribute :>> obligation="Bind composition projection to actual predecessor guard and update expression"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule4; ref part :>> counterpart=GambitRuntimeComposition::blueprintModule3; attribute :>> key="pending-gc-consumer"; attribute :>> owner="collector/roots"; attribute :>> actionName="registerA freeze finishScan"; attribute :>> invariant="Frozen startup slots are marked before strong closure by existing workers"; attribute :>> gap="Root adapter is proposed; actual pending directory and mark_array source bridge open"; }
part contract1:Contract { ref part :>> accountable=GambitRuntimeComposition::blueprintModule3; ref part :>> counterpart=GambitRuntimeComposition::blueprintModule2; attribute :>> key="context-adoption"; attribute :>> owner="roots/execution"; attribute :>> actionName="readyA adoptA"; attribute :>> invariant="Same canonical root changes pending owner to ready context only in running phase"; attribute :>> gap="Qualified context membership and readiness receipt is still an environment premise"; }
part contract2:Contract { ref part :>> accountable=GambitRuntimeComposition::blueprintModule4; ref part :>> counterpart=GambitRuntimeComposition::blueprintModule7; attribute :>> key="frozen-lifetimes"; attribute :>> owner="collector/release"; attribute :>> actionName="borrowScan restore releaseSourceA"; attribute :>> invariant="Immutable captured provider owners and source roots persist until worker-view drain"; attribute :>> gap="C11 publication and final physical storage reclamation remain open"; }
part contract3:Contract { ref part :>> accountable=GambitRuntimeComposition::blueprintModule5; ref part :>> counterpart=GambitRuntimeComposition::blueprintModule7; attribute :>> key="partial-batch-custody"; attribute :>> owner="control/release"; attribute :>> actionName="rejectB settleFailureB rollbackB"; attribute :>> invariant="Known uncreated member rollback never clears accepted member A"; attribute :>> gap="Created or unknown members require independent stop and delivery receipts"; }
part contract4:Contract { ref part :>> accountable=GambitRuntimeComposition::blueprintModule0; ref part :>> counterpart=GambitRuntimeComposition::blueprintModule3; attribute :>> key="composed-projections"; attribute :>> owner="semantic/roots"; attribute :>> actionName="adoptA enterFromHandle"; attribute :>> invariant="Adoption stutters root projection and commutes with actual startup entry step"; attribute :>> gap="Selected refinement square is proved; full all-action simulation is not"; }
part contract5:Contract { ref part :>> accountable=GambitRuntimeComposition::blueprintModule8; ref part :>> counterpart=GambitRuntimeComposition::blueprintModule5; attribute :>> key="source-bound-assurance"; attribute :>> owner="build/control"; attribute :>> actionName="registerA adoptA rollbackB"; attribute :>> invariant="Actual guards and composition certificates must be present at admission"; attribute :>> gap="Parser extraction C11 and full runtime source relation stay blocked"; }
part def Obligation { attribute key:String; attribute status:String; attribute scope:String; attribute counterexample:String; }
part obligation0:Obligation { attribute :>> key="joint-history"; attribute :>> status="bounded-checked"; attribute :>> scope="Two-member batch and two frozen rounds with pending-to-context ownership"; attribute :>> counterexample="Rollback of uncreated B cannot clear live A; frozen adoption invalidates captured view"; }
part obligation1:Obligation { attribute :>> key="startup-action"; attribute :>> status="conditional-proved"; attribute :>> scope="Actual predecessor enterFromHandle guard and update plus explicit startup projection"; attribute :>> counterexample="Projection does not prove GC value relocation epochs or arbitrary startup histories"; }
part obligation2:Obligation { attribute :>> key="root-adoption"; attribute :>> status="conditional-proved"; attribute :>> scope="Legal adoption preserves root projection and coverage"; attribute :>> counterexample="Ready context and canonical slot identity are supplied premises"; }
part obligation3:Obligation { attribute :>> key="partial-locality"; attribute :>> status="conditional-proved"; attribute :>> scope="Rollback B preserves A root and launch fields"; attribute :>> counterexample="No whole-batch cancellation termination or join proof"; }
part obligation4:Obligation { attribute :>> key="actual-expressions"; attribute :>> status="conditional-proved"; attribute :>> scope="Three composed action meanings and one predecessor startup action meaning"; attribute :>> counterexample="Parser and restricted emitter remain trusted"; }
part obligation5:Obligation { attribute :>> key="runtime-c11"; attribute :>> status="open"; attribute :>> scope="Real pending root adapter assignment ready cohort C11 publication and physical retirement"; attribute :>> counterexample="Current PSTATE cleanup and fatal create do not implement the proposed protocol"; }
part obligation6:Obligation { attribute :>> key="json-domain"; attribute :>> status="partially-proved"; attribute :>> scope="91-row finite reference environment plus two typed model inputs"; attribute :>> counterexample="Full source-root-map and parser extraction remain open"; }
part def Gain { attribute key:String; attribute avoided:String; attribute added:String; attribute condition:String; }
part gain0:Gain { attribute :>> key="canonical-root-adoption"; attribute :>> avoided="Repeated root copy and double scan during pending-to-context ownership change"; attribute :>> added="Stable slot identity owner metadata frozen manifests and exact adoption receipt"; attribute :>> condition="One physical slot has one scanner; embedded context slot copy needs a different proof"; }
part gain1:Gain { attribute :>> key="reuse-marker"; attribute :>> avoided="Second independent moving root tracer for startup records"; attribute :>> added="Typed provider adapter feeding current mark_array and strong closure"; attribute :>> condition="All admitted providers captured before scan; no untracked late source"; }
part gain2:Gain { attribute :>> key="member-local-rollback"; attribute :>> avoided="Retaining uncreated B record solely because A is still running"; attribute :>> added="Per-member launch outcome failure-delivery and scan-drain accounting"; attribute :>> condition="Only known uncreated settled member can retire independently"; }
part gain3:Gain { attribute :>> key="manifest-partition"; attribute :>> avoided="A mandatory new GC worker or full rescan for each pending start"; attribute :>> added="O(P*A) root visits partitioned over existing W workers and immutable directory snapshot"; attribute :>> condition="Slot partition is disjoint complete and bounded to retained manifest; load balance unproved"; }
part gain4:Gain { attribute :>> key="modern-c-composition"; attribute :>> avoided="Second-language ABI and runtime implementation are not necessary here"; attribute :>> added="Generated typed requests root maps custody and composition proofs in modern C"; attribute :>> condition="Zig needs independently demonstrated additional benefit"; }
part def Binding { attribute key:String; attribute qntAction:String; attribute leanLemma:String; attribute refinement:String; attribute guardLemma:String; attribute updateLemma:String; }
part binding0:Binding { attribute :>> key="guard"; attribute :>> qntAction="registerA"; attribute :>> leanLemma="frozenBlocksRegistration"; attribute :>> refinement="Actual selected joint-model expression meaning; runtime relation open"; attribute :>> guardLemma="registerAGuardMeaning"; attribute :>> updateLemma="registerANextMeaning"; }
part binding1:Binding { attribute :>> key="roots"; attribute :>> qntAction="adoptA"; attribute :>> leanLemma="notReadyRejectsAdoption"; attribute :>> refinement="Actual selected joint-model expression meaning; runtime relation open"; attribute :>> guardLemma="adoptAGuardMeaning"; attribute :>> updateLemma="adoptANextMeaning"; }
part binding2:Binding { attribute :>> key="release"; attribute :>> qntAction="rollbackB"; attribute :>> leanLemma="liveChildRejectsRollback"; attribute :>> refinement="Actual selected joint-model expression meaning; runtime relation open"; attribute :>> guardLemma="rollbackBGuardMeaning"; attribute :>> updateLemma="rollbackBNextMeaning"; }
part def Flow { attribute fromNode:String; attribute toNode:String; attribute reason:String; }
part flow0:Flow { attribute :>> fromNode="c0"; attribute :>> toNode="c2"; attribute :>> reason="Freeze startup slots before root enumeration"; }
part flow1:Flow { attribute :>> fromNode="c2"; attribute :>> toNode="c1"; attribute :>> reason="Old views drain before adoption"; }
part flow2:Flow { attribute :>> fromNode="c1"; attribute :>> toNode="c4"; attribute :>> reason="Adoption has explicit projection square"; }
part flow3:Flow { attribute :>> fromNode="c3"; attribute :>> toNode="c4"; attribute :>> reason="Member rollback preserves unrelated root projection"; }
part flow4:Flow { attribute :>> fromNode="c0"; attribute :>> toNode="o0"; attribute :>> reason="One joint root and startup history"; }
part flow5:Flow { attribute :>> fromNode="c1"; attribute :>> toNode="o2"; attribute :>> reason="Root projection is unchanged"; }
part flow6:Flow { attribute :>> fromNode="c4"; attribute :>> toNode="o1"; attribute :>> reason="Actual old startup action certificate"; }
part flow7:Flow { attribute :>> fromNode="c3"; attribute :>> toNode="o3"; attribute :>> reason="Rollback B leaves A live"; }
part flow8:Flow { attribute :>> fromNode="c5"; attribute :>> toNode="o4"; attribute :>> reason="Actual selected action meanings"; }
part flow9:Flow { attribute :>> fromNode="c5"; attribute :>> toNode="o6"; attribute :>> reason="Finite reference and expression inputs"; }
part flow10:Flow { attribute :>> fromNode="c2"; attribute :>> toNode="o5"; attribute :>> reason="Actual C11 old-view and source-release cut"; }
part flow11:Flow { attribute :>> fromNode="c3"; attribute :>> toNode="o5"; attribute :>> reason="Batch stop join and whole-cohort policy open"; }
part history:GambitAssuranceRouting::ModelNeed { ref part :>> owner=GambitBuildAssurance::planner.component; attribute :>> obligationId="PC-H"; attribute :>> kind="interleaving"; attribute :>> subjectPath="dev/refactoring/modern-c/models/quint/pending_start_composition.qnt"; attribute :>> subjectScope="Joint two-member startup and frozen manifest ownership histories"; attribute :>> premise="Bounded models and restricted algebra only; no runtime implementation or native acceptance"; }
part shards:GambitAssuranceRouting::ModelNeed { ref part :>> owner=GambitBuildAssurance::planner.component; attribute :>> obligationId="PC-B"; attribute :>> kind="interleaving"; attribute :>> subjectPath="dev/refactoring/modern-c/models/quint/thread_thunk_root.qnt"; attribute :>> subjectScope="Predecessor thread_thunk_root model and exact enterFromHandle expression input"; attribute :>> premise="Bounded models and restricted algebra only; no runtime implementation or native acceptance"; }
part induction:GambitAssuranceRouting::ModelNeed { ref part :>> owner=GambitBuildAssurance::planner.component; attribute :>> obligationId="PC-I"; attribute :>> kind="induction"; attribute :>> subjectPath="dev/refactoring/modern-c/models/lean/PendingStartComposition.lean"; attribute :>> subjectScope="Root stutter startup commuting square rollback locality and guard exclusions"; attribute :>> premise="Bounded models and restricted algebra only; no runtime implementation or native acceptance"; }
part expression:GambitAssuranceRouting::ModelNeed { ref part :>> owner=GambitBuildAssurance::planner.component; attribute :>> obligationId="PC-X"; attribute :>> kind="induction"; attribute :>> subjectPath="dev/refactoring/modern-c/models/lean/PendingStartAst.lean"; attribute :>> subjectScope="Actual joint registerA adoptA rollbackB plus finite JSON reference environment"; attribute :>> premise="Bounded models and restricted algebra only; no runtime implementation or native acceptance"; }
part source:GambitAssuranceRouting::ModelNeed { ref part :>> owner=GambitBuildAssurance::planner.component; attribute :>> obligationId="PC-S"; attribute :>> kind="source-refinement"; attribute :>> subjectPath="dev/refactoring/modern-c/pending-start-composition-design.org"; attribute :>> subjectScope="GC pending consumer canonical slot context readiness partial failure closure OPEN"; attribute :>> premise="Bounded models and restricted algebra only; no runtime implementation or native acceptance"; }
part platform:GambitAssuranceRouting::ModelNeed { ref part :>> owner=GambitBuildAssurance::planner.component; attribute :>> obligationId="PC-E"; attribute :>> kind="environment-refinement"; attribute :>> subjectPath="dev/refactoring/modern-c/pending-start-composition-design.org"; attribute :>> subjectScope="C11 freeze publication slot assignment and final scan/stop retirement OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitThreadThunkFrozenRoots::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; attribute sourcePath:String; attribute needle:String; }
part endorsement0:Endorsement { attribute :>> roleName="semantic"; attribute :>> scope="Canonical root identity persists across pending to context adoption"; attribute :>> issuer="Execution/root adapter owner"; attribute :>> sourcePath="vendor/gambit/lib/mem.c"; attribute :>> needle="mark_execution_roots (work,"; }
part endorsement1:Endorsement { attribute :>> roleName="foreign"; attribute :>> scope="Every created or unknown batch member retains independent custody"; attribute :>> issuer="Batch thread lifecycle owner"; attribute :>> sourcePath="vendor/gambit/lib/setup.c"; attribute :>> needle="static char *msgs[] = { \"Could not create OS thread\", NULL };"; }
part endorsement2:Endorsement { attribute :>> roleName="resident"; attribute :>> scope="Frozen startup directory descriptor and scan leases survive until all workers drain"; attribute :>> issuer="VM root and GC coordinator"; attribute :>> sourcePath="vendor/gambit/lib/mem.c"; attribute :>> needle="BARRIER(); /* no worker may retain a stopped root view past this cut */"; }
part flow12:Flow { attribute :>> fromNode="c4"; attribute :>> toNode="c5"; attribute :>> reason="Composition receipts participate in admission"; }
part flow13:Flow { attribute :>> fromNode="o4"; attribute :>> toNode="o5"; attribute :>> reason="Expression certificates do not prove runtime integration"; }
part flow14:Flow { attribute :>> fromNode="c0"; attribute :>> toNode="o5"; attribute :>> reason="Mark-array adapter still requires source implementation proof"; }
part flow15:Flow { attribute :>> fromNode="c4"; attribute :>> toNode="o2"; attribute :>> reason="No root ownership gap at selected step"; }
part def Composition { attribute key:String; attribute lemma:String; attribute certificate:String; }
part composition0:Composition { attribute :>> key="root-stutter"; attribute :>> lemma="adoptionRootStutters"; attribute :>> certificate="adoptANextMeaning"; }
part composition1:Composition { attribute :>> key="startup-square"; attribute :>> lemma="adoptionStartupCommutes"; attribute :>> certificate="enterFromHandleNextMeaning"; }
part composition2:Composition { attribute :>> key="startup-guard"; attribute :>> lemma="adoptionImpliesStartupGuard"; attribute :>> certificate="enterFromHandleGuardMeaning"; }
part composition3:Composition { attribute :>> key="batch-locality"; attribute :>> lemma="rollbackLeavesA"; attribute :>> certificate="rollbackBNextMeaning"; }
part startupExpression:GambitAssuranceRouting::ModelNeed { ref part :>> owner=GambitBuildAssurance::planner.component; attribute :>> obligationId="PC-Y"; attribute :>> kind="induction"; attribute :>> subjectPath="dev/refactoring/modern-c/models/lean/PendingStartupAst.lean"; attribute :>> subjectScope="Actual predecessor enterFromHandle guard and update certificate"; attribute :>> premise="Restricted JSON parser and emitter remain trusted; no full simulation"; }
part dependency6:GambitAssuranceRouting::NeedDependency { ref part :>> dependent=source; ref part :>> prerequisite=startupExpression; }
}
