package GambitFrameSealRootScope { private import ScalarValues::*;
part def SourceRow { attribute key:String; attribute path:String; attribute needle:String; attribute obligation:String; }
part source0:SourceRow { attribute :>> key="constructor"; attribute :>> path="vendor/gambit/gsc/_t-c-3.scm"; attribute :>> needle="(vector 'frame-spec kind fs actual-fs link gc-map out-of-line?)"; attribute :>> obligation="Fresh mutable vector; validation is not alias closure"; }
part source1:SourceRow { attribute :>> key="validation"; attribute :>> path="vendor/gambit/gsc/_t-c-3.scm"; attribute :>> needle="(< gc-map (expt 2 actual-fs))"; attribute :>> obligation="Revalidate exact kind size effective layout link and gc-map under frozen ABI"; }
part source2:SourceRow { attribute :>> key="chunks"; attribute :>> path="vendor/gambit/gsc/_t-c-3.scm"; attribute :>> needle="(targ-frame-spec-chunks spec)"; attribute :>> obligation="Emitter-time chunk generation also needs stable view"; }
part source3:SourceRow { attribute :>> key="return-wrappers"; attribute :>> path="vendor/gambit/gsc/_t-c-2.scm"; attribute :>> needle="(targ-make-frame-spec 'internal fs link gc-map)"; attribute :>> obligation="Three wrappers create normal task internal specs"; }
part source4:SourceRow { attribute :>> key="replace-class"; attribute :>> path="vendor/gambit/gsc/_t-c-2.scm"; attribute :>> needle="(vector-set! lbl-struct 2 class)"; attribute :>> obligation="Class and info writes are a logical pair, not atomic publish"; }
part source5:SourceRow { attribute :>> key="replace-payload"; attribute :>> path="vendor/gambit/gsc/_t-c-2.scm"; attribute :>> needle="(vector-set! lbl-struct 3 info)"; attribute :>> obligation="Replaces FrameSpec reference rather than mutating its scalar fields"; }
part source6:SourceRow { attribute :>> key="code-alias"; attribute :>> path="vendor/gambit/gsc/_t-c-2.scm"; attribute :>> needle="(targ-emit (cons 'label x))"; attribute :>> obligation="Code stream holds same canonical label as registry"; }
part source7:SourceRow { attribute :>> key="table-alias"; attribute :>> path="vendor/gambit/gsc/_t-c-2.scm"; attribute :>> needle="(queue-put! targ-proc-lbl-tbl (cons n y))"; attribute :>> obligation="Canonical label identity returned on repeated lookup"; }
part source8:SourceRow { attribute :>> key="order-alias"; attribute :>> path="vendor/gambit/gsc/_t-c-2.scm"; attribute :>> needle="(queue-put! targ-proc-lbl-tbl-ord lbl-struct)"; attribute :>> obligation="Ordered queue preserves label alias"; }
part source9:SourceRow { attribute :>> key="plan-alias"; attribute :>> path="vendor/gambit/gsc/_t-c-2.scm"; attribute :>> needle="(reverse val-lbls)"; attribute :>> obligation="Reversing list copies spine not label records"; }
part source10:SourceRow { attribute :>> key="plan-publish"; attribute :>> path="vendor/gambit/gsc/_t-c-2.scm"; attribute :>> needle="(set-car! p"; attribute :>> obligation="Procedure plan installed after scans but before goto numbering ends"; }
part source11:SourceRow { attribute :>> key="number-cell"; attribute :>> path="vendor/gambit/gsc/_t-c-2.scm"; attribute :>> needle="(targ-cell-set! (targ-lbl-num x) i)"; attribute :>> obligation="Seal must wait for loop3 goto numbering too"; }
part source12:SourceRow { attribute :>> key="ifd-reader"; attribute :>> path="vendor/gambit/gsc/_t-c-1.scm"; attribute :>> needle="(targ-frame-spec-stored-fs info)"; attribute :>> obligation="Descriptor pass reads mutable payload"; }
part source13:SourceRow { attribute :>> key="ofd-reader"; attribute :>> path="vendor/gambit/gsc/_t-c-1.scm"; attribute :>> needle="(targ-frame-spec-chunks info)"; attribute :>> obligation="OFD body pass must match count and IFD pass"; }
part source14:SourceRow { attribute :>> key="ofd-count"; attribute :>> path="vendor/gambit/gsc/_t-c-1.scm"; attribute :>> needle="(define (targ-get-ofd-count objs)"; attribute :>> obligation="Separate count traversal can disagree after mutation"; }
part source15:SourceRow { attribute :>> key="source-write"; attribute :>> path="vendor/gambit/lib/setup.c"; attribute :>> needle="source->thunk = thunk;"; attribute :>> obligation="Publish before any allocation callback safe point; reentry refused"; }
part source16:SourceRow { attribute :>> key="source-queue"; attribute :>> path="vendor/gambit/lib/setup.c"; attribute :>> needle="___RESIZE_SOURCE_WRITING, ___RESIZE_SOURCE_QUEUED"; attribute :>> obligation="Root publication precedes token enqueue"; }
part source17:SourceRow { attribute :>> key="token-check"; attribute :>> path="vendor/gambit/lib/setup.c"; attribute :>> needle="source->serial != token / ___MAX_PROCESSORS"; attribute :>> obligation="Serial and origin bind selected request"; }
part source18:SourceRow { attribute :>> key="reload"; attribute :>> path="vendor/gambit/lib/setup.c"; attribute :>> needle="(___ps, source->thunk, sop_ptr->arg[1]);"; attribute :>> obligation="Selected operation reloads GC-updated source slot"; }
part source19:SourceRow { attribute :>> key="ledger-publish"; attribute :>> path="vendor/gambit/lib/setup.c"; attribute :>> needle="r->thunk = thunk;"; attribute :>> obligation="Old participant barrier precedes possible GC"; }
part source20:SourceRow { attribute :>> key="ledger-clear"; attribute :>> path="vendor/gambit/lib/setup.c"; attribute :>> needle="r->thunk = ___FAL;"; attribute :>> obligation="Clear only outside retained phase; successor contexts can still own roots"; }
part source21:SourceRow { attribute :>> key="source-ack"; attribute :>> path="vendor/gambit/lib/setup.c"; attribute :>> needle="source->thunk = ___FAL;"; attribute :>> obligation="Only CONSUMED CAS winner clears then publishes IDLE"; }
part source22:SourceRow { attribute :>> key="source-unknown"; attribute :>> path="vendor/gambit/lib/setup.c"; attribute :>> needle="___RESIZE_SOURCE_QUEUED, ___RESIZE_SOURCE_RETAINED"; attribute :>> obligation="Unknown keeps thunk serial and exclusion of slot reuse"; }
part source23:SourceRow { attribute :>> key="root-scan"; attribute :>> path="vendor/gambit/lib/mem.c"; attribute :>> needle="mark_array (work, &___vms->resize_requests[i].thunk, 1);"; attribute :>> obligation="All MAX_PROCESSORS slots including retained absent origins"; }
part source24:SourceRow { attribute :>> key="ledger-scan"; attribute :>> path="vendor/gambit/lib/mem.c"; attribute :>> needle="mark_array (work, &___vms->resize.thunk, 1);"; attribute :>> obligation="Deduplicate transitive objects across ledger source and context aliases"; }
part source25:SourceRow { attribute :>> key="retire-guard"; attribute :>> path="vendor/gambit/lib/mem.c"; attribute :>> needle="No C stack or"; attribute :>> obligation="Current shrink refuses nonidle origin slot"; }
part source26:SourceRow { attribute :>> key="cleanup-guard"; attribute :>> path="vendor/gambit/lib/setup.c"; attribute :>> needle="return; /* source-root ownership outlives an interrupted C activation */"; attribute :>> obligation="Cleanup refusal is custody not a drain/liveness proof"; }
part source27:SourceRow { attribute :>> key="setup-root"; attribute :>> path="vendor/gambit/lib/setup.c"; attribute :>> needle="___vms->resize_requests[i].thunk = ___FAL;"; attribute :>> obligation="Exclusive pre-borrow setup; not an in-round writer"; }
part source28:SourceRow { attribute :>> key="serial"; attribute :>> path="vendor/gambit/include/gambit.h.in"; attribute :>> needle="___resize_request_root resize_requests[___MAX_PROCESSORS];"; attribute :>> obligation="VM-owned stable storage; generation/serial overflow must refuse reuse"; }
part source29:SourceRow { attribute :>> key="cas-family"; attribute :>> path="vendor/gambit/include/gambit.h.in"; attribute :>> needle="__sync_val_compare_and_swap(p,oldval,newval)"; attribute :>> obligation="Multiple macro backends; volatile alone establishes no C11 happens-before"; }
part source30:SourceRow { attribute :>> key="startup-publish"; attribute :>> path="vendor/gambit/lib/setup.c"; attribute :>> needle="ps->context->startup_thunk = r->thunk;"; attribute :>> obligation="Successor context keeps exact thunk before native start"; }
part source31:SourceRow { attribute :>> key="startup-scan"; attribute :>> path="vendor/gambit/lib/mem.c"; attribute :>> needle="mark_array (work, &context->startup_thunk, 1);"; attribute :>> obligation="Context root scanning must remain until successful downstream detach"; }
part def AliasRow { attribute key:String; attribute writer:String; attribute custody:String; attribute gap:String; }
part alias0:AliasRow { attribute :>> key="FrameSpec"; attribute :>> writer="constructor"; attribute :>> custody="fresh mutable vector; scalar exact integers and symbols"; attribute :>> gap="No named setter found in bounded target files; arbitrary vector/FFI escape unclosed"; }
part alias1:AliasRow { attribute :>> key="label.info"; attribute :>> writer="targ-add-label"; attribute :>> custody="class then info replacement"; attribute :>> gap="Owner excludes readers between paired writes"; }
part alias2:AliasRow { attribute :>> key="canonical-label"; attribute :>> writer="targ-get-lbl"; attribute :>> custody="table -> code stream -> ordered queue -> val-lbls"; attribute :>> gap="Copying list spine does not detach label vectors"; }
part alias3:AliasRow { attribute :>> key="procedure-plan"; attribute :>> writer="targ-scan-procedure"; attribute :>> custody="set-car! publishes vector of mutable code and labels"; attribute :>> gap="Wait for all numbering/resource/debug writes; whole generator reentry unqualified"; }
part alias4:AliasRow { attribute :>> key="number-cell"; attribute :>> writer="targ-cell-set!"; attribute :>> custody="label field0 mutable cell shared by generated code"; attribute :>> gap="Copy final resolved label identity or deep-copy cell with relocation map"; }
part alias5:AliasRow { attribute :>> key="emission-pass"; attribute :>> writer="targ-dump-prc / targ-get-ofd-count"; attribute :>> custody="count IFD OFD and chunks traverse repeatedly"; attribute :>> gap="All passes consume one private sealed plan identity"; }
part alias6:AliasRow { attribute :>> key="native-root"; attribute :>> writer="mark_array"; attribute :>> custody="collector updates source thunk and downstream slots"; attribute :>> gap="Freeze structural ownership, permit authorized relocation updates"; }
part alias7:AliasRow { attribute :>> key="module-users"; attribute :>> writer="closure/frame/continuation"; attribute :>> custody="transitive descriptor users can outlive public module entry"; attribute :>> gap="No executable old-descriptor pin closure proved"; }
part def ClaimRow { attribute key:String; attribute mechanism:String; attribute condition:String; attribute result:String; attribute gap:String; }
part claim0:ClaimRow { attribute :>> key="seal"; attribute :>> mechanism="Exclusive session -> close writers -> copy graph -> validate -> publish"; attribute :>> condition="All mutable aliases in code label cells target config and output hooks covered"; attribute :>> result="Later live-plan mutation leaves private snapshot unchanged in model"; attribute :>> gap="Full Scheme callback/FFI alias closure remains open"; }
part claim1:ClaimRow { attribute :>> key="B"; attribute :>> mechanism="Union of canonical physical source intervals reached by complete root domains"; attribute :>> condition="R includes all request slots ledger startup contexts and prior roots"; attribute :>> result="Delta B is incremental live object charge plus alignment and thresholds"; attribute :>> gap="Root slot count is not object bytes; root-completeness/source injection open"; }
part claim2:ClaimRow { attribute :>> key="old-modules"; attribute :>> mechanism="Descriptor leases follow all reachable procedures and captured frames"; attribute :>> condition="Transitive dependency union and generation retained through unknown transfer"; attribute :>> result="Only exact current profile can issue local G and B receipt"; attribute :>> gap="Loader unload and every continuation/FFI alias not closed"; }
part claim3:ClaimRow { attribute :>> key="receipt"; attribute :>> mechanism="Combine private producer summary with frozen root/source epoch"; attribute :>> condition="Complete producer caps source partition ABI and packing predicates"; attribute :>> result="Invalidate before copy; defer new activation during copy"; attribute :>> gap="Native complete gate and total fallback not implemented"; }
part claim4:ClaimRow { attribute :>> key="failure"; attribute :>> mechanism="Private failed candidate discarded; published unknown candidate retained"; attribute :>> condition="No source clear without consumed and downstream handoff receipt"; attribute :>> result="No unsafe free or untracked fallback after partial copy"; attribute :>> gap="Retained state is safe custody conditional on scanner, not eventual progress"; }
part def MemoryRow { attribute key:String; attribute publication:String; attribute consumer:String; attribute gap:String; }
part memory0:MemoryRow { attribute :>> key="root-publish"; attribute :>> publication="ordinary root write before release state; acquire before reading"; attribute :>> consumer="Writer and GC scanner must be mutually excluded by same frozen membership cut"; attribute :>> gap="C11 data-race proof and actual Darwin macro selection open"; }
part memory1:MemoryRow { attribute :>> key="scan-update"; attribute :>> publication="Scanner may rewrite root slot only with GC authority"; attribute :>> consumer="Resume/reload after collective acquire; raw C cached thunk cannot cross GC"; attribute :>> gap="All callers and generation close still source refinement"; }
part memory2:MemoryRow { attribute :>> key="seal"; attribute :>> publication="Private construction rooted before safepoints; release immutable handle"; attribute :>> consumer="Acquiring consumer sees one resolved plan across count/IFD/OFD/code"; attribute :>> gap="C11 publication does not itself root Scheme objects"; }
part memory3:MemoryRow { attribute :>> key="revoke"; attribute :>> publication="Serialize activation/revocation with issue/start epoch transition"; attribute :>> consumer="Once started use deferred queue; no free-space refund or tight plan replacement"; attribute :>> gap="CAS/version alone cannot repair a concurrent plain Scheme read"; }
part memory4:MemoryRow { attribute :>> key="retire"; attribute :>> publication="Close admissions and drain code/frame/maintenance/native users"; attribute :>> consumer="Release descriptor pin after acquire-observed final user and no queued roots"; attribute :>> gap="Hazard/epoch or refcount choice and ABA exhaustion qualification open"; }
part def GainRow { attribute key:String; attribute avoided:String; attribute added:String; attribute condition:String; }
part gain0:GainRow { attribute :>> key="descriptor-walks"; attribute :>> avoided="k redundant validation/count/summary walks over F labels -> one sealing walk; required code/IFD/OFD serialization remains"; attribute :>> added="O(F) private plan + identity relocation; source writer checks"; attribute :>> condition="Positive if saved repeated traversal exceeds seal/copy cost; not measured"; }
part gain1:GainRow { attribute :>> key="GC-source-budget"; attribute :>> avoided="Bnew = Bold + DeltaU + DeltaA + DeltaT"; attribute :>> added="Scan MAX_PROCESSORS request slots each GC; physical canonical dedup"; attribute :>> condition="DeltaU zero when all new roots alias already-counted objects; retained unique graph may increase B"; }
part gain2:GainRow { attribute :>> key="tight-packing"; attribute :>> avoided="K = P + floor(B / (C-G+1)) when 0<G<=C"; attribute :>> added="Module profile union old-descriptor leases and alternative-space reserve"; attribute :>> condition="No benefit if any producer cap missing or denominator near one"; }
part gain3:GainRow { attribute :>> key="module-summary"; attribute :>> avoided="Reuse size/root/ABI summaries across epochs and incremental builds"; attribute :>> added="Invalidate on generator profile layout code or producer coverage change"; attribute :>> condition="Retire repeated layout interpretation only after all native consumers migrate"; }
part gain4:GainRow { attribute :>> key="parallel-build"; attribute :>> avoided="Privatize label/code/target state for independent sessions"; attribute :>> added="Deep copy or rebuild mutable cells and provider closures; per-session output"; attribute :>> condition="FrameSpec sealing alone establishes neither compiler reentrancy nor speedup"; }
part gain5:GainRow { attribute :>> key="language-choice"; attribute :>> avoided="Modern C suffices for explicit root epochs and generated contracts"; attribute :>> added="Zig adds another code generator and ABI maintenance if introduced"; attribute :>> condition="No additional Zig net gain established by these mechanisms"; }
part def ContractRow { attribute fromNode:String; attribute toNode:String; attribute custody:String; }
part contract0:ContractRow { attribute :>> fromNode="Scheme-writers"; attribute :>> toNode="exclusive-seal"; attribute :>> custody="Close reentry aliases and stabilize ABI"; }
part contract1:ContractRow { attribute :>> fromNode="exclusive-seal"; attribute :>> toNode="private-plan"; attribute :>> custody="Copy label graph and resolve cells"; }
part contract2:ContractRow { attribute :>> fromNode="private-plan"; attribute :>> toNode="module-profile"; attribute :>> custody="One identity for code IFD OFD and G"; }
part contract3:ContractRow { attribute :>> fromNode="request-root-slots"; attribute :>> toNode="frozen-root-union"; attribute :>> custody="All VM origins; scanner updates authorized"; }
part contract4:ContractRow { attribute :>> fromNode="resize-ledger-and-contexts"; attribute :>> toNode="frozen-root-union"; attribute :>> custody="Successor custody remains after source ACK"; }
part contract5:ContractRow { attribute :>> fromNode="frozen-root-union"; attribute :>> toNode="canonical-source-B"; attribute :>> custody="Charge each physical object once"; }
part contract6:ContractRow { attribute :>> fromNode="frozen-root-union"; attribute :>> toNode="old-descriptor-leases"; attribute :>> custody="Transitive closure of closure and frame users"; }
part contract7:ContractRow { attribute :>> fromNode="old-descriptor-leases"; attribute :>> toNode="module-profile"; attribute :>> custody="Keep all still-live producer summaries"; }
part contract8:ContractRow { attribute :>> fromNode="module-profile"; attribute :>> toNode="capacity-receipt"; attribute :>> custody="Qualified global G and exact ABI"; }
part contract9:ContractRow { attribute :>> fromNode="canonical-source-B"; attribute :>> toNode="capacity-receipt"; attribute :>> custody="Frozen Q alignment threshold bound"; }
part contract10:ContractRow { attribute :>> fromNode="capacity-receipt"; attribute :>> toNode="start-or-alternative"; attribute :>> custody="Revoke before start; defer after start"; }
part contract11:ContractRow { attribute :>> fromNode="unknown-handoff"; attribute :>> toNode="retained-custody"; attribute :>> custody="Keep root and descriptor; refuse cleanup"; }
part def BindingRow { attribute actionName:String; attribute lemma:String; attribute scope:String; }
part binding0:BindingRow { attribute :>> actionName="frame_seal_root_scope.own"; attribute :>> lemma="FrameSealRoot.ownPreserves"; attribute :>> scope="Actual typed IR action; source semantics conditional"; }
part binding1:BindingRow { attribute :>> actionName="frame_seal_root_scope.mutateLive"; attribute :>> lemma="FrameSealRoot.mutateLivePreserves"; attribute :>> scope="Actual typed IR action; source semantics conditional"; }
part binding2:BindingRow { attribute :>> actionName="frame_seal_root_scope.seal"; attribute :>> lemma="FrameSealRoot.sealPreserves"; attribute :>> scope="Actual typed IR action; source semantics conditional"; }
part binding3:BindingRow { attribute :>> actionName="frame_seal_root_scope.beginRequest"; attribute :>> lemma="FrameSealRoot.beginRequestPreserves"; attribute :>> scope="Actual typed IR action; source semantics conditional"; }
part binding4:BindingRow { attribute :>> actionName="frame_seal_root_scope.publishRequest"; attribute :>> lemma="FrameSealRoot.publishRequestPreserves"; attribute :>> scope="Actual typed IR action; source semantics conditional"; }
part binding5:BindingRow { attribute :>> actionName="frame_seal_root_scope.selectRequest"; attribute :>> lemma="FrameSealRoot.selectRequestPreserves"; attribute :>> scope="Actual typed IR action; source semantics conditional"; }
part binding6:BindingRow { attribute :>> actionName="frame_seal_root_scope.unknownRequest"; attribute :>> lemma="FrameSealRoot.unknownRequestPreserves"; attribute :>> scope="Actual typed IR action; source semantics conditional"; }
part binding7:BindingRow { attribute :>> actionName="frame_seal_root_scope.completeRequest"; attribute :>> lemma="FrameSealRoot.completeRequestPreserves"; attribute :>> scope="Actual typed IR action; source semantics conditional"; }
part binding8:BindingRow { attribute :>> actionName="frame_seal_root_scope.ackSource"; attribute :>> lemma="FrameSealRoot.ackSourcePreserves"; attribute :>> scope="Actual typed IR action; source semantics conditional"; }
part binding9:BindingRow { attribute :>> actionName="frame_seal_root_scope.freeze"; attribute :>> lemma="FrameSealRoot.freezePreserves"; attribute :>> scope="Actual typed IR action; source semantics conditional"; }
part binding10:BindingRow { attribute :>> actionName="frame_seal_root_scope.coverSource"; attribute :>> lemma="FrameSealRoot.coverSourcePreserves"; attribute :>> scope="Actual typed IR action; source semantics conditional"; }
part binding11:BindingRow { attribute :>> actionName="frame_seal_root_scope.issue"; attribute :>> lemma="FrameSealRoot.issuePreserves"; attribute :>> scope="Actual typed IR action; source semantics conditional"; }
part binding12:BindingRow { attribute :>> actionName="frame_seal_root_scope.start"; attribute :>> lemma="FrameSealRoot.startPreserves"; attribute :>> scope="Actual typed IR action; source semantics conditional"; }
part binding13:BindingRow { attribute :>> actionName="frame_seal_root_scope.relocate"; attribute :>> lemma="FrameSealRoot.relocatePreserves"; attribute :>> scope="Actual typed IR action; source semantics conditional"; }
part binding14:BindingRow { attribute :>> actionName="frame_seal_root_scope.deferRootWriter"; attribute :>> lemma="FrameSealRoot.deferRootWriterPreserves"; attribute :>> scope="Actual typed IR action; source semantics conditional"; }
part binding15:BindingRow { attribute :>> actionName="frame_seal_root_scope.revokeBeforeCopy"; attribute :>> lemma="FrameSealRoot.revokeBeforeCopyPreserves"; attribute :>> scope="Actual typed IR action; source semantics conditional"; }
part binding16:BindingRow { attribute :>> actionName="frame_seal_root_scope.finishRound"; attribute :>> lemma="FrameSealRoot.finishRoundPreserves"; attribute :>> scope="Actual typed IR action; source semantics conditional"; }
part binding17:BindingRow { attribute :>> actionName="frame_seal_root_scope.closeLedger"; attribute :>> lemma="FrameSealRoot.closeLedgerPreserves"; attribute :>> scope="Actual typed IR action; source semantics conditional"; }
part binding18:BindingRow { attribute :>> actionName="frame_seal_root_scope.retireModule"; attribute :>> lemma="FrameSealRoot.retireModulePreserves"; attribute :>> scope="Actual typed IR action; source semantics conditional"; }
part binding19:BindingRow { attribute :>> actionName="frame_seal_root_scope.rejectOpaque"; attribute :>> lemma="FrameSealRoot.rejectOpaquePreserves"; attribute :>> scope="Actual typed IR action; source semantics conditional"; }
part def ProofRow { attribute key:String; attribute lemma:String; }
part proof0:ProofRow { attribute :>> key="all-step"; attribute :>> lemma="FrameSealRoot.stepPreserves"; }
part proof1:ProofRow { attribute :>> key="reachable"; attribute :>> lemma="FrameSealRoot.reachableSafe"; }
part proof2:ProofRow { attribute :>> key="receipt"; attribute :>> lemma="FrameSealRoot.receiptScope"; }
part proof3:ProofRow { attribute :>> key="snapshot"; attribute :>> lemma="FrameSealRoot.privateSnapshotUnaffected"; }
part proof4:ProofRow { attribute :>> key="unknown"; attribute :>> lemma="FrameSealRoot.unknownKeepsSource"; }
part proof5:ProofRow { attribute :>> key="budget-composition"; attribute :>> lemma="FrameRootComposition.sourceBudgetFromReceipt"; }
part proof6:ProofRow { attribute :>> key="root-monotonic"; attribute :>> lemma="FrameRootComposition.unionDelta"; }
part proof7:ProofRow { attribute :>> key="duplicate-root"; attribute :>> lemma="FrameRootComposition.duplicateHasNoCharge"; }
part proof8:ProofRow { attribute :>> key="reach-duplicate"; attribute :>> lemma="FrameRootComposition.duplicateRootSameReach"; }
part proof9:ProofRow { attribute :>> key="reach-added"; attribute :>> lemma="FrameRootComposition.addedRootPreservesReach"; }
part proof10:ProofRow { attribute :>> key="reach-ack"; attribute :>> lemma="FrameRootComposition.sourceAckPreservesSuccessor"; }
part history:GambitAssuranceRouting::ModelNeed { ref part :>> owner=GambitAssuranceRelations::modelUse3; attribute :>> obligationId="FS-history"; attribute :>> kind="interleaving"; attribute :>> subjectPath="dev/refactoring/modern-c/models/quint/frame_seal_root_scope.qnt"; attribute :>> subjectScope="Request custody private snapshot revocation and negative histories"; attribute :>> premise="Conditional architecture study; neither formal receipts nor anchors prove native correctness"; }
part induction:GambitAssuranceRouting::ModelNeed { ref part :>> owner=GambitAssuranceRelations::modelUse3; attribute :>> obligationId="FS-induction"; attribute :>> kind="induction"; attribute :>> subjectPath="dev/refactoring/modern-c/models/lean/FrameSealRoot.lean"; attribute :>> subjectScope="All actual typed AST steps and reachability induction"; attribute :>> premise="Conditional architecture study; neither formal receipts nor anchors prove native correctness"; }
part composition:GambitAssuranceRouting::ModelNeed { ref part :>> owner=GambitAssuranceRelations::modelUse3; attribute :>> obligationId="FS-composition"; attribute :>> kind="induction"; attribute :>> subjectPath="dev/refactoring/modern-c/models/lean/FrameRootComposition.lean"; attribute :>> subjectScope="SourceCover budget handoff and root union algebra"; attribute :>> premise="Conditional architecture study; neither formal receipts nor anchors prove native correctness"; }
part projection:GambitAssuranceRouting::ModelNeed { ref part :>> owner=GambitAssuranceRelations::modelUse2; attribute :>> obligationId="FS-projection"; attribute :>> kind="restricted-projection"; attribute :>> subjectPath="dev/refactoring/modern-c/models/lean/FrameSealRootAst.lean"; attribute :>> subjectScope="Typed JSON references and supported expression extraction"; attribute :>> premise="Conditional architecture study; neither formal receipts nor anchors prove native correctness"; }
part source:GambitAssuranceRouting::ModelNeed { ref part :>> owner=GambitAssuranceRelations::modelUse4; attribute :>> obligationId="FS-source"; attribute :>> kind="source-refinement"; attribute :>> subjectPath="dev/refactoring/modern-c/frame-seal-root-scope-design.org"; attribute :>> subjectScope="Alias closure all-origin frozen roots downstream descriptor user closure remain open"; attribute :>> premise="Conditional architecture study; neither formal receipts nor anchors prove native correctness"; }
part platform:GambitAssuranceRouting::ModelNeed { ref part :>> owner=GambitAssuranceRelations::modelUse3; attribute :>> obligationId="FS-platform"; attribute :>> kind="native-memory-order"; attribute :>> subjectPath="dev/refactoring/modern-c/frame-seal-root-scope-design.org"; attribute :>> subjectScope="Actual C11 loads stores freeze authority and total alternative remain open"; attribute :>> premise="Conditional architecture study; neither formal receipts nor anchors prove native correctness"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse3; attribute :>> contract="sealed-module-producer-summary"; attribute :>> actionName="frame_seal_root_scope.seal"; attribute :>> lemma="FrameSealRoot.privateSnapshotUnaffected"; }
part seam1:SeamRow { ref part :>> producer=GambitAssuranceRelations::modelUse4; ref part :>> consumer=GambitAssuranceRelations::modelUse3; attribute :>> contract="frozen-all-origin-root-domain"; attribute :>> actionName="frame_seal_root_scope.freeze"; attribute :>> lemma="FrameSealRoot.freezePreserves"; }
part seam2:SeamRow { ref part :>> producer=GambitAssuranceRelations::modelUse5; ref part :>> consumer=GambitAssuranceRelations::modelUse3; attribute :>> contract="old-frame-descriptor-lease-union"; attribute :>> actionName="frame_seal_root_scope.issue"; attribute :>> lemma="FrameSealRoot.receiptScope"; }
}
