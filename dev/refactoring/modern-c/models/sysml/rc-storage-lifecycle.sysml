package GambitRcStorageLifecycle { private import ScalarValues::*;
part def Owner { attribute componentId:String; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-register"; attribute :>> path="vendor/gambit/lib/_mem/rc-allocation.inc"; attribute :>> needle="tail->next = h;"; attribute :>> obligation="Plain list insertion requires owner and collector exclusion"; }
part source4:SourceRow { attribute :>> key="rc-free"; attribute :>> path="vendor/gambit/lib/_mem/rc-allocation.inc"; attribute :>> needle="if (--h->refcount == 0)"; attribute :>> obligation="Nonatomic decrement and unlink are not safe arbitrary-thread admission"; }
part source5:SourceRow { attribute :>> key="rc-write"; attribute :>> path="vendor/gambit/lib/_mem/rc-allocation.inc"; attribute :>> needle="h->data = val;"; attribute :>> obligation="All semantic writers must join freeze/generation protocol or deny admission"; }
part source6:SourceRow { attribute :>> key="rc-cleanup"; attribute :>> path="vendor/gambit/lib/_mem/rc-allocation.inc"; attribute :>> needle="___HIDDEN void cleanup_rc"; attribute :>> obligation="Bulk cleanup frees chain independent of per-entry leases"; }
part source7:SourceRow { attribute :>> key="rc-scan"; attribute :>> path="vendor/gambit/lib/_mem/rc-roots.inc"; attribute :>> needle="mark_array (work, &h->data, 1);"; attribute :>> obligation="Actual GC slot update; target private carrier is not implicitly scanned"; }
part source8:SourceRow { attribute :>> key="retire-refuse"; attribute :>> path="vendor/gambit/lib/_mem/capacity-resize.inc"; attribute :>> needle="return 0; /* no freeze receipt for external RC/native borrowers */"; attribute :>> obligation="Current processor retirement refuses nonempty RC rather than manufacturing a lease"; }
part source9:SourceRow { attribute :>> key="pstate-cleanup"; attribute :>> path="vendor/gambit/lib/_mem/memory-lifecycle.inc"; attribute :>> needle="free_still_objs (___ps);"; attribute :>> obligation="cleanup_mem_pstate frees still storage before cleanup_rc; not an active-lease release helper"; }
part source10:SourceRow { attribute :>> key="setter-export"; attribute :>> path="vendor/gambit/lib/setup.c"; attribute :>> needle="= ___set_data_rc;"; attribute :>> obligation="Public GSTATE function pointer permits indirect/out-of-tree callers; lexical sites do not close writer authority"; }
part source11:SourceRow { attribute :>> key="register-export"; attribute :>> path="vendor/gambit/lib/setup.c"; attribute :>> needle="= ___register_rc;"; attribute :>> obligation="Public registration ABI is not a stable VM SourceOwner registry"; }
part source12:SourceRow { attribute :>> key="closure-writer"; attribute :>> path="vendor/gambit/lib/os_dyn.c"; attribute :>> needle="___set_data_rc (c_closure, proc);"; attribute :>> obligation="Concrete semantic payload installer, architecture conditional"; }
part source13:SourceRow { attribute :>> key="view-drain"; attribute :>> path="vendor/gambit/lib/_mem/collection-round.inc"; attribute :>> needle="BARRIER(); /* no worker may retain a stopped root view past this cut */"; attribute :>> obligation="Root view grace cut precedes ordinary execution"; }
part source14:SourceRow { attribute :>> key="vm-root-retained"; attribute :>> path="vendor/gambit/lib/setup.c"; attribute :>> needle="return; /* do not erase retained source roots through repeated setup */"; attribute :>> obligation="Whole VM cleanup checks resize source requests; generic SourceRegistry not covered"; }
part source15:SourceRow { attribute :>> key="header-config"; attribute :>> path="vendor/gambit/include/makefile.in"; attribute :>> needle="HEADER_CONFIG ="; attribute :>> obligation="Ordered configured header composition; generated artifact provenance open"; }
part source16:SourceRow { attribute :>> key="mem-order"; attribute :>> path="vendor/gambit/lib/mem.c"; attribute :>> needle="#include \"_mem/rc-allocation.inc\""; attribute :>> obligation="Bind new implementation inclusion path/order"; }
part source17:SourceRow { attribute :>> key="rc-layout"; attribute :>> path="vendor/gambit/include/_gambit/memory_state.h.in"; attribute :>> needle="typedef struct ___rc_header_struct"; attribute :>> obligation="Links/refcount/data do not contain VM storage identity or extent"; }
part source18:SourceRow { attribute :>> key="rc-allocation"; attribute :>> path="vendor/gambit/lib/_mem/rc-allocation.inc"; attribute :>> needle="___ALLOC_MEM(bytes + sizeof (___rc_header))"; attribute :>> obligation="Allocation lacks durable identity and checked-extent receipt"; }
part source19:SourceRow { attribute :>> key="rc-address"; attribute :>> path="vendor/gambit/lib/_mem/rc-allocation.inc"; attribute :>> needle="return ___CAST(void*,h+1);"; attribute :>> obligation="Native payload address is not root-cell address"; }
part source20:SourceRow { attribute :>> key="allocator-export"; attribute :>> path="vendor/gambit/lib/setup.c"; attribute :>> needle="= ___alloc_rc_no_register;"; attribute :>> obligation="Indirect allocation authority remains public"; }
part source21:SourceRow { attribute :>> key="public-register"; attribute :>> path="vendor/gambit/include/_gambit/runtime_protocols.h.in"; attribute :>> needle="___IMP_FUNC(void*,___register_rc)"; attribute :>> obligation="Public declaration and implementation spelling require effective ABI qualification"; }
part source22:SourceRow { attribute :>> key="tcl-allocation"; attribute :>> path="vendor/gambit/examples/tcltk/tcltk.scm"; attribute :>> needle="void *cd = ___EXT(___alloc_rc) (0);"; attribute :>> obligation="Zero payload allocation still owns a root-bearing header"; }
part source23:SourceRow { attribute :>> key="string-resource"; attribute :>> path="vendor/gambit/lib/c_intf.c"; attribute :>> needle="___EXP_FUNC(void,___release_string)"; attribute :>> obligation="Native strings share RC allocator; classify Scheme payload separately"; }
part source24:SourceRow { attribute :>> key="alloc-default"; attribute :>> path="vendor/gambit/lib/_mem/rc-allocation.inc"; attribute :>> needle="h->data = ___FAL;"; attribute :>> obligation="Private native storage initially contains no Scheme payload; list links are not initialized here"; }
part source25:SourceRow { attribute :>> key="alloc-wrapper"; attribute :>> path="vendor/gambit/lib/_mem/rc-allocation.inc"; attribute :>> needle="if (ptr != 0) ___register_rc (___PSP ptr);"; attribute :>> obligation="Synchronous local NULL return excludes registration in this wrapper"; }
part source26:SourceRow { attribute :>> key="release-links"; attribute :>> path="vendor/gambit/lib/_mem/rc-allocation.inc"; attribute :>> needle="next->prev = prev;"; attribute :>> obligation="Ordinary release requires an already linked header; cannot abort never-registered allocation"; }
part source27:SourceRow { attribute :>> key="retain-counter"; attribute :>> path="vendor/gambit/lib/_mem/rc-allocation.inc"; attribute :>> needle="h->refcount++;"; attribute :>> obligation="Public retain must join native-borrow admission and exact release identity"; }
part source28:SourceRow { attribute :>> key="cleanup-head"; attribute :>> path="vendor/gambit/lib/_mem/rc-allocation.inc"; attribute :>> needle="rc_head.next = &rc_head;"; attribute :>> obligation="Bulk detach is not a result-aware transaction or destructor walk"; }
part source29:SourceRow { attribute :>> key="allocator-malloc"; attribute :>> path="vendor/gambit/lib/os_base.c"; attribute :>> needle="ptr = malloc (bytes);"; attribute :>> obligation="Default branch calls allocator; effective Darwin selection still must be qualified"; }
part source30:SourceRow { attribute :>> key="allocator-free"; attribute :>> path="vendor/gambit/lib/os_base.c"; attribute :>> needle="free (ptr);"; attribute :>> obligation="Physical free is a distinct irreversible effect after unpublish and grace"; }
part source31:SourceRow { attribute :>> key="allocator-macro"; attribute :>> path="vendor/gambit/include/_gambit/runtime_protocols.h.in"; attribute :>> needle="#define ___ALLOC_MEM(bytes)___EXT(___alloc_mem) (bytes)"; attribute :>> obligation="Exported allocation arithmetic reaches native allocator"; }
part source32:SourceRow { attribute :>> key="register-function-table"; attribute :>> path="vendor/gambit/include/_gambit/global_state.h.in"; attribute :>> needle="void *(*___register_rc)"; attribute :>> obligation="Declaration returns pointer while implementation returns void; ABI reconciliation prerequisite"; }
part source33:SourceRow { attribute :>> key="closure-install"; attribute :>> path="vendor/gambit/lib/os_dyn.c"; attribute :>> needle="C_CLOSURE_CODE_SIZE))"; attribute :>> obligation="Architecture-conditional allocation and installation; code publication separate from root publication"; }
part source34:SourceRow { attribute :>> key="closure-release"; attribute :>> path="vendor/gambit/lib/os_dyn.c"; attribute :>> needle="___release_rc (c_closure);"; attribute :>> obligation="Native trampoline and code borrow lifetime must join free permit"; }
part source35:SourceRow { attribute :>> key="string-last-ref"; attribute :>> path="vendor/gambit/lib/c_intf.c"; attribute :>> needle="if (___refcount_rc (x) == 1)"; attribute :>> obligation="Nested string list release traverses elements before parent release; pure header cleanup cannot replace it"; }
part source36:SourceRow { attribute :>> key="tls-destructor"; attribute :>> path="vendor/gambit/lib/os_io.c"; attribute :>> needle="SSL_CTX_free (c->tls_ctx);"; attribute :>> obligation="Native destructor effects precede RC free; context chain cleanup does not run this destructor"; }
part source37:SourceRow { attribute :>> key="tls-rc-release"; attribute :>> path="vendor/gambit/lib/os_io.c"; attribute :>> needle="___release_rc(c);"; attribute :>> obligation="Real resource adapter must issue effect completion only after child releases and native destructor settle"; }
part source38:SourceRow { attribute :>> key="tcl-vector-fail"; attribute :>> path="vendor/gambit/examples/tcltk/tcltk.scm"; attribute :>> needle="___EXT(___release_rc) (cd);"; attribute :>> obligation="Caller failure rollback is linked because alloc_rc already registered cd"; }
part source39:SourceRow { attribute :>> key="vm-cleanup-scope"; attribute :>> path="vendor/gambit/lib/_mem/memory-lifecycle.inc"; attribute :>> needle="/*TODO: other processors?*/"; attribute :>> obligation="VM cleanup text names processor zero; not a complete VM-owned registry drain proof"; }
part def IssuerRow { attribute key:String; attribute proposedIssuer:String; attribute actualSource:String; attribute status:String; attribute responsibility:String; }
part issuer0:IssuerRow { attribute :>> key="extent"; attribute :>> proposedIssuer="allocator attempt owner"; attribute :>> actualSource="alloc_rc_no_register plus alloc_mem"; attribute :>> status="native allocation exists; StorageId issuer absent"; attribute :>> responsibility="Record checked total bytes and original header base before exposing payload"; }
part issuer1:IssuerRow { attribute :>> key="reservation"; attribute :>> proposedIssuer="unified storage index owner"; attribute :>> actualSource="register_rc context list insertion"; attribute :>> status="proposed managed owner; not present"; attribute :>> responsibility="Atomic exclusive reservation and exact OperationId result"; }
part issuer2:IssuerRow { attribute :>> key="root"; attribute :>> proposedIssuer="VM RootRegistry and round owner"; attribute :>> actualSource="mark_rc context chain and root origin barrier"; attribute :>> status="VM generic scan adapter absent"; attribute :>> responsibility="Pin each distinct root cell and retain descriptor through scan grace"; }
part issuer3:IssuerRow { attribute :>> key="release"; attribute :>> proposedIssuer="exact native lease owner"; attribute :>> actualSource="addref_rc release_rc and string list wrappers"; attribute :>> status="plain counter/list helpers exist; exact token ledger absent"; attribute :>> responsibility="Distinguish caller reference release from physical free permit"; }
part issuer4:IssuerRow { attribute :>> key="cleanup"; attribute :>> proposedIssuer="VM storage and foreign effect owners"; attribute :>> actualSource="cleanup_rc and TLS destructor"; attribute :>> status="bulk free and foreign destruction are separate; no global receipt"; attribute :>> responsibility="Retain unknown outcomes and transfer roots/backing before context exit"; }
part issuer5:IssuerRow { attribute :>> key="reuse"; attribute :>> proposedIssuer="allocator incarnation owner"; attribute :>> actualSource="malloc may reuse freed address; public pointer APIs"; attribute :>> status="no expected generation in old raw API"; attribute :>> responsibility="No admission based on address lookup alone; refuse untracked stale raw aliases"; }
part issuer6:IssuerRow { attribute :>> key="ABI"; attribute :>> proposedIssuer="C23 profile and API schema owner"; attribute :>> actualSource="register_rc void body versus void pointer declarations"; attribute :>> status="effective ABI not qualified"; attribute :>> responsibility="Resolve signature and exported callers before managed migration"; }
part def BindingRow { attribute actionName:String; attribute lemma:String; }
part binding0:BindingRow { attribute :>> actionName="rc_storage_lifecycle.begin"; attribute :>> lemma="RcStorage.beginPreserves"; }
part binding1:BindingRow { attribute :>> actionName="rc_storage_lifecycle.beginZero"; attribute :>> lemma="RcStorage.beginZeroPreserves"; }
part binding2:BindingRow { attribute :>> actionName="rc_storage_lifecycle.beginTooLarge"; attribute :>> lemma="RcStorage.beginTooLargePreserves"; }
part binding3:BindingRow { attribute :>> actionName="rc_storage_lifecycle.ticketFailure"; attribute :>> lemma="RcStorage.ticketFailurePreserves"; }
part binding4:BindingRow { attribute :>> actionName="rc_storage_lifecycle.checkSize"; attribute :>> lemma="RcStorage.checkSizePreserves"; }
part binding5:BindingRow { attribute :>> actionName="rc_storage_lifecycle.rejectSize"; attribute :>> lemma="RcStorage.rejectSizePreserves"; }
part binding6:BindingRow { attribute :>> actionName="rc_storage_lifecycle.allocNull"; attribute :>> lemma="RcStorage.allocNullPreserves"; }
part binding7:BindingRow { attribute :>> actionName="rc_storage_lifecycle.allocSuccess"; attribute :>> lemma="RcStorage.allocSuccessPreserves"; }
part binding8:BindingRow { attribute :>> actionName="rc_storage_lifecycle.saveKey"; attribute :>> lemma="RcStorage.saveKeyPreserves"; }
part binding9:BindingRow { attribute :>> actionName="rc_storage_lifecycle.reserveIndex"; attribute :>> lemma="RcStorage.reserveIndexPreserves"; }
part binding10:BindingRow { attribute :>> actionName="rc_storage_lifecycle.prepareRoot"; attribute :>> lemma="RcStorage.prepareRootPreserves"; }
part binding11:BindingRow { attribute :>> actionName="rc_storage_lifecycle.publish"; attribute :>> lemma="RcStorage.publishPreserves"; }
part binding12:BindingRow { attribute :>> actionName="rc_storage_lifecycle.queryCommit"; attribute :>> lemma="RcStorage.queryCommitPreserves"; }
part binding13:BindingRow { attribute :>> actionName="rc_storage_lifecycle.releaseSource"; attribute :>> lemma="RcStorage.releaseSourcePreserves"; }
part binding14:BindingRow { attribute :>> actionName="rc_storage_lifecycle.retainExtra"; attribute :>> lemma="RcStorage.retainExtraPreserves"; }
part binding15:BindingRow { attribute :>> actionName="rc_storage_lifecycle.releaseExtra"; attribute :>> lemma="RcStorage.releaseExtraPreserves"; }
part binding16:BindingRow { attribute :>> actionName="rc_storage_lifecycle.releaseBase"; attribute :>> lemma="RcStorage.releaseBasePreserves"; }
part binding17:BindingRow { attribute :>> actionName="rc_storage_lifecycle.borrow"; attribute :>> lemma="RcStorage.borrowPreserves"; }
part binding18:BindingRow { attribute :>> actionName="rc_storage_lifecycle.returnBorrow"; attribute :>> lemma="RcStorage.returnBorrowPreserves"; }
part binding19:BindingRow { attribute :>> actionName="rc_storage_lifecycle.nativePin"; attribute :>> lemma="RcStorage.nativePinPreserves"; }
part binding20:BindingRow { attribute :>> actionName="rc_storage_lifecycle.nativeReturn"; attribute :>> lemma="RcStorage.nativeReturnPreserves"; }
part binding21:BindingRow { attribute :>> actionName="rc_storage_lifecycle.scan"; attribute :>> lemma="RcStorage.scanPreserves"; }
part binding22:BindingRow { attribute :>> actionName="rc_storage_lifecycle.finishScan"; attribute :>> lemma="RcStorage.finishScanPreserves"; }
part binding23:BindingRow { attribute :>> actionName="rc_storage_lifecycle.closeEntry"; attribute :>> lemma="RcStorage.closeEntryPreserves"; }
part binding24:BindingRow { attribute :>> actionName="rc_storage_lifecycle.requestCleanup"; attribute :>> lemma="RcStorage.requestCleanupPreserves"; }
part binding25:BindingRow { attribute :>> actionName="rc_storage_lifecycle.handoffVM"; attribute :>> lemma="RcStorage.handoffVMPreserves"; }
part binding26:BindingRow { attribute :>> actionName="rc_storage_lifecycle.exitContext"; attribute :>> lemma="RcStorage.exitContextPreserves"; }
part binding27:BindingRow { attribute :>> actionName="rc_storage_lifecycle.settleEffects"; attribute :>> lemma="RcStorage.settleEffectsPreserves"; }
part binding28:BindingRow { attribute :>> actionName="rc_storage_lifecycle.abortPrivate"; attribute :>> lemma="RcStorage.abortPrivatePreserves"; }
part binding29:BindingRow { attribute :>> actionName="rc_storage_lifecycle.unpublish"; attribute :>> lemma="RcStorage.unpublishPreserves"; }
part binding30:BindingRow { attribute :>> actionName="rc_storage_lifecycle.scanGrace"; attribute :>> lemma="RcStorage.scanGracePreserves"; }
part binding31:BindingRow { attribute :>> actionName="rc_storage_lifecycle.startFree"; attribute :>> lemma="RcStorage.startFreePreserves"; }
part binding32:BindingRow { attribute :>> actionName="rc_storage_lifecycle.finishFree"; attribute :>> lemma="RcStorage.finishFreePreserves"; }
part binding33:BindingRow { attribute :>> actionName="rc_storage_lifecycle.loseFreeOutcome"; attribute :>> lemma="RcStorage.loseFreeOutcomePreserves"; }
part binding34:BindingRow { attribute :>> actionName="rc_storage_lifecycle.reuseAddress"; attribute :>> lemma="RcStorage.reuseAddressPreserves"; }
part binding35:BindingRow { attribute :>> actionName="rc_storage_lifecycle.queryOld"; attribute :>> lemma="RcStorage.queryOldPreserves"; }
part binding36:BindingRow { attribute :>> actionName="rc_storage_lifecycle.rejectOldRelease"; attribute :>> lemma="RcStorage.rejectOldReleasePreserves"; }
part def RouteRow { attribute component:String; attribute actionName:String; attribute lemma:String; attribute producerAnchor:String; attribute obligationId:String; }
part route0:RouteRow { attribute :>> component="storage"; attribute :>> actionName="rc_storage_lifecycle.begin"; attribute :>> lemma="RcStorage.beginPreserves"; attribute :>> producerAnchor="alloc-wrapper"; attribute :>> obligationId="RC-storage"; }
part route1:RouteRow { attribute :>> component="storage"; attribute :>> actionName="rc_storage_lifecycle.beginZero"; attribute :>> lemma="RcStorage.beginZeroPreserves"; attribute :>> producerAnchor="alloc-wrapper"; attribute :>> obligationId="RC-storage"; }
part route2:RouteRow { attribute :>> component="storage"; attribute :>> actionName="rc_storage_lifecycle.beginTooLarge"; attribute :>> lemma="RcStorage.beginTooLargePreserves"; attribute :>> producerAnchor="alloc-wrapper"; attribute :>> obligationId="RC-storage"; }
part route3:RouteRow { attribute :>> component="storage"; attribute :>> actionName="rc_storage_lifecycle.ticketFailure"; attribute :>> lemma="RcStorage.ticketFailurePreserves"; attribute :>> producerAnchor="alloc-wrapper"; attribute :>> obligationId="RC-storage"; }
part route4:RouteRow { attribute :>> component="storage"; attribute :>> actionName="rc_storage_lifecycle.checkSize"; attribute :>> lemma="RcStorage.checkSizePreserves"; attribute :>> producerAnchor="rc-allocation"; attribute :>> obligationId="RC-platform"; }
part route5:RouteRow { attribute :>> component="storage"; attribute :>> actionName="rc_storage_lifecycle.rejectSize"; attribute :>> lemma="RcStorage.rejectSizePreserves"; attribute :>> producerAnchor="rc-allocation"; attribute :>> obligationId="RC-platform"; }
part route6:RouteRow { attribute :>> component="storage"; attribute :>> actionName="rc_storage_lifecycle.allocNull"; attribute :>> lemma="RcStorage.allocNullPreserves"; attribute :>> producerAnchor="alloc-wrapper"; attribute :>> obligationId="RC-storage"; }
part route7:RouteRow { attribute :>> component="storage"; attribute :>> actionName="rc_storage_lifecycle.allocSuccess"; attribute :>> lemma="RcStorage.allocSuccessPreserves"; attribute :>> producerAnchor="alloc-wrapper"; attribute :>> obligationId="RC-storage"; }
part route8:RouteRow { attribute :>> component="storage"; attribute :>> actionName="rc_storage_lifecycle.saveKey"; attribute :>> lemma="RcStorage.saveKeyPreserves"; attribute :>> producerAnchor="alloc-wrapper"; attribute :>> obligationId="RC-storage"; }
part route9:RouteRow { attribute :>> component="storage"; attribute :>> actionName="rc_storage_lifecycle.reserveIndex"; attribute :>> lemma="RcStorage.reserveIndexPreserves"; attribute :>> producerAnchor="alloc-wrapper"; attribute :>> obligationId="RC-storage"; }
part route10:RouteRow { attribute :>> component="storage"; attribute :>> actionName="rc_storage_lifecycle.prepareRoot"; attribute :>> lemma="RcStorage.prepareRootPreserves"; attribute :>> producerAnchor="rc-scan"; attribute :>> obligationId="RC-roots"; }
part route11:RouteRow { attribute :>> component="storage"; attribute :>> actionName="rc_storage_lifecycle.publish"; attribute :>> lemma="RcStorage.publishPreserves"; attribute :>> producerAnchor="rc-register"; attribute :>> obligationId="RC-execution"; }
part route12:RouteRow { attribute :>> component="storage"; attribute :>> actionName="rc_storage_lifecycle.queryCommit"; attribute :>> lemma="RcStorage.queryCommitPreserves"; attribute :>> producerAnchor="rc-register"; attribute :>> obligationId="RC-execution"; }
part route13:RouteRow { attribute :>> component="storage"; attribute :>> actionName="rc_storage_lifecycle.releaseSource"; attribute :>> lemma="RcStorage.releaseSourcePreserves"; attribute :>> producerAnchor="rc-scan"; attribute :>> obligationId="RC-roots"; }
part route14:RouteRow { attribute :>> component="storage"; attribute :>> actionName="rc_storage_lifecycle.retainExtra"; attribute :>> lemma="RcStorage.retainExtraPreserves"; attribute :>> producerAnchor="retain-counter"; attribute :>> obligationId="RC-writers"; }
part route15:RouteRow { attribute :>> component="storage"; attribute :>> actionName="rc_storage_lifecycle.releaseExtra"; attribute :>> lemma="RcStorage.releaseExtraPreserves"; attribute :>> producerAnchor="retain-counter"; attribute :>> obligationId="RC-writers"; }
part route16:RouteRow { attribute :>> component="storage"; attribute :>> actionName="rc_storage_lifecycle.releaseBase"; attribute :>> lemma="RcStorage.releaseBasePreserves"; attribute :>> producerAnchor="retain-counter"; attribute :>> obligationId="RC-writers"; }
part route17:RouteRow { attribute :>> component="storage"; attribute :>> actionName="rc_storage_lifecycle.borrow"; attribute :>> lemma="RcStorage.borrowPreserves"; attribute :>> producerAnchor="retain-counter"; attribute :>> obligationId="RC-writers"; }
part route18:RouteRow { attribute :>> component="storage"; attribute :>> actionName="rc_storage_lifecycle.returnBorrow"; attribute :>> lemma="RcStorage.returnBorrowPreserves"; attribute :>> producerAnchor="retain-counter"; attribute :>> obligationId="RC-writers"; }
part route19:RouteRow { attribute :>> component="storage"; attribute :>> actionName="rc_storage_lifecycle.nativePin"; attribute :>> lemma="RcStorage.nativePinPreserves"; attribute :>> producerAnchor="retain-counter"; attribute :>> obligationId="RC-writers"; }
part route20:RouteRow { attribute :>> component="storage"; attribute :>> actionName="rc_storage_lifecycle.nativeReturn"; attribute :>> lemma="RcStorage.nativeReturnPreserves"; attribute :>> producerAnchor="retain-counter"; attribute :>> obligationId="RC-writers"; }
part route21:RouteRow { attribute :>> component="storage"; attribute :>> actionName="rc_storage_lifecycle.scan"; attribute :>> lemma="RcStorage.scanPreserves"; attribute :>> producerAnchor="rc-scan"; attribute :>> obligationId="RC-roots"; }
part route22:RouteRow { attribute :>> component="storage"; attribute :>> actionName="rc_storage_lifecycle.finishScan"; attribute :>> lemma="RcStorage.finishScanPreserves"; attribute :>> producerAnchor="rc-scan"; attribute :>> obligationId="RC-roots"; }
part route23:RouteRow { attribute :>> component="storage"; attribute :>> actionName="rc_storage_lifecycle.closeEntry"; attribute :>> lemma="RcStorage.closeEntryPreserves"; attribute :>> producerAnchor="alloc-wrapper"; attribute :>> obligationId="RC-storage"; }
part route24:RouteRow { attribute :>> component="storage"; attribute :>> actionName="rc_storage_lifecycle.requestCleanup"; attribute :>> lemma="RcStorage.requestCleanupPreserves"; attribute :>> producerAnchor="rc-cleanup"; attribute :>> obligationId="RC-lifetime"; }
part route25:RouteRow { attribute :>> component="storage"; attribute :>> actionName="rc_storage_lifecycle.handoffVM"; attribute :>> lemma="RcStorage.handoffVMPreserves"; attribute :>> producerAnchor="rc-cleanup"; attribute :>> obligationId="RC-lifetime"; }
part route26:RouteRow { attribute :>> component="storage"; attribute :>> actionName="rc_storage_lifecycle.exitContext"; attribute :>> lemma="RcStorage.exitContextPreserves"; attribute :>> producerAnchor="rc-cleanup"; attribute :>> obligationId="RC-lifetime"; }
part route27:RouteRow { attribute :>> component="storage"; attribute :>> actionName="rc_storage_lifecycle.settleEffects"; attribute :>> lemma="RcStorage.settleEffectsPreserves"; attribute :>> producerAnchor="rc-cleanup"; attribute :>> obligationId="RC-lifetime"; }
part route28:RouteRow { attribute :>> component="storage"; attribute :>> actionName="rc_storage_lifecycle.abortPrivate"; attribute :>> lemma="RcStorage.abortPrivatePreserves"; attribute :>> producerAnchor="alloc-wrapper"; attribute :>> obligationId="RC-storage"; }
part route29:RouteRow { attribute :>> component="storage"; attribute :>> actionName="rc_storage_lifecycle.unpublish"; attribute :>> lemma="RcStorage.unpublishPreserves"; attribute :>> producerAnchor="rc-cleanup"; attribute :>> obligationId="RC-lifetime"; }
part route30:RouteRow { attribute :>> component="storage"; attribute :>> actionName="rc_storage_lifecycle.scanGrace"; attribute :>> lemma="RcStorage.scanGracePreserves"; attribute :>> producerAnchor="rc-cleanup"; attribute :>> obligationId="RC-lifetime"; }
part route31:RouteRow { attribute :>> component="storage"; attribute :>> actionName="rc_storage_lifecycle.startFree"; attribute :>> lemma="RcStorage.startFreePreserves"; attribute :>> producerAnchor="rc-cleanup"; attribute :>> obligationId="RC-lifetime"; }
part route32:RouteRow { attribute :>> component="storage"; attribute :>> actionName="rc_storage_lifecycle.finishFree"; attribute :>> lemma="RcStorage.finishFreePreserves"; attribute :>> producerAnchor="rc-cleanup"; attribute :>> obligationId="RC-lifetime"; }
part route33:RouteRow { attribute :>> component="storage"; attribute :>> actionName="rc_storage_lifecycle.loseFreeOutcome"; attribute :>> lemma="RcStorage.loseFreeOutcomePreserves"; attribute :>> producerAnchor="rc-cleanup"; attribute :>> obligationId="RC-lifetime"; }
part route34:RouteRow { attribute :>> component="storage"; attribute :>> actionName="rc_storage_lifecycle.reuseAddress"; attribute :>> lemma="RcStorage.reuseAddressPreserves"; attribute :>> producerAnchor="allocator-malloc"; attribute :>> obligationId="RC-storage"; }
part route35:RouteRow { attribute :>> component="storage"; attribute :>> actionName="rc_storage_lifecycle.queryOld"; attribute :>> lemma="RcStorage.queryOldPreserves"; attribute :>> producerAnchor="rc-register"; attribute :>> obligationId="RC-execution"; }
part route36:RouteRow { attribute :>> component="storage"; attribute :>> actionName="rc_storage_lifecycle.rejectOldRelease"; attribute :>> lemma="RcStorage.rejectOldReleasePreserves"; attribute :>> producerAnchor="retain-counter"; attribute :>> obligationId="RC-writers"; }
part def NeedRow { attribute key:String; attribute kind:String; attribute path:String; attribute scope:String; ref owner:Owner; }
part need0:NeedRow { attribute :>> key="RC-formal"; attribute :>> kind="formal"; attribute :>> path="dev/refactoring/modern-c/models/quint/rc_storage_lifecycle.qnt"; attribute :>> scope="one allocation cohort; two generations and exact fixed extra lease; safety only"; ref :>> owner = storageOwner; }
part need1:NeedRow { attribute :>> key="RC-bridge"; attribute :>> kind="bridge"; attribute :>> path="dev/refactoring/modern-c/models/lean/RcStorage.lean"; attribute :>> scope="restricted typed IR; all actions and reachable-state induction; trusted projection"; ref :>> owner = storageOwner; }
part need2:NeedRow { attribute :>> key="RC-storage"; attribute :>> kind="native"; attribute :>> path="vendor/gambit/lib/_mem/rc-allocation.inc"; attribute :>> scope="allocator identity extent and pre-index allocation custody; no stable signer implemented"; ref :>> owner = storageOwner; }
part need3:NeedRow { attribute :>> key="RC-roots"; attribute :>> kind="native"; attribute :>> path="vendor/gambit/lib/_mem/rc-roots.inc"; attribute :>> scope="every-GC VM registry coverage and source-before-allocation protection unproved"; ref :>> owner = storageOwner; }
part need4:NeedRow { attribute :>> key="RC-writers"; attribute :>> kind="native"; attribute :>> path="vendor/gambit/lib/setup.c"; attribute :>> scope="exported allocation registration setter retain release and raw caller closure incomplete"; ref :>> owner = storageOwner; }
part need5:NeedRow { attribute :>> key="RC-platform"; attribute :>> kind="native"; attribute :>> path="vendor/gambit/include/_gambit/runtime_protocols.h.in"; attribute :>> scope="C23 checked arithmetic atomic/mutex effective Darwin ABI including register return type open"; ref :>> owner = storageOwner; }
part need6:NeedRow { attribute :>> key="RC-lifetime"; attribute :>> kind="native"; attribute :>> path="vendor/gambit/lib/_mem/memory-lifecycle.inc"; attribute :>> scope="unknown outcomes retained beyond processor lifetime; real free and foreign effects signers incomplete"; ref :>> owner = storageOwner; }
part need7:NeedRow { attribute :>> key="RC-execution"; attribute :>> kind="native"; attribute :>> path="vendor/gambit/examples/tcltk/tcltk.scm"; attribute :>> scope="native callbacks continuations exceptions and stable guard product open"; ref :>> owner = storageOwner; }
part def ContractRow { attribute fromNode:String; attribute toNode:String; attribute custody:String; }
part contract0:ContractRow { attribute :>> fromNode="SchemeAndNativeCaller"; attribute :>> toNode="StableAttempt"; attribute :>> custody="operation identity and preallocation custody before allocation"; }
part contract1:ContractRow { attribute :>> fromNode="StableAttempt"; attribute :>> toNode="CheckedExtent"; attribute :>> custody="C23 checked header plus payload size"; }
part contract2:ContractRow { attribute :>> fromNode="CheckedExtent"; attribute :>> toNode="NoStorageFailure"; attribute :>> custody="overflow or synchronous NULL: definite no registration"; }
part contract3:ContractRow { attribute :>> fromNode="CheckedExtent"; attribute :>> toNode="PrivateNativeBlock"; attribute :>> custody="success retains header base and allocator provenance"; }
part contract4:ContractRow { attribute :>> fromNode="PrivateNativeBlock"; attribute :>> toNode="IndexReservation"; attribute :>> custody="check overlap and record private allocation custody"; }
part contract5:ContractRow { attribute :>> fromNode="PrivateNativeBlock"; attribute :>> toNode="PrivateAbort"; attribute :>> custody="never-linked rollback uses private destructor contract"; }
part contract6:ContractRow { attribute :>> fromNode="IndexReservation"; attribute :>> toNode="ScanVisibleCarrier"; attribute :>> custody="root and descriptor protection before publication"; }
part contract7:ContractRow { attribute :>> fromNode="ScanVisibleCarrier"; attribute :>> toNode="PublishedResult"; attribute :>> custody="one root bundle and operation result commit"; }
part contract8:ContractRow { attribute :>> fromNode="PublishedResult"; attribute :>> toNode="UnknownCommit"; attribute :>> custody="lost response retains allocation and source hold"; }
part contract9:ContractRow { attribute :>> fromNode="UnknownCommit"; attribute :>> toNode="StableVMOwner"; attribute :>> custody="context exit transfers responsibility; no cleanup_rc bypass"; }
part contract10:ContractRow { attribute :>> fromNode="StableVMOwner"; attribute :>> toNode="ExactQuery"; attribute :>> custody="same operation and request; definitive outcome only"; }
part contract11:ContractRow { attribute :>> fromNode="PublishedResult"; attribute :>> toNode="CloseAndDrain"; attribute :>> custody="close raw borrow admission and settle caller references"; }
part contract12:ContractRow { attribute :>> fromNode="ExactQuery"; attribute :>> toNode="CloseAndDrain"; attribute :>> custody="observed commit authorizes release protocol"; }
part contract13:ContractRow { attribute :>> fromNode="CloseAndDrain"; attribute :>> toNode="Unpublish"; attribute :>> custody="withdraw root-use view; retain owned extent until physical free"; }
part contract14:ContractRow { attribute :>> fromNode="PrivateAbort"; attribute :>> toNode="Unpublish"; attribute :>> custody="definite nonpublication and private root withdrawal"; }
part contract15:ContractRow { attribute :>> fromNode="Unpublish"; attribute :>> toNode="ScanGrace"; attribute :>> custody="old root views and descriptor users drained; extent still owned"; }
part contract16:ContractRow { attribute :>> fromNode="ScanGrace"; attribute :>> toNode="PhysicalFree"; attribute :>> custody="free header base only with exact permit"; }
part contract17:ContractRow { attribute :>> fromNode="PhysicalFree"; attribute :>> toNode="FreeOutcomeUnknown"; attribute :>> custody="never repeat irreversible free on uncertainty"; }
part contract18:ContractRow { attribute :>> fromNode="PhysicalFree"; attribute :>> toNode="NextGeneration"; attribute :>> custody="known completion; address may be equal but identity differs"; }
part contract19:ContractRow { attribute :>> fromNode="NextGeneration"; attribute :>> toNode="OldTokenRejection"; attribute :>> custody="expected generation required from caller"; }
part contract20:ContractRow { attribute :>> fromNode="CurrentRawAPI"; attribute :>> toNode="AdmissionRefusal"; attribute :>> custody="address-only input cannot prove expected generation"; }
part def GainRow { attribute key:String; attribute avoided:String; attribute added:String; attribute condition:String; }
part gain0:GainRow { attribute :>> key="failed-allocation"; attribute :>> avoided="preserve existing NULL to zero registrations; add checked overflow rejection, not a new NULL fast path"; attribute :>> added="checked add and stable attempt slot; O(n) reference overlap check versus current O(1) context append"; attribute :>> condition="ordinary synchronous path can add work; required lifecycle safety and actual retry frequency must justify it; unknown delivery is not NULL"; }
part gain1:GainRow { attribute :>> key="private-abort"; attribute :>> avoided="avoid invalid linked release of unregistered header"; attribute :>> added="separate private abort and foreign effect permit"; attribute :>> condition="new path replaces responsibility; no current in-tree misuse claimed"; }
part gain2:GainRow { attribute :>> key="retry"; attribute :>> avoided="one physical allocation and one publish for repeated same-operation delivery"; attribute :>> added="result records query handling and retained candidate storage"; attribute :>> condition="r requests imply one effect plus r-1 queries only with stable issuer and same request"; }
part gain3:GainRow { attribute :>> key="root-and-storage"; attribute :>> avoided="one VM-owned canonical storage/root authority across processor exit"; attribute :>> added="VM root enumeration descriptor pins and source handoff"; attribute :>> condition="only if generic scan coverage replaces context-only ownership; no scan-byte reduction proved"; }
part gain4:GainRow { attribute :>> key="native-release"; attribute :>> avoided="exact once reference settlement without premature physical free"; attribute :>> added="close admission drain native leases effect completion and scan grace"; attribute :>> condition="zero RC count is insufficient; all raw callers migrate or remain excluded"; }
part gain5:GainRow { attribute :>> key="address-reuse"; attribute :>> avoided="reject old token without dereferencing freed header"; attribute :>> added="generation-bearing handle or externally proved lifetime confinement"; attribute :>> condition="pointer-only ABI cannot supply this property by internal lookup"; }
part gain6:GainRow { attribute :>> key="cleanup"; attribute :>> avoided="retain unknown publication instead of unconditional bulk free"; attribute :>> added="u unresolved allocations and associated root/backing records remain live"; attribute :>> condition="capacity backpressure required; no eventual resolution or bounded u proved"; }
part gain7:GainRow { attribute :>> key="modern-C-versus-Zig"; attribute :>> avoided="one shared C23 contract and generated ABI schema"; attribute :>> added="both languages still maintain provenance GC bridge token ledger and foreign cleanup"; attribute :>> condition="no additional Zig return demonstrated by this component"; }
part def MemoryRow { attribute key:String; attribute publication:String; attribute observation:String; attribute obligation:String; attribute overhead:String; }
part memory0:MemoryRow { attribute :>> key="allocation"; attribute :>> publication="preallocate stable attempt metadata before allocator call"; attribute :>> observation="record returned native base in a nonabandonable owner interval"; attribute :>> obligation="no Scheme callback or moving allocation inside index lock; native return-to-record gap remains unproved"; attribute :>> overhead="one control record; allocator call outside lock"; }
part memory1:MemoryRow { attribute :>> key="register"; attribute :>> publication="revalidate allocator provenance and reserve occupied extent under owner transaction"; attribute :>> observation="publish root descriptor and immutable result together; acquire only with lifetime pin"; attribute :>> obligation="source/private roots precede Scheme allocation; old void ABI has no unknown outcome representation"; attribute :>> overhead="short serialized reserve and publish mutations"; }
part memory2:MemoryRow { attribute :>> key="release"; attribute :>> publication="exact generation OperationId and LeaseId settle under same owner"; attribute :>> observation="closed admission excludes future retains; accepted native references still accounted"; attribute :>> obligation="reference count itself neither lifetime pin nor completion receipt"; attribute :>> overhead="exact result ledger; no blind duplicate decrement"; }
part memory3:MemoryRow { attribute :>> key="free"; attribute :>> publication="withdraw root-use view but retain physical extent; scan/code/native grace then free"; attribute :>> observation="stable owner records free completion or quarantines unknown effect"; attribute :>> obligation="never free twice after lost acknowledgement; free-return-to-record window requires completion guard proof"; attribute :>> overhead="retained poisoned identity on unknown outcome"; }
part memory4:MemoryRow { attribute :>> key="cleanup"; attribute :>> publication="VM owner accepts roots backing descriptor and unresolved results before context disappears"; attribute :>> observation="cleanup can reclaim only receipt-authorized nodes; walk saves next before free"; attribute :>> obligation="mixed legacy-managed chain needs separate ownership traversal; do not reset head then consult unknown nodes"; attribute :>> overhead="VM arena census and result-aware drain"; }
part def ProofRow { attribute key:String; attribute lemma:String; }
part proof0:ProofRow { attribute :>> key="checkedTotal"; attribute :>> lemma="RcStorageBoundary.checkedTotal"; }
part proof1:ProofRow { attribute :>> key="zeroPayloadStillOwnsHeader"; attribute :>> lemma="RcStorageBoundary.zeroPayloadStillOwnsHeader"; }
part proof2:ProofRow { attribute :>> key="staleKeyNotCurrent"; attribute :>> lemma="RcStorageBoundary.staleKeyNotCurrent"; }
part proof3:ProofRow { attribute :>> key="addressOnlyCannotSeparate"; attribute :>> lemma="RcStorageBoundary.addressOnlyCannotSeparate"; }
part proof4:ProofRow { attribute :>> key="metadataDoesNotFixMissingExpectedIdentity"; attribute :>> lemma="RcStorageBoundary.metadataDoesNotFixMissingExpectedIdentity"; }
part proof5:ProofRow { attribute :>> key="unregisteredNeedsPrivateAbort"; attribute :>> lemma="RcStorageBoundary.unregisteredNeedsPrivateAbort"; }
part proof6:ProofRow { attribute :>> key="countZeroAloneInsufficient"; attribute :>> lemma="RcStorageBoundary.countZeroAloneInsufficient"; }
part proof7:ProofRow { attribute :>> key="unknownOutcomeCannotFree"; attribute :>> lemma="RcStorageBoundary.unknownOutcomeCannotFree"; }
part proof8:ProofRow { attribute :>> key="unknownNativeBorrowCannotFree"; attribute :>> lemma="RcStorageBoundary.unknownNativeBorrowCannotFree"; }
}
