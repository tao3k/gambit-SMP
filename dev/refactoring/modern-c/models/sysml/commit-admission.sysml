package GambitModernCCommitAdmission {
  private import ScalarValues::*;
  ref part vmRegistryOwnership = GambitVmLifecycle::registry;
  ref part vmOwnerRetirement = GambitVmLifecycle::owner;
  ref part globalReclaimPermit = GambitVmLifecycle::globalReclaim;
  ref part realization = GambitRuntimeRoleRealization::cut0;
  ref part gerbilPlanner = GerbilModuleBuild::planning;
  ref part gerbilFrontend = GerbilModuleBuild::frontend;
  ref part gerbilReadiness = GerbilModuleBuild::readiness;
  ref part gerbilExecution = GerbilModuleBuild::execution;
  ref part reconstructionContract = GambitHashIndexOwnership::construction;
  ref part reconstructionSchedule = GambitHashIndexOwnership::qnt;
  ref part reconstructionTransport = GambitHashIndexOwnership::lean;
  attribute gerbilHeaderPublication : String = GambitHeaderOrganization::publication;
  attribute selectedAdmissionModel:String="dev/refactoring/modern-c/models/sysml/index-owner-delivery.sysml";
  attribute legacyNeedBoundary:String="The31 Need/Question records in this package retain mixed-candidate programme scope; actual first-submission facts are projected from GambitSourceOrganization, never auto-waived or asserted passed here.";
  attribute candidateStatus : String = "DELIVERED-INDEX-OWNER-REV; INDEPENDENT-TWELVE-REQUIREMENT-CAMPAIGN-STARTED; NO-AGGREGATE-ACCEPTANCE";
  attribute currentStage : String = "Committed modern-c 582104b861ac31beebe2ffaa56a66f3f2d9ccf5e contains four production changes separating GC reference repair from Scheme index ownership and three namespaced vendor Scheme tests. Exact production-equivalent full bootstrap and interpreted/compiled controls passed. Original branch GSI/GSC and the remaining programme contracts are independent postcommit tests.";
  attribute vmRegistryProtocolId : String = "vm-registry";
  attribute vmRegistryModel : String = "dev/refactoring/modern-c/models/quint/vm_registry.qnt";
  attribute vmRegistryEvidence : String = "evidence/research/revision-admission/vm-lifecycle-results.json";
  attribute vmRegistryModelDuty : String = "QNT alone checks finite writer/reader/acknowledgement/interrupt schedules, with retained-effect and late-publication negative controls. No new Lean proof is introduced for this finite protocol; unchanged root/round algebra stays with its owning component. No duplicate schedule or new universal C theorem is claimed. LLM source review checks owner/TLS, signal backend, constructor stage and native-stop premises. Native tests exercise actual initialized secondary VM lifecycle, not secondary Scheme execution or secondary GC.";
  attribute custodyRefinementEvidence : String = "evidence/research/revision-admission/runtime-custody-refinement.json";
  attribute custodyRefinementBoundary : String = "Seven real source routes and27 anchors locate root publication, RC scanning, task completion, R-context restoration before owner cleanup, join-dependent still transfer and retained-state cleanup refusal. These are conditional source observations, not complete C memory-order or stopped-writer proofs. Supported synchronous lifetime and changed callers must close in this REV; independent carrier retirement, universal foreign recovery, collector generations and frontend performance remain later programme work.";
  attribute globalCleanupFrontier : String = "Implemented candidate: allocator no longer edits VM membership; setup publishes after initialization. A stable atomic registry admission word separates signal readers from exclusive setup/retirement/global shutdown. Other owners explicitly retire their VM and receive BOOL acknowledgement; global cleanup refuses while any secondary remains. Effectful still teardown retains a VM-owned cursor/payload on failed/unknown return and never grants global free or replays it. Native qualification and C refinement remain required; no universal foreign-stop claim.";
  attribute testedSourceLock : String = "evidence/research/revision-admission/reconstruction-source.lock.json; partial11-input consumer frontier; full1228 production-core manifest and exact bootstrap witness remain separately bound";
  attribute prospectiveCommitTree : String = "Delivered 582104b861ac31beebe2ffaa56a66f3f2d9ccf5e tree e27bb1ed6118134eef2aa07933a451cabae7b895 on modern-c. The three tests live in vendor/gambit/tests/smp/gc. Other pending header/worker/root/FFI research is not part of this REV.";
  attribute revisionScope : String = "Use the immutable committed REV for its independent twelve-requirement campaign, consuming the same Modern C SDK only after exact input/artifact checks. Keep other working and staged research intact. Do not borrow patch-line progress or deliver runtime changes solely as external evidence fixtures or patch files.";
  attribute revisionTests : String = "The four production changes match the retained 422.880377-second full bootstrap; three added vendor tests have no bootstrap-generation edge and were separately interpreted and compiled. The original374-file GSI campaign now starts with parentp1/childp2 and300 seconds. Original GSC remains separately bound to its original limits; no heap or time increases.";
  attribute revisionBlockers : String = "The selected seven-path bootstrap prerequisite passed its scoped five submission gates and was committed. Postcommit runtime/whole-inventory/stress/lifecycle/GC-FFI/Gerbil/performance acceptance remains separate; each failure keeps its actual REV/profile/artifact identity and does not reopen a mixed-candidate source scope.";
  attribute revisionObservations : String = "VM lifecycle runtime source on c9258cba passed a full406.118-second two-pass bootstrap, sixteen-case218.683-second campaign and seven W/R/fault observations. The Make source-distribution-only successor2c5d161b passed a separate358.346-second whole bootstrap within600. No native lifecycle campaign is retagged onto its rebuilt binaries. Earlier600-second failure remains failed. These observations do not select a submission tree or solve the programme twelve gates.";
  attribute buildResourceBoundary : String = "Make -j11 with inherited p11 formerly permitted 121 initial Scheme processor contexts. Qualified native gsc-boot actions now specify -:p1, so initial processor sum <= active jobs <= 11 while target SMP features remain unchanged. Not an OS-thread quota, matched speedup or arbitrary macro/interpreted-adapter guarantee.";
  attribute baselineDefinition : String = "The twelve semantic requirement labels are comparison targets. The recorded8/12 belongs to the patch-repair evidence line in evidence/source-results/current-checkpoint-qualification/summary.json; it is not a modern-c branch checkpoint or inherited credit.";
  attribute baselineAcceptance : String = "No8/12 or9/12 credit transfers from the patch-repair line. db7e3425 retains its failed bootstrap. The committed index-owner successor starts its own source-bound twelve-requirement campaign; bootstrap reuse uses explicit production-input equivalence, not inherited repair credit.";
  attribute comparisonHistoricalScope:String="patch-repair-line; not-modern-c-branch";
  attribute comparisonCreditInherited:Boolean=false;
  attribute comparisonBranchProgress:String="not-established; no-branch9-of12-evidence";
  attribute comparisonClassification:String="evidence/research/modern-c-mainline-comparison/progress-classification.json";
  attribute comparisonEvidence:String="evidence/research/modern-c-mainline-comparison/official-results.json";
  attribute comparisonSource:String="0b16c5bd5138decf478599c163c3735056cd3436";
  attribute comparisonPublishedCommit:String="db7e3425152c7036aec4cc30b20dd188d034773a";
  attribute comparisonAppliesToPublishedCommit:Boolean=false;
  attribute comparisonNewMilestoneCredit:Boolean=false;
  attribute comparisonPassed:Boolean=true;
  attribute comparisonSameRecipes:Boolean=true;
  attribute comparisonSameFixtures:Boolean=true;
  attribute comparisonSameLimits:Boolean=false;
  attribute comparisonFullGate:Boolean=false;
  attribute comparisonBranchCoverageEstablished:Boolean=false;
  attribute comparisonInputs:String="Six original mem/server/client/expected-output files and the complete test7-test9 Make recipe block are byte-identical to the recorded patch-repair observation. The whole Make template differs outside these recipes.";
  attribute comparisonLimits:String="This is the original three-target support observation, not the complete GC/FFI inventory. The baseline receipt does not record the numerical cap here and its raw log is unavailable at the declared path; no budget-equivalence, performance or ninth-gate claim. The caller epilogue failed after successful native completion; terminal receipts and streams are checked without executing the command again.";
  attribute comparisonNextProof:String="Establish the modern-c branch acceptance inventory and exact revision/profile/artifacts, then independently execute and review the applicable original tests and full required contracts. Prior patch outcomes are problem evidence and comparison inputs only. The research-tree three-target observation is not branch-HEAD proof.";
  attribute modularSuite : String = "Sixteen named vendor Scheme catalog/CI cases, including owner retirement and global reclamation. Local executions, source equivalence, remote CI and twelve-milestone acceptance remain separate.";
  attribute revisionFfiBoundary : String = "CFFI refactoring is already ongoing in the existing source and concurrent research. Inseparable changed SFUN/RC/marker/root consumers belong to the selected ownership cut; broad service work is coordinated through its actual contracts and receipts. Do not relabel that lane as unstarted, claim its progress, or import its completion without source-bound original-test evidence.";
  attribute roadmapBoundary : String = "DeliveryStep and DeliveryDependency in runtime-role-realization.sysml define an ordered refactoring programme. Global12-milestone acceptance and complete future CFFI/generation services do not become unconditional early-REV gates. Scope must be frozen before tests, not narrowed afterwards to hide a failure. An intermediate synchronous adapter is an explicit bounded architecture stage, not a claim of the final independent-worker design.";
  attribute originalInventoryBoundary : String = "Original379 assertion bodies and PR fixtures stay unchanged. Bounded p3 and p2 compiled observations remain incomplete. The shared-support and byte-order experiments failed to establish whole-inventory closure and are retired. Complete current GSI/GSC native inventories remain separate mandatory checks.";
  attribute producerAdmissionBoundary : String = "The preceding37aaf01a bootstrap and producer/map/verdict import remain historical bound events. VM lifecycle source changes invalidate their use as the current mutable SDK reference. New bootstrap, explicit input/core/native qualification and real consumer admission are required. The600-second failed attempt is retained; compiler-seed custody is separate from native source/runtime admission. No ancestor or failure is retagged.";
  attribute semanticBoundary:String="Preserve Scheme observable evaluation, exception and dynamic-wind behaviour, proper tail calls, shared object identity and multi-shot continuation/GC restoration; effects may be extended explicitly without silently weakening these guarantees.";
  attribute representationBoundary:String="Replace internal PSTATE/carrier bindings, frame/root representations, C helper signatures, function tables, ownership and allocation protocols as complete producer/consumer migrations. No duplicate namespace, alias or compatibility facade is required.";
  attribute binaryArtifactBoundary:String="A rebuilt generator/header/runtime/module cohort is the default migration. Unrebuilt old binary extensions are not promised to load. setup.c currently checks compiler version and selected structure sizes; this is not a complete same-size layout or function-signature fingerprint. Reject or rebuild uncertain artifacts; a size check alone is not admission.";
  attribute originalCompilerCostBoundary : String = "Keep unchanged GSC300 and numeric90 limits and the existing profile. single-host=0 is unlimited single-host, not disabled. The8008-label/5.60MB module finishes generation then times out in native construction; preprocessing alone1.98s/21.49MB does not account for the whole phase. Structural host partition must preserve PointId/FrameSpec/tail/root/multi-shot contracts, not tune a test threshold.";
  attribute gerbilBuildBoundary : String = "Pinned Gerbil source and existing SourceLock/build.sh consume one owned workspace.185 stage0 modules completed under explicit p1/J5 context. Stage1 failed70 in47.379901 seconds on partial-source lookup; withdrawing unpublished outputs preserves bootstrap and advances to Bach, but300-second old-runtime diagnostic still times out.186 native files are not independent completed-action receipts. Full current-runtime producer/consumer qualification and runtime-ABI invalidation remain open; no new source copy was created.";
  attribute reconstructionBoundary:String="Text and binary table decoders share strong construction roots before committing weak/index flags and reconstruction debt. Real roundtrip plus concurrent GC and explicit between-store GC controls pass on the new bootstrap. This closes an observed construction window, not all GC/FFI root producers or native stop recovery.";
  attribute checkedIncrementBoundary:String="Safe vector-inc specialization must check vector, mutability, index, increment and existing element before the unsafe atomic fetch-add. Checks short circuit before vector-ref and preserve the Scheme fallback and old-value result. Original invalid-delta assertion and independent invalid-element/no-write controls pass; no concurrent arbitrary-type mutation claim.";
  attribute testSupportDecision:String="REJECTED-FOR-THIS-REV: corrected nine-file inline13.618715s/shared13.396316s does not establish sufficient net return. Current original inline driver and namespace restored; no shared support feature or byte-order scheduler retained.";
  attribute gitExecutionAuthorized : Boolean = false;

  /* Labels are the parent's semantic acceptance inventory, not newly assigned
   * native gate ordinals. These assessments do not award cumulative credit. */
  part def BaselineAssessment {
    attribute label:String; attribute currentStatus:String; attribute remaining:String;
    attribute sourceApplicability:String="not-established-for-published-or-current-research-source; retained-status-is-not-gate-credit";
    attribute currentGateCredit:Boolean=false;
  }
  part baselineBootstrap:BaselineAssessment { attribute :>> label="Complete bootstrap"; attribute :>> currentStatus="Final exact-tree complete two-pass PASS within whole600; original timeout remains retained"; attribute :>> remaining="Current bounded bootstrap observation supplied; retained executable producer and complete other inventories remain separate"; }
  part baselineGsi:BaselineAssessment { attribute :>> label="Complete GSI inventory"; attribute :>> currentStatus="Original379/379 PASS; source-bound runner observation; aggregate submission still blocked"; attribute :>> remaining="Complete original declared interpreter inventory, not selected diagnostic fixtures"; }
  part baselinePrGsi:BaselineAssessment { attribute :>> label="PR regressions GSI"; attribute :>> currentStatus="All five unchanged SHA-bound PR additions included in the379 interpreter PASS"; attribute :>> remaining="Original declared PR fixture hashes and interpreter outcomes"; }
  part baselineGsc:BaselineAssessment { attribute :>> label="Complete GSC inventory"; attribute :>> currentStatus="Current original379 declared; whole300 ends with two timed-out groups. Completed groups have no assertion failure; numeric test PASS88.44s under90 and prim_port PASS18.35s under20. No complete GSC acceptance"; attribute :>> remaining="Complete original compiled inventory and loader/assertion protocol; retain original per-file limits"; }
  part baselinePrGsc:BaselineAssessment { attribute :>> label="PR regressions GSC"; attribute :>> currentStatus="Compiled pipe and serialization-GC complete; separate targeted serialization also passes. Other PR entries in truncated/unexecuted groups remain unqualified; no aggregate compiled PR acceptance"; attribute :>> remaining="Declared PR fixture hashes with complete compiled execution coverage"; }
  part baselineStressGsi:BaselineAssessment { attribute :>> label="Stress GSI"; attribute :>> currentStatus="Not executed on this current candidate"; attribute :>> remaining="Original full interpreted SMP stress workloads and unchanged witness/termination contracts"; }
  part baselineStressGsc:BaselineAssessment { attribute :>> label="Stress GSC"; attribute :>> currentStatus="Not executed on this current candidate"; attribute :>> remaining="Original full compiled SMP stress workloads; no shortened workloads promoted to this gate"; }
  part baselineRegistry:BaselineAssessment { attribute :>> label="Registry lifetime"; attribute :>> currentStatus="Selected root domains and isolated startup controls pass; full grid open"; attribute :>> remaining="Actual shared registry readers, resource incarnations, retirement and complete supported population grid"; }
  part baselineFaults:BaselineAssessment { attribute :>> label="Lifecycle faults"; attribute :>> currentStatus="Fresh calibrated empty unpublished abort: healthy 3-root/1-worker cohort completes three GCs; full fault inventory open"; attribute :>> remaining="Root-bearing or published unknown members, real failure/rollback, retained resources and complete supported recovery"; }
  part baselineFfi:BaselineAssessment { attribute :>> label="GC/FFI"; attribute :>> currentStatus="On research tree0b16c5bd5138decf478599c163c3735056cd3436 the unchanged official test7/test8/test9 pass in17.238s, exit0, no timeout. The patch-repair line already passed these same three targets; full GC/FFI remains open and no aggregate credit is granted."; attribute :>> remaining="Official interface inventory, actual FFI writers and bounded participation/source refinement; unknown raw writers are not silently admitted"; }
  part baselineGerbil:BaselineAssessment { attribute :>> label="Gerbil correctness"; attribute :>> currentStatus="Pinned source-facing build contract audited; actual current-candidate Gerbil build/test not executed; T-GERBIL remains required"; attribute :>> remaining="Actual downstream producer binding, complete required build and tests"; }
  part baselinePerformance:BaselineAssessment { attribute :>> label="Release performance"; attribute :>> currentStatus="Not qualified; validation elapsed time is not a performance result"; attribute :>> remaining="Matched accepted producers, declared workloads and complete measurement populations; scope before making release/speed claims"; }

  ref part tests = GambitCommitGates::tests;
  ref part learning = GambitCommitGates::learning;
  ref part process = GambitCommitGates::process;
  ref part models = GambitCommitGates::models;
  ref part questions = GambitCommitGates::questions;

  part def Need { ref part gate : GambitCommitGates::Gate; attribute id : String; attribute method : String; attribute artifact : String; attribute scope : String; }
  part tObject : Need { ref part :>> gate = tests; attribute :>> id="T-OBJECT"; attribute :>> method="native"; attribute :>> artifact="vendor/gambit/lib/mem.c"; attribute :>> scope="six-canonical-objects-with-recorded-bazel-profile"; }
  part tStorage : Need { ref part :>> gate=tests; attribute :>> id="T-STORAGE"; attribute :>> method="native"; attribute :>> artifact="vendor/gambit/tests/runtime-roles.c"; attribute :>> scope="accessors-storage-sanitizer-and-retired-field-controls"; }
  part tFrame : Need { ref part :>> gate=tests; attribute :>> id="T-FRAME"; attribute :>> method="native"; attribute :>> artifact="vendor/gambit/tests/frame-contract.c"; attribute :>> scope="frame-fixtures-three-register-configurations"; }
  part tQnt : Need { ref part :>> gate=tests; attribute :>> id="T-QNT"; attribute :>> method="quint"; attribute :>> artifact="dev/refactoring/modern-c/models/quint/runtime_roles.qnt"; attribute :>> scope="three-histories-finite-two-participant-safety-and-four-invariant-negative-controls"; }
  part tLean : Need { ref part :>> gate=tests; attribute :>> id="T-LEAN"; attribute :>> method="lean"; attribute :>> artifact="dev/refactoring/modern-c/models/lean/RuntimeRoles.lean"; attribute :>> scope="six-conditional-laws-and-axiom-audit"; }
  part tCohort : Need { ref part :>> gate=tests; attribute :>> id="T-COHORT"; attribute :>> method="native"; attribute :>> artifact="vendor/gambit/lib/_kernel.scm"; attribute :>> scope="source-generated-compiler-runtime-bootstrap-cohort"; }
  part tMap : Need { ref part :>> gate=tests; attribute :>> id="T-MAP"; attribute :>> method="native"; attribute :>> artifact="vendor/gambit/lib/_std.scm"; attribute :>> scope="real-map-multishot-continuation-gc-and-resume"; }
  part tSmp : Need { ref part :>> gate=tests; attribute :>> id="T-SMP"; attribute :>> method="native"; attribute :>> artifact="vendor/gambit/lib/setup.c"; attribute :>> scope="resize-rc-roots-callbacks-join-failure-and-runtime-retirement"; }
  part tCatalog : Need { ref part :>> gate=tests; attribute :>> id="T-CATALOG"; attribute :>> method="native"; attribute :>> artifact="vendor/gambit/tests/smp/catalog.scm"; attribute :>> scope="all-sixteen-named-cases-including-vm-retirement-global-permit-and-nonlocal-callback-exit-on-current-generated-cohort-with-original-bounds"; }
  part tProducts : Need { ref part :>> gate=tests; attribute :>> id="T-PRODUCTS"; attribute :>> method="source-refinement"; attribute :>> artifact="evidence/research/revision-admission/candidate-tree.json"; attribute :>> scope="complete-tree-to-bootstrap-inputs-and-regenerated-tracked-products-reconciliation"; }
  part tOriginal : Need { ref part :>> gate=tests; attribute :>> id="T-ORIGINAL"; attribute :>> method="native"; attribute :>> artifact="vendor/gambit/tests/makefile.in"; attribute :>> scope="full-declared-GSI-GSC-and-PR-inventories-no-selected-case-substitution"; }
  part tGerbil : Need { ref part :>> gate=tests; attribute :>> id="T-GERBIL"; attribute :>> method="native"; attribute :>> artifact="evidence/research/revision-admission/gerbil-build-contract.json"; attribute :>> scope="selected-Gerbil-producer-bootstrap-core-stdlib-tools-gxi-gxc-macro-import-supported-profile-module-executable-linkage-and-native-artifact-invalidation-on-current-Gambit-with-unchanged-Gerbil-facing-contracts"; }
  part tBaseline : Need { ref part :>> gate=tests; attribute :>> id="T-BASELINE"; attribute :>> method="source-analysis"; attribute :>> artifact="docs/smp-threaded-vm-milestone.md"; attribute :>> scope="twelve-semantic-gates-applicability-required-controls-and-explicit-unqualified-release-boundaries"; }
  part tUnequal : Need { ref part :>> gate=tests; attribute :>> id="T-UNEQUAL"; attribute :>> method="native"; attribute :>> artifact="vendor/gambit/tests/smp/gc/worker-root-domains.scm"; attribute :>> scope="fresh-current-runtime-three-roots-worker-sequence-1-2-3-1-owner-cleanup-three-no-independent-worker-thread-claim"; }
  part tUnknownEmpty : Need { ref part :>> gate=tests; attribute :>> id="T-UNKNOWN-EMPTY"; attribute :>> method="native"; attribute :>> artifact="vendor/gambit/tests/smp/gc/unknown-join-worker-domains.scm"; attribute :>> scope="fresh-calibrated-empty-unpublished-abort-with-healthy-three-roots-one-worker-and-three-GCs-no-general-unknown-exit-claim"; }
  part tIncremental : Need { ref part :>> gate=tests; attribute :>> id="T-INCREMENTAL"; attribute :>> method="native"; attribute :>> artifact="vendor/gambit/include/makefile.in"; attribute :>> scope="same-workspace-no-change-zero-generation-zero-C-zero-configuration-C-only-one-C-and-restored-no-change-source-and-stamp-stable"; }

  part tProducer : Need { ref part :>> gate=tests; attribute :>> id="T-PRODUCER"; attribute :>> method="source-refinement"; attribute :>> artifact="src/gambit_smp/completed_producer.py"; attribute :>> scope="renewed-current-generation-runtime-consumer-contract-and-original-bootstrap-ancestry-without-forged-or-retagged-Recipe-events"; }

  /* This is the existing Make/Configure path, not another profile or executor.
   * Native observations discharge source/budget boundaries; no concurrent
   * QNT machine or duplicated Lean theorem is introduced for byte comparison. */
  part def GenerationBoundary {
    ref part evidence : Need;
    attribute id:String; attribute source:String; attribute anchor:String;
    attribute invariant:String; attribute removedWork:String; attribute remaining:String;
  }

part gerbilModules:GenerationBoundary {
  ref part :>> evidence=tGerbil;
  attribute :>> id="gerbil-bootstrap-module-custody";
  attribute :>> source="src/gambit_smp/gerbil_build.py;src/gambit_smp/step_checkpoint.py;src/gambit_smp/research_kernel.py";
  attribute :>> anchor="_stage0_modules;recovered_resumption;failed_prefix_retry";
  attribute :>> invariant="Unchanged per-module source/options/parent/runtime and exact output bytes require the immutable same-run completed process witness; queued, partial, failed or unknown outputs never qualify. Child records do not become recipe-stage PASS. Publication is serialized while independent compiler processes overlap within a host-derived envelope.";
  attribute :>> removedWork="Reuse165 authenticated completed bootstrap modules in one owned source workspace; avoid full Git archive/extract for a pinned empty overlay after normal source-checkpoint validation; remove serial scheduling of independent stage0 compiler actions.";
  attribute :>> remaining="Full native Gerbil build/test remains mandatory after the actual stage1 timeout. Nine adapter controls pass, including same-workspace managed source replacement and scheduling-budget-independent warm reuse. They are not native Gerbil acceptance, an OS-thread quota or a matched speedup. Preserve failed-attempt expenditure and watchdog limits.";
}
  part gerbilBudget:GenerationBoundary {
    ref part :>> evidence=tGerbil;
    attribute :>> id="gerbil-resource-and-source-context";
    attribute :>> source="src/gambit_smp/gerbil_build.py;evidence/research/revision-admission/gerbil-build-source.patch;Gerbil src/build.sh and compiler/base.ss";
    attribute :>> anchor="_stage0_modules;GAMBOPT;GERBIL_BUILD_CORES;__jobs-mx";
    attribute :>> invariant="The existing managed source delta preserves caller runtime options before authoritative install mappings. Source overlays enter action identity rather than the physical workspace key. Only a target matching its previous witnessed input may be replaced. Compiler semantic context includes GAMBOPT; independent-action job capacity does not change it. Parent plus J one-processor compiler jobs uses a conservative 2J+1 scheduling envelope, not an OS-thread quota.";
    attribute :>> removedWork="No new checkout for a managed source delta; unchanged input copies retain timestamps. Exact completed-module outputs can be reused after validation. No automatic multiplication by the host default processor population.";
    attribute :>> remaining="Actual upstream build.sh previously overwrote outer GAMBOPT with install mappings; outer receipts alone did not prove child p1. Default measured6 versus explicit1; one util Scheme-to-C pilot2.67 versus4.39 seconds does not prove throughput gain. Aggregate memory grows with simultaneous compilers. Full original GSC still times out with161 accepted files, including the unchanged90-second numeric cap.";
  }
  part sfunExit:GenerationBoundary {
    ref part :>> evidence=tCatalog;
    attribute :>> id="callback-nonlocal-exit-custody";
    attribute :>> source="vendor/gambit/lib/c_intf.c;vendor/gambit/lib/setup.c;vendor/gambit/include/_gambit/foreign_conversion.h.in;vendor/gambit/tests/sfun-exit.scm";
    attribute :>> anchor="call_sfun_with_cleanup;___call_sfun;___sfun_error;___END_SFUN;___propagate_error";
    attribute :>> invariant="A throw from ___call carries explicit control origin through both SFUN sites. All three generated families skip conversion recovery for thrown control, execute existing cleanup and propagate the unchanged status. Declarations and function-table signatures migrate with the wrappers. Reaching a Scheme continuation can precede physical C return: still-active callback banks remain roots across GC until their own unwind. Never restore an obsolete Scheme frame or prematurely drop its bank.";
    attribute :>> removedWork="Retire raw ___call returns that bypass the generated cleanup boundary; do not weaken teardown refusal or discard retained roots.";
    attribute :>> remaining="The first catcher-only cut bootstraps245.953481 seconds but passes13/14 catalog cases and fails callback exit. Borrow0-to1 alone is not a leak: physical C frames can remain live. Explicit control origin repairs exit-versus-conversion classification; current direct/nested/normal/GC/dynamic-wind validation and full bootstrap remain required. No arbitrary foreign-thread, owner-death, dead-C-continuation or whole FFI admission follows; QNT schedule and Lean algebra remain separately owned.";
  }
  part stage1Lookup:GenerationBoundary {
    ref part :>> evidence=tGerbil;
    attribute :>> id="unpublished-stage1-lookup-custody";
    attribute :>> source="src/gambit_smp/gerbil_build.py;Gerbil src/build.sh;src/build/build1.ss;src/gerbil/runtime/loader.ss";
    attribute :>> anchor="_withdraw_stage1_outputs;__find-library-module;execute-pending-compile-jobs!";
    attribute :>> invariant="Only a completed matching stage1 proof may remain in the consumer lookup path. Before retrying an unqualified stage1, leased and quiescent ownership permits withdrawing its core/static outputs and Gerbil launchers by inode move into the attempt evidence directory. Preserve completed bootstrap and Gambit runtime payloads. Never overwrite retained failed custody or move outputs of an unknown live producer.";
    attribute :>> removedWork="Avoid retrying bootstrap from a loader polluted by previously failed frontend output; keep completed stage0 products and the same physical source workspace";
    attribute :>> remaining="Actual resource-context attempt closes185 modules then stage1 fails70 in47.379901 seconds on optimize-call~1 source via an SSI import. The loader checks source before later search directories, while build1 queues native jobs. Clean-lookup counterfactual and native regression remain required; no claim that the prior timeout had one exclusive cause.";
  }
  part compilationUnit:GenerationBoundary {
    ref part :>> evidence=tOriginal;
    attribute :>> id="generated-host-compilation-unit";
    attribute :>> source="vendor/gambit/configure.ac;vendor/gambit/include/_gambit/configuration.h.in;vendor/gambit/gsc/_t-c-1.scm;generated numeric.c and existing gambuild-C";
    attribute :>> anchor="CONF_SINGLE_HOST_LIMIT;___SINGLE_HOST_LIMIT;___LBLCOUNT;DEFS_DYN";
    attribute :>> invariant="The existing profile single-host=0 enables single-host with no label-count limit; zero does not disable it. Compile-unit structure, frontend generation and independent-action scheduling are distinct responsibilities. Any proposed host partition must preserve PointId/FrameSpec, cross-host tail transfer, root maps and multi-shot continuation interpretation rather than changing a test's acceptance context.";
    attribute :>> removedWork="No removal claimed yet. Structural host partitioning must be justified on the generator/runtime chain; neither extra Make jobs nor C23 itself splits one host function";
    attribute :>> remaining="Actual numeric source has8008 labels and5595981 C bytes. Scheme-to-C completes12.398549 seconds; native-module construction exhausts remaining77.112252 seconds under the original90-second aggregate and produces no module. GCC16.2 command includes SINGLE_HOST and O1. This proves this attempt fails before test execution, not a universal timing law or a reason to change the profile. Host-graph refinement and full GSC remain open.";
  }
  part compilerBudget:GenerationBoundary {
    ref part :>> evidence=tCohort;
    attribute :>> id="compiler-job-budget";
    attribute :>> source="vendor/gambit/lib/makefile.in;gsc/makefile.in;gsi/makefile.in";
    attribute :>> anchor="gsc-boot -:p1";
    attribute :>> invariant="Qualified native core compiler actions start one Scheme processor per Make job. Initial processor sum <= active jobs <= J; configured target Scheme SMP features are unchanged. This is not an OS-thread quota or a claim about arbitrary effectful compile-time code or interpreted compiler adapters";
    attribute :>> removedWork="Retire nested J-by-host-processor initial populations and idle participant/GC coordination in the admitted native core path";
    attribute :>> remaining="Native selected source/profile only; do not infer a universal workload speedup or an enforced quota against arbitrary macro effects";
  }
  part generationFeatures:GenerationBoundary {
    ref part :>> evidence=tProducts;
    attribute :>> id="target-feature-dependency";
    attribute :>> source="vendor/gambit/configure.ac;include/config.h.in;lib/makefile.in;gsc/makefile.in;gsi/makefile.in";
    attribute :>> anchor="___RTLIB_COND_EXPAND_FEATURES;___GSC_COMPILATION_OPTIONS";
    attribute :>> invariant="One existing Configure source exports the target prelude and generation options into its existing feature header; module C depends on that header. C source edits do not change it; configuration changes cannot silently reuse unqualified generated C";
    attribute :>> removedWork="Remove implicit feature selection from timestamp-only module reuse; retire hand-maintained derived bodies as semantic authority";
    attribute :>> remaining="The whole feature header is conservative; unrelated probe-content changes may over-invalidate. Distribution dummy bootstrap is not evidence that Scheme generation executed";
  }
  part configuredTools:GenerationBoundary {
    ref part :>> evidence=tCohort;
    attribute :>> id="configured-tool-lifetime";
    attribute :>> source="vendor/gambit/bin/makefile.in";
    attribute :>> anchor="bootclean-pre: mostlyclean-pre";
    attribute :>> invariant="Compiler clean removes generated compiler/runtime products but retains configuration-owned tool templates and launchers; their existing dependencies still rebuild on configuration/source changes";
    attribute :>> removedWork="Remove repeated configuration-template emission from the two mandatory source bootstrap passes";
    attribute :>> remaining="Two full source and native compilation passes remain mandatory; retained executable producers need independent publication";
  }
  part stableStamp:GenerationBoundary {
    ref part :>> evidence=tIncremental;
    attribute :>> id="content-stable-stamp";
    attribute :>> source="vendor/gambit/include/makefile.in";
    attribute :>> anchor="cmp -s stamp.h.new stamp.h";
    attribute :>> invariant="The non-Git working source keeps the stamp timestamp when its bytes are unchanged, without changing stamp contents or version semantics";
    attribute :>> removedWork="Retire unconditional stamp rewriting and resulting unnecessary kernel object rebuild";
    attribute :>> remaining="Actual metadata changes must still invalidate dependent objects";
  }
  part publicationFamily:GenerationBoundary {
    ref part :>> evidence=tProducts;
    attribute :>> id="generated-publication-family";
    attribute :>> source="vendor/gambit/lib/_kernel.scm;_thread.scm;_io.scm;_num.scm;_system.scm;_module.scm;generated C and link descriptors";
    attribute :>> anchor="##current-vm-resize-ready;context->type_cache;macro-gc-hash-table-flag-scheme-index;~~lib/_syntax-xform.scm";
    attribute :>> invariant="Default publication and configured SMP outputs carry distinct target-feature and source-location contexts. Changed Scheme/native embedded bodies regenerate their default C and all downstream descriptors. Never copy profile-specific SMP C over default publication or normalize observable source paths away";
    attribute :>> removedWork="Retire stale manually maintained derived C and blanket cross-family equality as an admission rule; preserve exact within-family byte/input checks";
    attribute :>> remaining="Source-location metadata remains context-bearing. Derived-only bootstrap reuse requires equality of all non-generated source inputs, original event identity and stable compiler/profile/cwd; no retagged execution";
  }
  part aLesson : Need { ref part :>> gate=learning; attribute :>> id="A-LESSON"; attribute :>> method="source-analysis"; attribute :>> artifact="dev/refactoring/modern-c/bootstrap-validation.org"; attribute :>> scope="architectural-learning-and-real-consumer-replacement"; }
  part aCost : Need { ref part :>> gate=learning; attribute :>> id="A-COST"; attribute :>> method="source-analysis"; attribute :>> artifact="dev/refactoring/modern-c/bootstrap-validation.org"; attribute :>> scope="whole-vm-size-indirection-final-collective-and-unmeasured-costs"; }
  part pCurrent : Need { ref part :>> gate=process; attribute :>> id="P-CURRENT"; attribute :>> method="source-analysis"; attribute :>> artifact="dev/refactoring/modern-c/models/sysml/commit-admission.sysml"; attribute :>> scope="candidate-source-cut-stage-and-next-dependent-stages"; }
  part mNative : Need { ref part :>> gate=models; attribute :>> id="M-NATIVE"; attribute :>> method="sysml"; attribute :>> artifact="dev/refactoring/modern-c/models/sysml/runtime-role-realization.sysml"; attribute :>> scope="native-role-need-use-flow-projection"; }
  part mAscent : Need { ref part :>> gate=models; attribute :>> id="M-ASCENT"; attribute :>> method="ascent"; attribute :>> artifact="dev/modeling/ascent/commit-admission.rules.scm"; attribute :>> scope="artifact-scope-source-frontier-and-synthetic-class-negative-controls"; }
  part mRefine : Need { ref part :>> gate=models; attribute :>> id="M-REFINE"; attribute :>> method="source-refinement"; attribute :>> artifact="vendor/gambit/lib/mem.c"; attribute :>> scope="real-root-freeze-termination-barrier-and-cleanup-to-model-obligations"; }

  part def Question { ref part gate : GambitCommitGates::Gate = questions; attribute id : String; attribute method : String="paper-source-analysis"; attribute artifact : String="dev/refactoring/modern-c/commit-admission.org"; attribute scope : String; attribute prompt : String; attribute answer : String; attribute status : String; attribute evidence : String; attribute counterexample : String; }
  part qPvm : Question { attribute :>> id="Q-PVM"; attribute :>> scope="gvm-semantic-ownership-and-c-portability"; attribute :>> prompt="Which PVM idea is amplified, and which Scheme semantic decisions must stay out of C layout helpers?"; attribute :>> answer="Retain GVM target cooperation; one explicit frame/root origin feeds collectors and continuation consumers. The C role cut is groundwork, not a completed generator rewrite or LLVM backend."; attribute :>> status="answered-scoped"; attribute :>> evidence="FeeleyMillerLFP90 sections 1-2; gambit.h.in context accessors; mem.c mark_execution_roots; frame-consumers.org"; attribute :>> counterexample="Recreating Scheme control semantics independently in a new backend duplicates the semantic authority; moving C fields alone does not amplify PVM optimization."; }
  part qPoll : Question { attribute :>> id="Q-POLL"; attribute :>> scope="bounded-safepoint-and-participation-progress"; attribute :>> prompt="Does the new root participant prove progress for nonallocating loops, foreign blocking calls and collector cooperation?"; attribute :>> answer="No. This cut keeps the existing synchronous safepoint mechanism; phase guards establish ordering only. A bounded-progress claim needs generator placement, root freeze and foreign participation together."; attribute :>> status="answered-scoped"; attribute :>> evidence="Feeley1993 via retro-parallel section 3.4; mem.c require_gc_phase and garbage_collect_pstate; modernization-target.org"; attribute :>> counterexample="A nonallocating spin loop can avoid allocation checks and prevent a collective; new phase enums cannot force it to participate."; }
  part qMulti : Question { attribute :>> id="Q-MULTISHOT"; attribute :>> scope="map-capture-and-repeated-resume-with-gc"; attribute :>> prompt="Can captured map frames be resumed repeatedly after GC without consuming roots or imposing one-shot ownership?"; attribute :>> answer="Fresh current-runtime catalog passes map multi-shot, eleven forced-GC wide-root controls at one and host processors, and dynamic-wind multi-shot. Fresh role controls exercise three roots with one/two/three workers and owner cleanup. Arbitrary continuation/FFI writer coverage remains open; a full bounded bootstrap has passed; earlier p11 failures retain their identities."; attribute :>> status="answered-scoped"; attribute :>> evidence="bootstrap-validation.org; mem.c mark_continuation/shared frame decoder; frame-continuation-roots.scm; retro-concurrency sections 4-5 distinguish one-shot fibers"; attribute :>> counterexample="Treating a captured frame as uniquely consumed after its first resume preserves an OCaml-style use case but breaks Scheme multi-shot behavior. A one-context pass cannot qualify failed multi-processor startup."; }
  part qLifetime : Question { attribute :>> id="Q-LIFETIME"; attribute :>> scope="touched-context-participant-worker-lifetime-under-supported-synchronous-adapter"; attribute :>> prompt="Do all changed context, participant and arena consumers retain valid storage through supported synchronous GC, resize and cleanup; which independent retirement remains outside this cut?"; attribute :>> answer="VM-owned origins and worker arenas separate storage from carrier fields, with current W<R/owner-cleanup controls. The supported adapter remains synchronous and borrows work->carrier; cleanup_pstate still owns resource lifetime. Complete touched-path storage/borrow/exit refinement remains open. Independent carrier retirement is a later claim and is not demanded merely by this question."; attribute :>> status="unresolved"; attribute :>> evidence="setup.c cleanup_pstate; mem.c worker carrier uses; runtime-role-realization.sysml RR-LIFETIME"; attribute :>> counterexample="Clearing carrier bytes leaves a VM array intact but does not prove that a thread or context can retire while users remain."; }
  part qFfi : Question { attribute :>> id="Q-FFI"; attribute :>> scope="changed-foreign-consumer-migration-coherence-and-root-exit-custody"; attribute :>> prompt="Do the changed generator, C declarations/function tables/definitions and actual SFUN/RC/Tcl callers agree on the new result, root and exit contracts, without retaining obsolete interfaces?"; attribute :>> answer="Internal ABI/layout preservation is not required. Source evidence already shows set_data_rc changes from void to BOOL, with declarations/function table and Tcl result checks migrated. This REV owes complete touched-consumer migration and root/error/exit safety under the new design. Old binary extensions require rebuild or verified rejection; setup version/size checks are not a full ABI fingerprint. Universal CFFI/foreign-thread/destructor redesign remains later. Native touched-path safety is still open."; attribute :>> status="unresolved"; attribute :>> evidence="include/_gambit/runtime_protocols.h.in and global_state.h.in set_data_rc; lib/_mem/rc-allocation.inc; examples/tcltk/tcltk.scm; gsc/_t-c-1.scm; setup.c setup_module/run/catcher"; attribute :>> counterexample="Keeping a void function-table entry while a migrated caller consumes a success result is incoherent even if structure size is unchanged. Conversely, freezing the old signature prevents the new admission result contract. GC waiting for an owner callback can still form an independent cycle."; }
  part qFailure : Question { attribute :>> id="Q-FAILURE"; attribute :>> scope="closed-census-result-and-unknown-exit-custody"; attribute :>> prompt="Who retains roots and work after partial startup, failed join, unknown exit or a missing final acknowledgement?"; attribute :>> answer="Earlier calibrated empty-unpublished-abort control preserves a healthy three-root/one-worker cohort through three GCs. Root-bearing or published unknown members remain refused. The new registry/owner/global protocol replaces that ignored-refusal path; prototype native host and retained-effect controls pass. Final current-cohort tests, complete barrier/failure custody and source refinement remain open. Unqualified published/root-bearing unknown exits remain refused."; attribute :>> status="unresolved"; attribute :>> evidence="mem.c gc_round and final barrier; runtime_roles.qnt; setup.c resize cleanup; registered repair-9-12 evidence"; attribute :>> counterexample="A two-participant model assumes both members reach their barriers; a failed native participant can prevent that premise."; }
  part qCost : Question { attribute :>> id="Q-COST"; attribute :>> scope="structural-benefit-versus-runtime-cost"; attribute :>> prompt="Which work is removed now, what is added, and what would refute a net-benefit claim?"; attribute :>> answer="Old carrier payload fields, implicit origin and queue selection are replaced. Earlier role-only +3080 VM bytes is historical. Current configured storage control reports context584, worker408, participant120, carrier648 and VM122824 bytes at word64; no matched complete-candidate delta or speedup is established. Root indirection, coordination, capacity reservations and writer obligations remain costs."; attribute :>> status="answered-scoped"; attribute :>> evidence="matched parent/current sizeof; runtime-role-matrix.org; source commit diff; verification.json"; attribute :>> counterexample="A smaller carrier is not a smaller VM. If downstream retirement never occurs, extra indirection and coordination can exceed the value of the split."; }
  part qRetire : Question { attribute :>> id="Q-RETIRE"; attribute :>> scope="old-path-retirement-and-historical-evidence-separation"; attribute :>> prompt="Which old responsibilities actually disappear, and is any patch result being presented as refactoring acceptance?"; attribute :>> answer="Direct carrier root/memory fields and old visitor trio are removed; embedded C consumers change. Cleanup lifecycle remains open; source-generated bootstrap and product reconciliation now have scoped evidence. Bazel provides configuration; patch receipts retain their own identities and no historical score is inherited by this candidate."; attribute :>> status="answered-scoped"; attribute :>> evidence="negative old-field compile; source diff; runtime-role-realization.org; historical SMP observation"; attribute :>> counterexample="Importing patch candidates or labeling historical passes with the new source SHA does not retire ownership or establish native acceptance."; }


  part def OwnershipBoundary {
    ref part evidence:Need;
    attribute id:String; attribute source:String; attribute anchor:String;
    attribute invariant:String; attribute removedWork:String; attribute remaining:String;
    attribute model:String; attribute modelReceipt:String; attribute abstractPremise:String;
  }
  part vmRegistry:OwnershipBoundary {
    ref part :>> evidence=mRefine;
    attribute :>> id="vm-registry";
    attribute :>> source="vendor/gambit/lib/_setup/vm-registry.inc;vendor/gambit/lib/_setup/vm-lifecycle.inc;vendor/gambit/lib/setup.c";
    attribute :>> anchor="vm_registry_try_write;cleanup_vmstate_owned;cleanup_runtime";
    attribute :>> invariant=GambitVmLifecycle::registry.authority;
    attribute :>> removedWork=GambitVmLifecycle::globalReclaim.retirement;
    attribute :>> remaining="Current native source/cohort and platform premises must match. Finite schedule plus prototype native controls do not discharge all C root/failure/lifetime refinement.";
    attribute :>> model=GambitVmLifecycle::qntModel;
    attribute :>> modelReceipt=GambitVmLifecycle::evidence;
    attribute :>> abstractPremise=GambitVmLifecycle::platformPremise;
  }
  part threadLease:OwnershipBoundary {
    ref part :>> evidence=tOriginal;
    attribute :>> id="thread-lock-lease";
    attribute :>> source="vendor/gambit/lib/_thread.scm";
    attribute :>> anchor="##thread-lock-remove-btq-toq!;##thread-intr-propagate!";
    attribute :>> invariant="All successful lock acquisitions terminate through helper release before external interrupt dispatch; retry releases before reacquisition; the decision callback performs internal queue operations only";
    attribute :>> removedWork="Retire branch-owned final releases and dispatch while the helper lock remains borrowed; no per-operation allocation or layout field added";
    attribute :>> remaining="Existing lock acquire/release ordering and callback non-escape premises require source refinement; bounded QNT is not C weak-memory or all-exit liveness proof";
    attribute :>> model="models/gambit/ended_interrupt_lock.qnt";
    attribute :>> modelReceipt="evidence/model-results/ended-interrupt-lock.json";
    attribute :>> abstractPremise="acquire/propagate/observe; propagate closes locked in fixed state; exceptional termination does not preserve the lock";
  }
  part pipeOwnership:OwnershipBoundary {
    ref part :>> evidence=tOriginal;
    attribute :>> id="shared-fifo-guard";
    attribute :>> source="vendor/gambit/lib/_io.scm";
    attribute :>> anchor="##make-vect-pipe-port;##make-vector-port;##make-string-port;##make-u8vector-port";
    attribute :>> invariant="Both endpoint constructors receive the same mutex before peer/shared FIFO publication; predicate read, registration, publication and close use the same guard";
    attribute :>> removedWork="Retire endpoint-private locks for shared state and post-construction lock replacement; mutex allocations per pair2 to1";
    attribute :>> remaining="Pair-wide serialization can reduce bidirectional throughput; exact latency/memory delta unmeasured; existing wait atomicity, timeout reentry and GC root premises remain";
    attribute :>> model="models/gambit/pipe_close_wait.qnt";
    attribute :>> modelReceipt="evidence/model-results/pipe-close-wait.json";
    attribute :>> abstractPremise="shared=true before checkEmpty/acquireWriter; registerWait atomically releases predicate lock; bounded one-direction conservation only";
  }
  part producerWitness:OwnershipBoundary {
    ref part :>> evidence=tProducer;
    attribute :>> id="native-producer-ancestry";
    attribute :>> source="src/gambit_smp/completed_producer.py;generation_artifacts.py;research_kernel.py";
    attribute :>> anchor="native_ancestry;export_reference;generation_artifact";
    attribute :>> invariant="Unchanged actual native bootstrap event and requalification witnesses join the current producer identity; existing generation consumer leases it and executes a real map test";
    attribute :>> removedWork="Reuse the completed SDK without reconstruction or fabricated Recipe ancestor; no extra source copy, profile or executor";
    attribute :>> remaining="Hash verification and leases add read work; external producer mutation rejects reuse; other mutable-origin consumer bridges and native completeness not implied";
    attribute :>> model="none:identity/source-refinement";
    attribute :>> modelReceipt="evidence/research/revision-admission/ownership-bootstrap-producer.json";
    attribute :>> abstractPremise="Distinct native reference; exact profile/input/generated/runtime/log witnesses; no duplicate QNT or Lean obligation";
  }


  part checkedResult:OwnershipBoundary {
    ref part :>> evidence=tOriginal;
    attribute :>> id="checked-result-control";
    attribute :>> source="vendor/gambit/include/_gambit/gvm_operations.h.in;gsc/_t-c-2.scm";
    attribute :>> anchor="FIXMULPCONSTY_NOTFALSEP;FIXMULPCONSTX_NOTFALSEP;FIXNEGP_NOTFALSEP;targ-apply-ifjump";
    attribute :>> invariant="Constant -1 multiplication returns the checked-negation success predicate and writes a numeric result only on success; generated C reads it only along the success edge. Minimum fixnum takes the existing fallback/exception edge. CONSTX delegates to the same CONSTY owner";
    attribute :>> removedWork="Remove duplicated success manufacture from the value-returning helper; no root slot, runtime record, allocation or representation field added";
    attribute :>> remaining="Original whole GSC inventory and other target/word-width cohorts remain separate; the real local regression establishes the selected current C23 cohort only. Correct exceptional branching is required work, not a measured speedup";
    attribute :>> model="none:sequential-delegation-source-law-and-native-regression";
    attribute :>> modelReceipt="evidence/research/revision-admission/checked-predicate-results.json";
    attribute :>> abstractPremise="For multiplier -1, success iff x differs from MIN_FIX; then out=-x. On failure the output is not consumed. Existing negation helper owns both outcomes; no duplicate QNT or Lean state machine";
  }

  part gerbilSurface:OwnershipBoundary {
    ref part :>> evidence=tGerbil;
    attribute :>> id="gerbil-build-surface";
    attribute :>> source="Gerbil1cfb032:compiler/driver.ss;runtime/gambit.ss;build0.scm;build0-lib.scm;build-libgerbil.ss;std/make.ss;host gerbil/repository.bzl";
    attribute :>> anchor="gsc-compile-file;-obj;-link;_gambit#.scm;libgambit;GerbilModuleBuild planning/frontend/readiness/execution";
    attribute :>> invariant="Preserved namespaces and exported contracts remain usable through existing Gerbil build frontdoors; compiler CLI, macro phase, module linkage and new native cohort are coherent";
    attribute :>> removedWork="Avoid a parallel Gerbil namespace or alternate build frontdoor; internal Gambit restructuring is consumed through the existing interfaces";
    attribute :>> remaining="Exact downstream producer binding and actual build/runtime acceptance missing; a pinned source audit or namespace equality cannot supply T-GERBIL. Native old-ABI artifacts may be invalidated and rebuilt";
    attribute :>> model="dev/architecture/toolchain/models/sysml/gerbil-module-build.sysml; existing build assurance/QNT/Lean obligations remain owned there";
    attribute :>> modelReceipt="evidence/research/revision-admission/gerbil-build-contract.json";
    attribute :>> abstractPremise="Planning/front-end/readiness/execution preserve their actual source-duty edges; unchanged Scheme namespaces do not imply compiler-option, phase, ABI or artifact identity equivalence";
  }

  part def MigrationBoundary {
    ref part question:Question;
    attribute id:String; attribute category:String; attribute preserved:String;
    attribute replaceable:String; attribute admission:String; attribute source:String;
  }
  part languageContract:MigrationBoundary { ref part :>> question=qMulti;
    attribute :>> id="scheme-language-contract";
    attribute :>> category="semantic";
    attribute :>> preserved="Observable Scheme control, proper tail calls, multi-shot continuation, dynamic-wind, shared identity and GC root correctness";
    attribute :>> replaceable="Internal frame, root, worker, scheduler and calling representations";
    attribute :>> admission="Actual interpreter/compiler/continuation/root tests under the new cohort; a stale binary or historical pass is not evidence";
    attribute :>> source="lib/_std.scm;gsc/_t-c-1.scm;_mem/continuation-roots.inc;tests/frame-continuation.scm";
  }
  part foreignMigration:MigrationBoundary { ref part :>> question=qFfi;
    attribute :>> id="foreign-consumer-migration";
    attribute :>> category="migration";
    attribute :>> preserved="Root/resource custody, allocation reloading, result and exception semantics at changed Scheme/C boundaries";
    attribute :>> replaceable="C signatures, function tables, marker/root APIs and layouts; migrate all producers and consumers together";
    attribute :>> admission="No blanket old ABI requirement; list actual consumers and validate them under the new declarations/runtime";
    attribute :>> source="include/_gambit/runtime_protocols.h.in;global_state.h.in;lib/_mem/rc-allocation.inc;lib/c_intf.c;examples/tcltk/tcltk.scm";
  }
  part internalRetirement:MigrationBoundary { ref part :>> question=qRetire;
    attribute :>> id="internal-responsibility-retirement";
    attribute :>> category="retirement";
    attribute :>> preserved="One canonical semantic/ownership authority and C portability";
    attribute :>> replaceable="Carrier-owned fields, old visitor paths, duplicated locks and old helper interfaces";
    attribute :>> admission="Delete obsolete paths after actual generator/caller/scanner/exit consumers migrate; no parallel compatibility layer";
    attribute :>> source="lib/setup.c;_mem/root-origins.inc;include/_gambit/runtime_roles.h.in";
  }
  part binaryCohort:MigrationBoundary { ref part :>> question=qFfi;
    attribute :>> id="binary-cohort-admission";
    attribute :>> category="artifact";
    attribute :>> preserved="Only representation-coherent code and data may execute together";
    attribute :>> replaceable="Previous binary objects/modules may be discarded and rebuilt";
    attribute :>> admission="Default rebuilt cohort; old binaries need actual rejection or specific layout/signature evidence. Version and size checks alone are insufficient";
    attribute :>> source="lib/setup.c:setup_module;native_development.py:native_object_context";
  }

  part def Stage { attribute id : String; attribute status : String; attribute exitCriterion : String; }
  part design : Stage { attribute :>> id="semantic-contract"; attribute :>> status="scoped-design-and-open-premises"; attribute :>> exitCriterion="Source owners, semantic invariants, paper questions and dependency cuts explicitly recorded"; }
  part compilerContext:OwnershipBoundary {
    ref part :>> evidence=tOriginal;
    attribute :>> id="compiler-context";
    attribute :>> source="vendor/gambit/tests/run-unit-tests.scm";
    attribute :>> anchor="compiler-runtime-options;test-using-mode;run-gsi-under-debugger";
    attribute :>> invariant="One compilation action owns p1 and full-buffered artifact output; test execution independently inherits requested p3 and unchanged console settings. Existing namespace and original test bodies/caps remain unchanged";
    attribute :>> removedWork="Three concurrent compiler VMs start three initial Scheme participants instead of nine; completed core/generation inputs survive a test-driver-only change";
    attribute :>> remaining="Matched prim_port control passes with byte-identical C, but whole379/300 and numeric90 aggregate still require current qualification; not a quota on C subprocesses or all OS threads";
    attribute :>> model="GerbilModuleBuild::execution and existing toolchain resource obligations";
    attribute :>> modelReceipt="evidence/research/revision-admission/construction-results.json";
    attribute :>> abstractPremise="Different execution roles have separate resource and artifact ownership; test population is not lowered to make compilation pass";
  }
  part reconstructionRoots:OwnershipBoundary {
    ref part :>> evidence=mRefine;
    attribute :>> id="reconstruction-roots";
    attribute :>> source="vendor/gambit/lib/_system.scm";
    attribute :>> anchor="gc-hash-table-reconstruction-begin;gc-hash-table-reconstruction-commit!;implode-gc-hash-table;deserialize!";
    attribute :>> invariant="Every installed heap key/value is scanned throughout partial construction; final weak/index policy and reconstruction debt publish after the payload stores";
    attribute :>> removedWork="Retire the two flags-zero construction windows; reuse one begin/commit protocol for both decoders without new per-object metadata";
    attribute :>> remaining="Constructor failure, incomplete cycles, caller root maps and raw FFI producers remain source/native obligations; a representative QNT slot is not a concrete C pointer proof";
    attribute :>> model="dev/refactoring/modern-c/models/quint/hash_index_owner.qnt; existing HashIndexOwner Lean transport premise";
    attribute :>> modelReceipt="evidence/research/revision-admission/construction-protocol.recipe.json";
    attribute :>> abstractPremise="QNT owns the partial-store/relocation/commit schedule; Lean owns the existing conditional semantic transport law; the native adapter must establish scanned references and policy publication";
  }
  part contextInitialization:OwnershipBoundary {
    ref part :>> evidence=mRefine;
    ref part lifetimeQuestion=qLifetime;
    attribute :>> id="context-initialization-permit";
    attribute :>> source="vendor/gambit/lib/setup.c;vendor/gambit/lib/_mem/capacity-resize.inc";
    attribute :>> anchor="setup_vmstate;setup_pstate;reserve_vm_resize";
    attribute :>> invariant="Only the first primordial incarnation or a current INITIALIZING resize reservation with matching range, slot phase, generation and startup state may initialize context storage; admission precedes incarnation, bindings and sync writes";
    attribute :>> removedWork="Retire the inference that an empty cleanup escrow grants initialization; consume the existing reservation identity without another slot table or per-object field";
    attribute :>> remaining="Current bootstrap and three-origin no-debt/cleanup controls pass. Upstream setup/cleanup issuer admission and exclusive-caller premises remain unresolved; the leaf check is not a global VM lifecycle seal";
    attribute :>> model="Existing runtime_roles.qnt frozen-origin and participant premises; initialization is a C source refinement, not another schedule or Lean theorem";
    attribute :>> modelReceipt="evidence/research/revision-admission/context-initialization-results.json";
    attribute :>> abstractPremise="The real setup callers are initial VM setup and the closed resize coordinator; callbacks cannot recreate an already admitted live origin even when no cleanup payload is in flight";
  }
  part checkedIncrement:OwnershipBoundary {
    ref part :>> evidence=tOriginal;
    attribute :>> id="checked-vector-increment";
    attribute :>> source="vendor/gambit/gsc/_prims.scm";
    attribute :>> anchor="make-ref-set!-cas!-inc!-expander;value-check;index-value-check";
    attribute :>> invariant="Safe specialization evaluates operands once, validates increment and old element only after vector/index admission, then performs one unsafe atomic mutation or the authoritative Scheme error fallback";
    attribute :>> removedWork="Remove the unsafe gap in general-vector increment specialization; no parallel safe primitive or namespace";
    attribute :>> remaining="No typed atomic claim for concurrent writers that replace a fixnum with arbitrary values; whole original-suite acceptance is still required";
    attribute :>> model="Existing Scheme primitive specialization contract and native counterexamples; no duplicate QNT or Lean scheduler";
    attribute :>> modelReceipt="evidence/research/revision-admission/construction-results.json";
    attribute :>> abstractPremise="Short-circuit index checks precede element access; rejected operations preserve the vector; default and explicit deltas return the old value";
  }
  part source : Stage { attribute :>> id="source-cut"; attribute :>> status="current-tree-bound;construction-and-safe-specialization-replaced;aggregate-admission-open"; attribute :>> exitCriterion="Representation and consumers replaced; exact proposed Git tree and dependencies bound to tests; no fallback aliases or unrelated staged changes; regenerated tracked products reconciled explicitly"; }
  part projection : Stage { attribute :>> id="scoped-controls"; attribute :>> status="object-fixtures-and-local-models-checked"; attribute :>> exitCriterion="Recorded profile object controls and model negative controls; this does not replace bootstrap"; }
  part cohort : Stage { attribute :>> id="generated-cohort"; attribute :>> status="research-tree-bootstrap-pass;submission-tree-unselected;prior600-timeout-retained"; attribute :>> exitCriterion="Regenerate and link matching compiler, embedded C, runtime and modules on the proposed source using the existing Bazel profile; historical failed bootstrap remains failed; default and SMP products retain their separate contexts"; }
  part semantics : Stage { attribute :>> id="semantic-lifecycle-acceptance"; attribute :>> status="preceding-c925-native-campaign-pass;exact-first-submission-tests-unselected"; attribute :>> exitCriterion="Real map multi-shot plus GC, RC roots, resize, FFI and failure custody controls, original inventories and affected modular SMP cases; source-model bridge and explicit twelve-gate applicability"; }
  part submit : Stage { attribute :>> id="commit-admission"; attribute :>> status="blocked"; attribute :>> exitCriterion="Five ASCENT gates ready for the exact candidate; no unresolved mandatory question or missing required test"; }
  part def Dependency { ref part sourceStage : Stage; ref part targetStage : Stage; }
  part d0 : Dependency { ref part :>> sourceStage=design; ref part :>> targetStage=source; }
  part d1 : Dependency { ref part :>> sourceStage=source; ref part :>> targetStage=projection; }
  part d2 : Dependency { ref part :>> sourceStage=projection; ref part :>> targetStage=cohort; }
  part d3 : Dependency { ref part :>> sourceStage=cohort; ref part :>> targetStage=semantics; }
  part d4 : Dependency { ref part :>> sourceStage=semantics; ref part :>> targetStage=submit; }
}
