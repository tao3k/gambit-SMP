package GambitPrimitiveHeaderBinding { private import ScalarValues::*;
part def SourceRow { attribute key:String; attribute path:String; attribute needle:String; attribute obligation:String; }
part source0:SourceRow { attribute :>> key="scheme-primitive"; attribute :>> path="vendor/gambit/lib/_kernel.scm"; attribute :>> needle="(define-prim (##get-monotonic-time! u64vect i)"; attribute :>> obligation="Actual primitive source; native payload writes vector, no pure-operation claim"; }
part source1:SourceRow { attribute :>> key="macro-lowering"; attribute :>> path="vendor/gambit/lib/_gambit#.scm"; attribute :>> needle="(##define-syntax define-prim"; attribute :>> obligation="Macro transforms definition; compile-time primitive table controls inline choice"; }
part source2:SourceRow { attribute :>> key="front-primitive"; attribute :>> path="vendor/gambit/gsc/_front.scm"; attribute :>> needle="(proc-obj-primitive?-set!"; attribute :>> obligation="Global constant procedure branch marks primitive; not every arbitrary lambda"; }
part source3:SourceRow { attribute :>> key="main-demand"; attribute :>> path="vendor/gambit/gsc/_t-c-1.scm"; attribute :>> needle="(targ-use-prc proc #f)"; attribute :>> obligation="Main starts demanded before header"; }
part source4:SourceRow { attribute :>> key="other-supply"; attribute :>> path="vendor/gambit/gsc/_t-c-1.scm"; attribute :>> needle="(targ-use-prc proc #t)"; attribute :>> obligation="Non-tree-shaken procedures are supplied; not necessarily demanded"; }
part source5:SourceRow { attribute :>> key="primitive-use"; attribute :>> path="vendor/gambit/gsc/_t-c-1.scm"; attribute :>> needle="(targ-use-glo (string->symbol name) supply?)"; attribute :>> obligation="Primitive discovery updates resource roles before dump"; }
part source6:SourceRow { attribute :>> key="entry-lookup"; attribute :>> path="vendor/gambit/gsc/_t-c-1.scm"; attribute :>> needle="(table-ref targ-glo-vars glo #f)"; attribute :>> obligation="Idempotence requires same interned symbol and existing entry"; }
part source7:SourceRow { attribute :>> key="demand-write"; attribute :>> path="vendor/gambit/gsc/_t-c-1.scm"; attribute :>> needle="(targ-rsrc-demanders-set! (cdr x) '(\"\"))"; attribute :>> obligation="False use normalizes the whole demander list even when entry exists"; }
part source8:SourceRow { attribute :>> key="supply-write"; attribute :>> path="vendor/gambit/gsc/_t-c-1.scm"; attribute :>> needle="(targ-rsrc-suppliers-set! (cdr x) '(\"\"))"; attribute :>> obligation="True use normalizes the whole supplier list"; }
part source9:SourceRow { attribute :>> key="absent-insert"; attribute :>> path="vendor/gambit/gsc/_t-c-1.scm"; attribute :>> needle="(table-set! targ-glo-vars glo (cons y r))"; attribute :>> obligation="Absent entry allocates unresolved cell; cannot replace by readonly lookup"; }
part source10:SourceRow { attribute :>> key="vector-writer"; attribute :>> path="vendor/gambit/gsc/_t-c-1.scm"; attribute :>> needle="(vector-set! r 1 demanders)"; attribute :>> obligation="Value idempotence does not remove physical setter or alias observation"; }
part source11:SourceRow { attribute :>> key="snapshot-alias"; attribute :>> path="vendor/gambit/gsc/_t-c-1.scm"; attribute :>> needle="(map targ-glo-rsrc glo-list)"; attribute :>> obligation="Resource vectors remain shared, classification must snapshot values at read time"; }
part source12:SourceRow { attribute :>> key="header-snd"; attribute :>> path="vendor/gambit/gsc/_t-c-1.scm"; attribute :>> needle="(targ-write-rsrc-names 'globals-s-nd"; attribute :>> obligation="Header serializes supplied/not-demanded before dump-mod"; }
part source13:SourceRow { attribute :>> key="index-write"; attribute :>> path="vendor/gambit/gsc/_t-c-1.scm"; attribute :>> needle="(targ-cell-set! (cadr g) i)"; attribute :>> obligation="Global index assigned after header and before native binding"; }
part source14:SourceRow { attribute :>> key="mod-call"; attribute :>> path="vendor/gambit/gsc/_t-c-1.scm"; attribute :>> needle="(targ-dump-mod prm-list c-inits sym-list key-list)"; attribute :>> obligation="Module output consumes extracted primitive roster"; }
part source15:SourceRow { attribute :>> key="late-demand"; attribute :>> path="vendor/gambit/gsc/_t-c-1.scm"; attribute :>> needle="(targ-use-glo (string->symbol name) #f)"; attribute :>> obligation="Native helper invoked twice, first use need not be idempotent"; }
part source16:SourceRow { attribute :>> key="prm-call"; attribute :>> path="vendor/gambit/gsc/_t-c-1.scm"; attribute :>> needle="(def-mod-prm-glo \"DEF_MOD_PRM\")"; attribute :>> obligation="First binding block precedes C init"; }
part source17:SourceRow { attribute :>> key="c-init"; attribute :>> path="vendor/gambit/gsc/_t-c-1.scm"; attribute :>> needle="(targ-display x)"; attribute :>> obligation="Opaque C initializer between binding blocks requires exact text custody"; }
part source18:SourceRow { attribute :>> key="glo-call"; attribute :>> path="vendor/gambit/gsc/_t-c-1.scm"; attribute :>> needle="(def-mod-prm-glo \"DEF_MOD_GLO\")"; attribute :>> obligation="Second binding block must use same slot/name/label"; }
part source19:SourceRow { attribute :>> key="runtime-prm"; attribute :>> path="vendor/gambit/include/gambit.h.in"; attribute :>> needle="#define ___DEF_MOD_PRM(i,glo,n)___PRM(i,glo)=___MLBL(n);"; attribute :>> obligation="setup_mod primitive-slot store distinct from init_mod global store"; }
part source20:SourceRow { attribute :>> key="runtime-glo"; attribute :>> path="vendor/gambit/include/gambit.h.in"; attribute :>> needle="#define ___DEF_MOD_GLO(i,glo,n)___GLO(i,glo)=___MLBL(n);"; attribute :>> obligation="Profile-dependent macro semantics; no preprocessing performed"; }
part source21:SourceRow { attribute :>> key="artifact-prm"; attribute :>> path="vendor/gambit/lib/_kernel.c"; attribute :>> needle="___DEF_MOD_PRM(146,___G__23__23_get_2d_monotonic_2d_time_21_,828)"; attribute :>> obligation="Existing artifact supplies exact binding tuple, no fresh generation claim"; }
part source22:SourceRow { attribute :>> key="artifact-glo"; attribute :>> path="vendor/gambit/lib/_kernel.c"; attribute :>> needle="___DEF_MOD_GLO(146,___G__23__23_get_2d_monotonic_2d_time_21_,828)"; attribute :>> obligation="Independent second binding span must agree with tuple"; }
part source23:SourceRow { attribute :>> key="artifact-header"; attribute :>> path="vendor/gambit/lib/_kernel.c"; attribute :>> needle="( #|*/\"*/\"globals-s-nd|#"; attribute :>> obligation="Header section membership is independently read from artifact bytes"; }
part source24:SourceRow { attribute :>> key="artifact-provenance"; attribute :>> path="vendor/gambit/lib/_kernel.c"; attribute :>> needle="produced by Gambit v4.9.8"; attribute :>> obligation="Embedded version alone cannot bind generator revision or Darwin flags"; }
part source25:SourceRow { attribute :>> key="c2-use-1396"; attribute :>> path="vendor/gambit/gsc/_t-c-2.scm"; attribute :>> needle="(targ-use-glo name #f)"; attribute :>> obligation="Other native global-use writer; phase-specific closure must include this caller"; }
part source26:SourceRow { attribute :>> key="c2-use-2278"; attribute :>> path="vendor/gambit/gsc/_t-c-2.scm"; attribute :>> needle="(targ-use-glo name #f)"; attribute :>> obligation="Other native global-use writer; phase-specific closure must include this caller"; }
part source27:SourceRow { attribute :>> key="c2-use-2337"; attribute :>> path="vendor/gambit/gsc/_t-c-2.scm"; attribute :>> needle="(targ-use-glo name #t)"; attribute :>> obligation="Other native global-use writer; phase-specific closure must include this caller"; }
part source28:SourceRow { attribute :>> key="c2-use-2383"; attribute :>> path="vendor/gambit/gsc/_t-c-2.scm"; attribute :>> needle="(targ-use-glo name #f)"; attribute :>> obligation="Other native global-use writer; phase-specific closure must include this caller"; }
part source29:SourceRow { attribute :>> key="c2-use-2413"; attribute :>> path="vendor/gambit/gsc/_t-c-2.scm"; attribute :>> needle="(targ-use-glo name #t))))"; attribute :>> obligation="Other native global-use writer; phase-specific closure must include this caller"; }
part source30:SourceRow { attribute :>> key="c2-use-2439"; attribute :>> path="vendor/gambit/gsc/_t-c-2.scm"; attribute :>> needle="(targ-use-glo name #t)"; attribute :>> obligation="Other native global-use writer; phase-specific closure must include this caller"; }
part def ClaimRow { attribute key:String; attribute mechanism:String; attribute condition:String; attribute result:String; attribute gap:String; }
part claim0:ClaimRow { attribute :>> key="roles"; attribute :>> mechanism="Two temporal projections"; attribute :>> condition="Capture header values before native helper writes"; attribute :>> result="Header s-nd and native binding coexist"; attribute :>> gap="Current-source generation provenance OPEN"; }
part claim1:ClaimRow { attribute :>> key="idempotence"; attribute :>> mechanism="Demand setter maps payload to singleton"; attribute :>> condition="Same interned key and entry identity; no intervening mutation"; attribute :>> result="Second value update redundant; first may change classification"; attribute :>> gap="Physical-write removal requires alias observer closure"; }
part claim2:ClaimRow { attribute :>> key="spans"; attribute :>> mechanism="Independent byte parser for existing C"; attribute :>> condition="Exact SHA and half-open byte intervals"; attribute :>> result="Two binding tuple spans agree with global and host labels"; attribute :>> gap="Full ModuleSpec encoder and native expansion OPEN"; }
part def GainRow { attribute key:String; attribute avoided:String; attribute added:String; attribute condition:String; }
part gain0:GainRow { attribute :>> key="two-helpers"; attribute :>> avoided="2P emission-time use-glo calls and existing-entry setters; artifact P=455 gives 910 calls"; attribute :>> added="P immutable binding records plus 2P readonly consumers"; attribute :>> condition="Producer closure proves entries and indices; no missing-use error changes"; }
part gain1:GainRow { attribute :>> key="header"; attribute :>> avoided="Repeated role classification for C and Spec in proposed dual consumers"; attribute :>> added="One owned header snapshot; copy cost H"; attribute :>> condition="Only savings against dual-consumer design; current compiler already writes header once"; }
part gain2:GainRow { attribute :>> key="binding"; attribute :>> avoided="Repeated name conversion and binding tuple derivation"; attribute :>> added="P records; span metadata O(P); byte verification O(C)"; attribute :>> condition="Share encoding without alias retention; no measured speedup"; }
part gain3:GainRow { attribute :>> key="macos"; attribute :>> avoided="No directly established preprocessing or startup saving"; attribute :>> added="Same C bytes retain downstream compile work"; attribute :>> condition="Darwin improvement requires separate artifact reuse or C emission redesign"; }
part gain4:GainRow { attribute :>> key="net"; attribute :>> avoided="2P mutation-capable uses plus duplicate work D"; attribute :>> added="Planning K + owned storage S + byte verification V + profile qualification A"; attribute :>> condition="Positive only if avoided work exceeds K+S+V+A; no numeric timing claim"; }
part def ContractRow { attribute fromNode:String; attribute toNode:String; attribute custody:String; }
part contract0:ContractRow { attribute :>> fromNode="Scheme primitive"; attribute :>> toNode="Discovery"; attribute :>> custody="semantics"; }
part contract1:ContractRow { attribute :>> fromNode="Discovery"; attribute :>> toNode="HeaderRoleSnapshot"; attribute :>> custody="roles at read"; }
part contract2:ContractRow { attribute :>> fromNode="HeaderRoleSnapshot"; attribute :>> toNode="Layout"; attribute :>> custody="indices"; }
part contract3:ContractRow { attribute :>> fromNode="Layout"; attribute :>> toNode="BindingPlan"; attribute :>> custody="slot and label"; }
part contract4:ContractRow { attribute :>> fromNode="BindingPlan"; attribute :>> toNode="PRM output"; attribute :>> custody="setup"; }
part contract5:ContractRow { attribute :>> fromNode="PRM output"; attribute :>> toNode="C init"; attribute :>> custody="ordered text"; }
part contract6:ContractRow { attribute :>> fromNode="C init"; attribute :>> toNode="GLO output"; attribute :>> custody="init"; }
part contract7:ContractRow { attribute :>> fromNode="HeaderRoleSnapshot"; attribute :>> toNode="ModuleSpec witness"; attribute :>> custody="header spans"; }
part contract8:ContractRow { attribute :>> fromNode="GLO output"; attribute :>> toNode="ModuleSpec witness"; attribute :>> custody="binding spans"; }
part contract9:ContractRow { attribute :>> fromNode="ModuleSpec witness"; attribute :>> toNode="Pair receipt"; attribute :>> custody="verify + close"; }
part def BindingRow { attribute actionName:String; attribute lemma:String; attribute scope:String; }
part binding0:BindingRow { attribute :>> actionName="primitive_header_binding.seedSupply"; attribute :>> lemma="PrimitiveHeader.seedSupplyPreserves"; attribute :>> scope="Actual extracted sequential step; native alias and C11 refinement external"; }
part binding1:BindingRow { attribute :>> actionName="primitive_header_binding.seedDemand"; attribute :>> lemma="PrimitiveHeader.seedDemandPreserves"; attribute :>> scope="Actual extracted sequential step; native alias and C11 refinement external"; }
part binding2:BindingRow { attribute :>> actionName="primitive_header_binding.seedOtherDemand"; attribute :>> lemma="PrimitiveHeader.seedOtherDemandPreserves"; attribute :>> scope="Actual extracted sequential step; native alias and C11 refinement external"; }
part binding3:BindingRow { attribute :>> actionName="primitive_header_binding.writeHeader"; attribute :>> lemma="PrimitiveHeader.writeHeaderPreserves"; attribute :>> scope="Actual extracted sequential step; native alias and C11 refinement external"; }
part binding4:BindingRow { attribute :>> actionName="primitive_header_binding.emitPrm"; attribute :>> lemma="PrimitiveHeader.emitPrmPreserves"; attribute :>> scope="Actual extracted sequential step; native alias and C11 refinement external"; }
part binding5:BindingRow { attribute :>> actionName="primitive_header_binding.emitGlo"; attribute :>> lemma="PrimitiveHeader.emitGloPreserves"; attribute :>> scope="Actual extracted sequential step; native alias and C11 refinement external"; }
part binding6:BindingRow { attribute :>> actionName="primitive_header_binding.sealSpec"; attribute :>> lemma="PrimitiveHeader.sealSpecPreserves"; attribute :>> scope="Actual extracted sequential step; native alias and C11 refinement external"; }
part binding7:BindingRow { attribute :>> actionName="primitive_header_binding.checkCoverage"; attribute :>> lemma="PrimitiveHeader.checkCoveragePreserves"; attribute :>> scope="Actual extracted sequential step; native alias and C11 refinement external"; }
part binding8:BindingRow { attribute :>> actionName="primitive_header_binding.closePair"; attribute :>> lemma="PrimitiveHeader.closePairPreserves"; attribute :>> scope="Actual extracted sequential step; native alias and C11 refinement external"; }
part binding9:BindingRow { attribute :>> actionName="primitive_header_binding.issue"; attribute :>> lemma="PrimitiveHeader.issuePreserves"; attribute :>> scope="Actual extracted sequential step; native alias and C11 refinement external"; }
part binding10:BindingRow { attribute :>> actionName="primitive_header_binding.unknownOutput"; attribute :>> lemma="PrimitiveHeader.unknownOutputPreserves"; attribute :>> scope="Actual extracted sequential step; native alias and C11 refinement external"; }
part binding11:BindingRow { attribute :>> actionName="primitive_header_binding.rejectLateUse"; attribute :>> lemma="PrimitiveHeader.rejectLateUsePreserves"; attribute :>> scope="Actual extracted sequential step; native alias and C11 refinement external"; }
part def ProofRow { attribute key:String; attribute lemma:String; }
part proof0:ProofRow { attribute :>> key="step"; attribute :>> lemma="PrimitiveHeader.stepPreserves"; }
part proof1:ProofRow { attribute :>> key="reachable"; attribute :>> lemma="PrimitiveHeader.reachableSafe"; }
part proof2:ProofRow { attribute :>> key="header"; attribute :>> lemma="PrimitiveHeader.lateBindingKeepsHeader"; }
part proof3:ProofRow { attribute :>> key="pair"; attribute :>> lemma="PrimitiveHeader.receiptNeedsPair"; }
part proof4:ProofRow { attribute :>> key="demand-idempotent"; attribute :>> lemma="PrimitiveBindingAlgebra.demandIdempotent"; }
part proof5:ProofRow { attribute :>> key="supply-idempotent"; attribute :>> lemma="PrimitiveBindingAlgebra.supplyIdempotent"; }
part proof6:ProofRow { attribute :>> key="exact"; attribute :>> lemma="PrimitiveBindingAlgebra.exactDemandUnchanged"; }
part proof7:ProofRow { attribute :>> key="classification"; attribute :>> lemma="PrimitiveBindingAlgebra.classificationUnchanged"; }
part proof8:ProofRow { attribute :>> key="supplier"; attribute :>> lemma="PrimitiveBindingAlgebra.supplierPreserved"; }
part proof9:ProofRow { attribute :>> key="counterexample"; attribute :>> lemma="PrimitiveBindingAlgebra.suppliedOnlyChangesHeader"; }
part proof10:ProofRow { attribute :>> key="payload"; attribute :>> lemma="PrimitiveBindingAlgebra.noncanonicalChangesPayload"; }
part proof11:ProofRow { attribute :>> key="span"; attribute :>> lemma="PrimitiveBindingAlgebra.correspondenceRequiresBoth"; }
part proof12:ProofRow { attribute :>> key="width"; attribute :>> lemma="PrimitiveBindingAlgebra.equalWidthsInsufficient"; }
part def MigrationRow { attribute key:String; attribute producerAnchor:String; attribute consumerAnchor:String; attribute actionName:String; attribute lemma:String; }
part migration0:MigrationRow { attribute :>> key="header-values"; attribute :>> producerAnchor="snapshot-alias"; attribute :>> consumerAnchor="header-snd"; attribute :>> actionName="primitive_header_binding.writeHeader"; attribute :>> lemma="PrimitiveHeader.writeHeaderPreserves"; }
part migration1:MigrationRow { attribute :>> key="readonly-plan"; attribute :>> producerAnchor="index-write"; attribute :>> consumerAnchor="late-demand"; attribute :>> actionName="primitive_header_binding.emitPrm"; attribute :>> lemma="PrimitiveHeader.emitPrmPreserves"; }
part migration2:MigrationRow { attribute :>> key="both-stores"; attribute :>> producerAnchor="prm-call"; attribute :>> consumerAnchor="glo-call"; attribute :>> actionName="primitive_header_binding.emitGlo"; attribute :>> lemma="PrimitiveHeader.emitGloPreserves"; }
part migration3:MigrationRow { attribute :>> key="pair-close"; attribute :>> producerAnchor="artifact-prm"; attribute :>> consumerAnchor="artifact-glo"; attribute :>> actionName="primitive_header_binding.issue"; attribute :>> lemma="PrimitiveHeader.receiptNeedsPair"; }
part history:GambitAssuranceRouting::ModelNeed { ref part :>> owner=GambitAssuranceRelations::modelUse2; attribute :>> obligationId="PH-history"; attribute :>> kind="interleaving"; attribute :>> subjectPath="dev/refactoring/modern-c/models/quint/primitive_header_binding.qnt"; attribute :>> subjectScope="11 representative histories; sequential temporal roles, no parallel implementation"; attribute :>> premise="Design research only; no native permission"; }
part induction:GambitAssuranceRouting::ModelNeed { ref part :>> owner=GambitAssuranceRelations::modelUse2; attribute :>> obligationId="PH-induction"; attribute :>> kind="induction"; attribute :>> subjectPath="dev/refactoring/modern-c/models/lean/PrimitiveHeader.lean"; attribute :>> subjectScope="All extracted steps preserve conditional invariant"; attribute :>> premise="Design research only; no native permission"; }
part algebra:GambitAssuranceRouting::ModelNeed { ref part :>> owner=GambitAssuranceRelations::modelUse2; attribute :>> obligationId="PH-algebra"; attribute :>> kind="induction"; attribute :>> subjectPath="dev/refactoring/modern-c/models/lean/PrimitiveBindingAlgebra.lean"; attribute :>> subjectScope="Exact payload idempotence and symbolic spans; no native encoder proof"; attribute :>> premise="Design research only; no native permission"; }
part projection:GambitAssuranceRouting::ModelNeed { ref part :>> owner=GambitAssuranceRelations::modelUse2; attribute :>> obligationId="PH-projection"; attribute :>> kind="restricted-projection"; attribute :>> subjectPath="dev/refactoring/modern-c/models/lean/PrimitiveHeaderAst.lean"; attribute :>> subjectScope="Checked binding identities field kinds supported expressions action roster; parser trusted"; attribute :>> premise="Design research only; no native permission"; }
part source:GambitAssuranceRouting::ModelNeed { ref part :>> owner=GambitAssuranceRelations::modelUse2; attribute :>> obligationId="PH-source"; attribute :>> kind="source-refinement"; attribute :>> subjectPath="dev/refactoring/modern-c/primitive-header-binding-design.org"; attribute :>> subjectScope="Entire writer alias GC exception closure and selected artifact generation provenance OPEN"; attribute :>> premise="Design research only; no native permission"; }
part emission:GambitAssuranceRouting::ModelNeed { ref part :>> owner=GambitAssuranceRelations::modelUse2; attribute :>> obligationId="PH-emission"; attribute :>> kind="emitter-fidelity"; attribute :>> subjectPath="dev/refactoring/modern-c/primitive-header-binding-design.org"; attribute :>> subjectScope="All C constructors and exact full ModuleSpec codec coverage OPEN"; attribute :>> premise="Design research only; no native permission"; }
part platform:GambitAssuranceRouting::ModelNeed { ref part :>> owner=GambitAssuranceRelations::modelUse2; attribute :>> obligationId="PH-platform"; attribute :>> kind="native-memory-order"; attribute :>> subjectPath="dev/refactoring/modern-c/primitive-header-binding-design.org"; attribute :>> subjectScope="C11 snapshot publication and macro profile qualification OPEN"; attribute :>> premise="Design research only; no native permission"; }

part def CallerRow { attribute key:String; attribute caller:String; attribute phase:String; attribute effect:String; attribute condition:String; }
part caller0:CallerRow { attribute :>> key="global-jump"; attribute :>> caller="targ-gen-jump"; attribute :>> phase="glo operand jump"; attribute :>> effect="demand false"; attribute :>> condition="Registration happens while converting procedures; preserve safe/unsafe jump distinction"; }
part caller1:CallerRow { attribute :>> key="boxed-read"; attribute :>> caller="targ-repr-opnd-boxed"; attribute :>> phase="boxed global operand"; attribute :>> effect="demand false"; attribute :>> condition="Uses global-ID form after registering demand"; }
part caller2:CallerRow { attribute :>> key="boxed-write"; attribute :>> caller="targ-repr-loc-boxed"; attribute :>> phase="boxed global location"; attribute :>> effect="supply true"; attribute :>> condition="Preserve SET_GLO and value boxing requirements"; }
part caller3:CallerRow { attribute :>> key="operand-read"; attribute :>> caller="targ-opnd"; attribute :>> phase="generic global operand"; attribute :>> effect="demand false"; attribute :>> condition="Location helper can call this after supplying; same key may become both"; }
part caller4:CallerRow { attribute :>> key="location-read"; attribute :>> caller="targ-loc-opnd"; attribute :>> phase="global location operand"; attribute :>> effect="supply then demand"; attribute :>> condition="Supply call followed by targ-opnd; do not summarize as supply-only"; }
part caller5:CallerRow { attribute :>> key="location-write"; attribute :>> caller="targ-loc-no-invalidate"; attribute :>> phase="generic global store"; attribute :>> effect="supply true"; attribute :>> condition="Preserve flonum-cache invalidation caller and SET_GLO"; }

part source31:SourceRow { attribute :>> key="label-constructor-intro"; attribute :>> path="vendor/gambit/include/gambit.h.in"; attribute :>> needle="#define ___DEF_LBL_INTRO("; attribute :>> obligation="One macro constructor per label table initializer; selected PROC ordinal differs from INTRO ordinal"; }
part source32:SourceRow { attribute :>> key="label-constructor-proc"; attribute :>> path="vendor/gambit/include/gambit.h.in"; attribute :>> needle="#define ___DEF_LBL_PROC("; attribute :>> obligation="One macro constructor per label table initializer; selected PROC ordinal differs from INTRO ordinal"; }
part source33:SourceRow { attribute :>> key="label-constructor-ret"; attribute :>> path="vendor/gambit/include/gambit.h.in"; attribute :>> needle="#define ___DEF_LBL_RET("; attribute :>> obligation="One macro constructor per label table initializer; selected PROC ordinal differs from INTRO ordinal"; }
}
