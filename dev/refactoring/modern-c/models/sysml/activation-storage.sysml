package GambitActivationStorage {
 private import ScalarValues::*;
 attribute stage:String="activation-storage";
 attribute baseline:String="c438df5cc193ea1a17102b3d0c72e4285cfea96c";
 attribute scope:String="Complete physical activation storage ownership: lifecycle-authenticated source owner acquires a fresh or clean idle record; known physical exit unlinks and returns all roots before offering one record to that RC domain; excess records free normally and domain cleanup drains the idle slot only after entry closure. No lock/check removed, no new registry/VM identity, no public GVM layout or Scheme heap/profile change.";
 attribute formalDuty:String="Existing native_entry_admission.qnt owns entry/root publication, revoked versus physical lifetime, unknown retention and settleKnown. RootSpan.lean retains count/range laws. Concrete C storage refinement may reuse an address only where the old implementation already freed that record after known final use. Idle storage is not a logical activation handle or scan root. No duplicate state machine/theorem and no recovery of unknown native effects.";
 attribute sourceCases:String="acquire;retire;rootlessness;cleanup;caller-custody";
 attribute requiredCases:String="storage;moving-pbt;teardown;original;cost;abi;model";
 attribute obligations:String="admissionProof;idle;physical;scan;drain;identity;benefit";
 attribute refinements:String="acquireMap;retireMap;drainMap";
 part def Obligation { attribute id:String; attribute status:String; attribute premise:String; }
 part admissionProof:Obligation { attribute :>> id="STORAGE-ENTRY"; attribute :>> status="CLOSED"; attribute :>> premise="Unchanged lifecycle_enter authenticates TLS/native owner, registry, VM phase, context/source and entry borrow before idle storage access. No safepoint/callback in acquisition."; }
 part idle:Obligation { attribute :>> id="STORAGE-IDLE"; attribute :>> status="CLOSED"; attribute :>> premise="One typed pointer per RC domain, not an unbounded pool. Constructor verifies IDLE/owner0/roots0/next0/markerFAL before take; active list insertion creates a new logical scope."; }
 part physical:Obligation { attribute :>> id="STORAGE-PHYSICAL"; attribute :>> status="CLOSED"; attribute :>> premise="Same known abort boundary unlinks first, returns root borrow/releases bank, clears every pointer and marker, then offers idle storage before last lifecycle_leave. Revoked, active and unknown physical extents remain live, never cached."; }
 part scan:Obligation { attribute :>> id="STORAGE-SCAN"; attribute :>> status="CLOSED"; attribute :>> premise="Idle record has no Scheme payload, marker or next-link and is absent from active list. Collector workers do not access the owner-only idle pointer. Existing registered banks/markers and multi-shot frames retain their original GC protocol."; }
 part drain:Obligation { attribute :>> id="STORAGE-DRAIN"; attribute :>> status="CLOSED"; attribute :>> premise="Existing entry closure and RC cleanup gate precede slot destruction. Live entry refuses VM cleanup; after abort the byte RC owner retains the detached domain to observe idle0 safely. Unknown join grants no stop/reuse permission."; }
 part identity:Obligation { attribute :>> id="STORAGE-IDENTITY"; attribute :>> status="CLOSED"; attribute :>> premise="Raw scope pointer expires at physical end as before malloc/free; reuse is not authority to use old pointers. Enum values preserved by appending IDLE; RC-private domain grows8 bytes, activation40 bytes. Public GVM layouts unchanged; final cost variant rebuilds byte-identically without resampling."; }
 part benefit:Obligation { attribute :>> id="STORAGE-BENEFIT"; attribute :>> status="CLOSED"; attribute :>> premise="One declared24-row matched cohort has favorable0/1/8 medians, complete RSS observations retained; native retained-cost bound is explicit. No stable universal percentage, old regression cause or whole SMP admission inferred."; }
 part def Refinement { attribute actions:String; attribute source:String; attribute guard:String; attribute obligation:String; attribute quint:String default="dev/refactoring/modern-c/models/quint/native_entry_admission.qnt"; attribute leanDuty:String default="RootSpan.lean size/count/address laws unchanged; no native lifecycle or scheduling theorem added."; }
 part acquireMap:Refinement { attribute :>> actions="jointIssue;writeEntryState"; attribute :>> source="lib/_setup/vm-registry.inc ___lifecycle_marker_prepare;lib/_mem/rc-allocation.inc setup_rc"; attribute :>> guard="Admitted cooperative native/source owner holds lifecycle entry before ordinary slot access. Reused storage must be clean; fresh allocation failure leaves through existing lifecycle_leave. No GC or callback observes partial metadata."; attribute :>> obligation="STORAGE-ENTRY"; }
 part retireMap:Refinement { attribute :>> actions="revokeMarker;settleKnown"; attribute :>> source="___lifecycle_marker_abort;existing ___end_sfun and marker/catcher callers"; attribute :>> guard="Revocation retains physical record/bank/entry. Only the prior final-use boundary unlinks/releases/clears the record. A raw pointer kept past that boundary was invalid in the old allocator too; no ABA-tolerant handle contract is introduced."; attribute :>> obligation="STORAGE-PHYSICAL"; }
 part drainMap:Refinement { attribute :>> actions="closeIngress;confirmGrace;retireCarrier"; attribute :>> source="lib/_setup/vm-lifecycle.inc lifecycle_close_context;lib/_mem/rc-allocation.inc rc_can_close/cleanup_rc"; attribute :>> guard="Existing lifecycle entry CAS publishes prior slot writes before entry0; teardown acquires entry closure and source gate. No worker reads idle storage. Unsettled/unknown owners still refuse cleanup. Only rootless IDLE state frees; native byte owner may retain detached domain for observation."; attribute :>> obligation="STORAGE-DRAIN"; }
 part submission:GambitCommitGates::SubmissionUnit { attribute :>> kind="integration"; attribute :>> result="activation-storage"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="STORAGE-TESTS"; attribute :>> method="native"; attribute :>> artifact="evidence/research/retained/modern-c/activation-storage/qualification.json"; attribute :>> scope="Actual clean reuse, nested/middle unlink/GC, live cleanup refusal/detached drain, original408, existing frame/SFUN/RC/VM consumers and matched24 samples; no increased heap/time limits."; }
 part learning:Need { ref part :>> gate=GambitCommitGates::learning; attribute :>> id="STORAGE-LEARNING"; attribute :>> method="source-analysis"; attribute :>> artifact="dev/refactoring/modern-c/activation-storage.org"; attribute :>> scope="RC source owns bounded rootless native storage instead of unconditional allocator churn; logical activation/root ownership stays distinct from reusable address."; }
 part process:Need { ref part :>> gate=GambitCommitGates::process; attribute :>> id="STORAGE-PROCESS"; attribute :>> method="source-analysis"; attribute :>> artifact="dev/refactoring/modern-c/activation-storage.org"; attribute :>> scope="One complete acquire/known-exit/root-return/reuse/domain-cleanup chain. Existing13-stage catalogue and12 independent SMP families do not advance from a small control or cache speed claim."; }
 part models:Need { ref part :>> gate=GambitCommitGates::models; attribute :>> id="STORAGE-MODELS"; attribute :>> method="native"; attribute :>> artifact="evidence/research/retained/modern-c/activation-storage/qualification.json"; attribute :>> scope="Actual OpenSysML SDK and shared ASCENT current/missing/stale controls, strict positive-benefit publication gate, existing disjoint QNT/Lean references only."; }
 part questions:Need { ref part :>> gate=GambitCommitGates::questions; attribute :>> id="STORAGE-QUESTIONS"; attribute :>> method="source-analysis"; attribute :>> artifact="dev/refactoring/modern-c/activation-storage.org"; attribute :>> scope="No GC in original regression, same entry instruction operands except rebased stubs, hardware cause unresolved; actual request allocation work retired, all retained/native costs and lifetime/unknown boundaries explicit."; }
}
