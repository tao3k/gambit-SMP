package GambitFrameWeakCoverage { private import ScalarValues::*;
part def Source { attribute key:String; attribute path:String; attribute needle:String; attribute obligation:String; }
part source0:Source { attribute :>> key="private-exclusion"; attribute :>> path="vendor/gambit/lib/mem.c"; attribute :>> needle="!(scan_ptr >= alloc_heap_chunk_start && scan_ptr < work->context->mem.alloc_heap_ptr_))"; attribute :>> obligation="Initial chunk exclusion is interval-local, not whole-chain protection"; }
part source1:Source { attribute :>> key="rollover"; attribute :>> path="vendor/gambit/lib/mem.c"; attribute :>> needle="alloc_heap_chunk_start = work->context->mem.alloc_heap_ptr_;"; attribute :>> obligation="New section/chunk start can differ while scan_ptr stays in prior chunk"; }
part source2:Source { attribute :>> key="capacity-before-fixup"; attribute :>> path="vendor/gambit/lib/mem.c"; attribute :>> needle="while (alloc + words + ___SUBTYPED_BODY > limit)"; attribute :>> obligation="Next fresh frame can publish previous chunk before writing previous ptr"; }
part source3:Source { attribute :>> key="frame-ready"; attribute :>> path="vendor/gambit/lib/mem.c"; attribute :>> needle="publish_object_scan (work, copy_header);"; attribute :>> obligation="All publisher call sites inventoried; frame publisher follows initial copied payload"; }
part source4:Source { attribute :>> key="pending-link"; attribute :>> path="vendor/gambit/lib/mem.c"; attribute :>> needle="ptr = &___FP_STK(alloc,link+1);"; attribute :>> obligation="Cursor retains preceding copied-frame link address"; }
part source5:Source { attribute :>> key="new-frame-fixup"; attribute :>> path="vendor/gambit/lib/mem.c"; attribute :>> needle="*ptr = forw;"; attribute :>> obligation="Next iteration mutates preceding frame link after its READY"; }
part source6:Source { attribute :>> key="already-forwarded-fixup"; attribute :>> path="vendor/gambit/lib/mem.c"; attribute :>> needle="*ptr = ra2; /* already copied, replace by forwarding pointer */"; attribute :>> obligation="Separate fixup branch exists; capacity witness uses the fresh-frame branch"; }
part source7:Source { attribute :>> key="copy-lock"; attribute :>> path="vendor/gambit/lib/mem.c"; attribute :>> needle="MISC_MEM_LOCK();\n\n      next_frame:"; attribute :>> obligation="Copier holds global memory lock; this alone does not exclude frame scanner"; }
part source8:Source { attribute :>> key="scanner-read"; attribute :>> path="vendor/gambit/lib/mem.c"; attribute :>> needle="frame = ___FP_STK(fp,descriptor.link+1);"; attribute :>> obligation="Frame scanner snapshots link before its temporary write"; }
part source9:Source { attribute :>> key="scanner-hide"; attribute :>> path="vendor/gambit/lib/mem.c"; attribute :>> needle="___FP_SET_STK(fp,descriptor.link+1,___FAL)"; attribute :>> obligation="Scanner temporary store can overlap copier fixup"; }
part source10:Source { attribute :>> key="scanner-restore"; attribute :>> path="vendor/gambit/lib/mem.c"; attribute :>> needle="___FP_SET_STK(fp,descriptor.link+1,___TAG(___UNTAG_AS(frame, ___tFIXNUM), ___tSUBTYPED))"; attribute :>> obligation="Restore uses earlier snapshot; SC schedule can lose newer fixup"; }
part source11:Source { attribute :>> key="steal"; attribute :>> path="vendor/gambit/lib/mem.c"; attribute :>> needle="scan_complete_heap_chunk (work, ptr+1);"; attribute :>> obligation="Other carrier executes scanner after FIFO dequeue without taking copy lock at frame entry"; }
part source12:Source { attribute :>> key="root-scan-then-steal"; attribute :>> path="vendor/gambit/lib/mem.c"; attribute :>> needle="mark_execution_roots (work,"; attribute :>> obligation="Workers enter their own reachable-work loop after their roots; no intervening root-only collective barrier"; }
part source13:Source { attribute :>> key="strong-weak-barrier"; attribute :>> path="vendor/gambit/lib/mem.c"; attribute :>> needle="garbage_collect_mark_strong_phase (work);\n\n  BARRIER();"; attribute :>> obligation="Strong closure precedes weak phase but does not serialize weak classification against weak marking"; }
part source14:Source { attribute :>> key="will-flag"; attribute :>> path="vendor/gambit/lib/mem.c"; attribute :>> needle="body[0] = body[0] | ___UNMARKED_TESTATOR_WILL;"; attribute :>> obligation="Strong will scan records omitted testator field"; }
part source15:Source { attribute :>> key="will-repair"; attribute :>> path="vendor/gambit/lib/mem.c"; attribute :>> needle="mark_array (work, tail_exec+___WILL_TESTATOR, 1);"; attribute :>> obligation="Executable and moved-to-executable paths directly repair testator"; }
part source16:Source { attribute :>> key="nonexec-repair"; attribute :>> path="vendor/gambit/lib/mem.c"; attribute :>> needle="mark_array (work, tail_nonexec+___WILL_TESTATOR, 1);"; attribute :>> obligation="Nonexecutable branch directly repairs testator"; }
part source17:Source { attribute :>> key="fresh-weak-will"; attribute :>> path="vendor/gambit/lib/mem.c"; attribute :>> needle="mark_array (work, body+1, 2); /* scan action and testator */"; attribute :>> obligation="Fresh weak-phase will scanner covers both fields"; }
part source18:Source { attribute :>> key="hash-register"; attribute :>> path="vendor/gambit/lib/mem.c"; attribute :>> needle="reached_gc_hash_tables = ___CAST(___WORD,body);"; attribute :>> obligation="Scanner registers table once; list retained until cleanup"; }
part source19:Source { attribute :>> key="hash-cleanup"; attribute :>> path="vendor/gambit/lib/mem.c"; attribute :>> needle="body[i] = ___DELETED;"; attribute :>> obligation="Weak cleanup forwards surviving references or deletes dead entries without tracing weak edges"; }
part source20:Source { attribute :>> key="will-layout"; attribute :>> path="vendor/gambit/include/gambit.h.in"; attribute :>> needle="#define ___WILL_TESTATOR 1"; attribute :>> obligation="NEXT flag and testator offsets match tail pointer arithmetic"; }
part source21:Source { attribute :>> key="hash-layout"; attribute :>> path="vendor/gambit/include/gambit.h.in"; attribute :>> needle="#define ___GCHASHTABLE_KEY0      5"; attribute :>> obligation="Key/value parity and MEM_ALLOC_KEYS determine collector footprint"; }
part def Footprint { attribute key:String; attribute required:String; attribute reuse:String; attribute premise:String; }
part footprint0:Footprint { attribute :>> key="ordinary closure symbol"; attribute :>> required="Same named/freevar/ordinary fields in strong and weak"; attribute :>> reuse="DONE may be reused after original scanner completes"; attribute :>> premise="Tail and frame fixup obligations remain separate"; }
part footprint1:Footprint { attribute :>> key="strong-scanned will"; attribute :>> required="Strong action only; NEXT flag records deferred testator"; attribute :>> reuse="process_wills repairs testator through destination body; DONE unchanged"; attribute :>> premise="Unique list ownership and flag preservation through list rewrites"; }
part footprint2:Footprint { attribute :>> key="fresh weak will"; attribute :>> required="Weak scanner traces action and testator together"; attribute :>> reuse="READY to OWNED to DONE normally"; attribute :>> premise="List/root update and queue publication must retain storage"; }
part footprint3:Footprint { attribute :>> key="strong hash fields"; attribute :>> required="Keys iff !WEAK_KEYS and MEM_ALLOC_KEYS; values iff !WEAK_VALS"; attribute :>> reuse="Same generic footprint in either phase; register reached list once"; attribute :>> premise="Flags stable and scan owner unique"; }
part footprint4:Footprint { attribute :>> key="weak hash fields"; attribute :>> required="Not tracing roots; cleanup rewrites live references or deletes entries"; attribute :>> reuse="Cleanup consumes retained reached list after weak closure"; attribute :>> premise="All four weak-flag cases plus non-heap key mode; no ephemeron claim"; }
part footprint5:Footprint { attribute :>> key="new weak hash table"; attribute :>> required="Generic scanner sees it first in weak phase"; attribute :>> reuse="Strong-field policy plus reached-list registration unchanged"; attribute :>> premise="Existing reached list must not be reset at weak entry"; }
part footprint6:Footprint { attribute :>> key="captured frame"; attribute :>> required="Descriptor root runs plus RA; link temporarily hidden/restored"; attribute :>> reuse="READY requires overlapping copier fixups settled or synchronized"; attribute :>> premise="Current post-READY write is not excluded by scan bitmap"; }
part footprint7:Footprint { attribute :>> key="still objects"; attribute :>> required="No movable scan-state bitmap in scan entry"; attribute :>> reuse="Still-mark/list ownership remains separate"; attribute :>> premise="Not covered by movable DONE uniqueness proof"; }
part def Contract { attribute fromNode:String; attribute toNode:String; attribute custody:String; }
part contract0:Contract { attribute :>> fromNode="private-chunk"; attribute :>> toNode="capacity-cut"; attribute :>> custody="exclude current cursor"; }
part contract1:Contract { attribute :>> fromNode="capacity-cut"; attribute :>> toNode="published-frame"; attribute :>> custody="legacy later chunk visible"; }
part contract2:Contract { attribute :>> fromNode="published-frame"; attribute :>> toNode="scanner-snapshot"; attribute :>> custody="READY allows scan"; }
part contract3:Contract { attribute :>> fromNode="scanner-snapshot"; attribute :>> toNode="copier-fixup"; attribute :>> custody="overlap is enabled"; }
part contract4:Contract { attribute :>> fromNode="copier-fixup"; attribute :>> toNode="stale-restore"; attribute :>> custody="lost link witness"; }
part contract5:Contract { attribute :>> fromNode="capacity-cut"; attribute :>> toNode="deferred-chunk"; attribute :>> custody="candidate retains custody"; }
part contract6:Contract { attribute :>> fromNode="deferred-chunk"; attribute :>> toNode="seal-frame"; attribute :>> custody="fill link before READY"; }
part contract7:Contract { attribute :>> fromNode="seal-frame"; attribute :>> toNode="published-sealed"; attribute :>> custody="release readiness and queue"; }
part contract8:Contract { attribute :>> fromNode="strong-DONE"; attribute :>> toNode="weak-repair"; attribute :>> custody="will testator flag"; }
part contract9:Contract { attribute :>> fromNode="strong-DONE"; attribute :>> toNode="cleanup-list"; attribute :>> custody="hash registration retained"; }
part contract10:Contract { attribute :>> fromNode="weak-repair"; attribute :>> toNode="weak-closure"; attribute :>> custody="settle derived work"; }
part contract11:Contract { attribute :>> fromNode="cleanup-list"; attribute :>> toNode="field-resolution"; attribute :>> custody="forward or delete"; }
part def Obligation { attribute key:String; attribute status:String; attribute scope:String; attribute gap:String; }
part obligation0:Obligation { attribute :>> key="legacy-source-path"; attribute :>> status="source-enabled-under-premises"; attribute :>> scope="Two capacity cuts with stale private cursor; fresh next frame; second worker may steal"; attribute :>> gap="No native input/configuration witness; no defined C11 outcome once racing stores occur"; }
part obligation1:Obligation { attribute :>> key="managed-frame"; attribute :>> status="proved-in-model"; attribute :>> scope="Delay READY and chunk visibility until pending link is fixed; all modeled steps preserve invariant"; attribute :>> gap="Whole chain staging capacity and descriptor/native mapping remain open"; }
part obligation2:Obligation { attribute :>> key="weak-field-coverage"; attribute :>> status="proved-in-model"; attribute :>> scope="Strong DONE retained; explicit will repair and table cleanup cover omitted fields"; attribute :>> gap="List aliasing flag lifetime and full C source refinement remain open"; }
part obligation3:Obligation { attribute :>> key="global-will-decision"; attribute :>> status="open"; attribute :>> scope="Shared testator strong reachability decision must precede weak marking across lists"; attribute :>> gap="Field coverage does not prove executability semantics"; }
part obligation4:Obligation { attribute :>> key="descriptor-validity"; attribute :>> status="open"; attribute :>> scope="RETI/RETN coordinates frame-size bounds and enough destination space"; attribute :>> gap="Source schedule assumes valid nonterminal frame chain spanning capacity cuts"; }
part obligation5:Obligation { attribute :>> key="c11-publication"; attribute :>> status="open"; attribute :>> scope="Post-fixup release READY and FIFO publication; acquire object claim"; attribute :>> gap="Existing atomics cannot publish later ordinary writes backwards"; }
part obligation6:Obligation { attribute :>> key="epoch-and-termination"; attribute :>> status="open"; attribute :>> scope="Scanner frame copier deferred batch derived work and two phase closures retain custody"; attribute :>> gap="No native completion or old storage retirement receipt issued"; }
part obligation7:Obligation { attribute :>> key="restricted-projection"; attribute :>> status="conditional-checked"; attribute :>> scope="Actual scalar typed IR invariant initial expressions and all-step roster emitted to Lean"; attribute :>> gap="Parser/emitter trusted; no verified full QNT or C semantics"; }
part def Gain { attribute key:String; attribute avoided:String; attribute added:String; attribute condition:String; }
part gain0:Gain { attribute :>> key="frame seal"; attribute :>> avoided="Prevent stale restoration of a newer chain fixup"; attribute :>> added="Pending-link record plus deferred chunk custody and seal checks"; attribute :>> condition="Correctness admission; no performance gain claimed"; }
part gain1:Gain { attribute :>> key="deferred allocation"; attribute :>> avoided="Keep allocating next frame without exposing mutable predecessor"; attribute :>> added="Candidate local closed-chunk list; requires no-allocation failure-safe storage"; attribute :>> condition="At most one pending predecessor per sequential chain; physical staging bound still conditional on frame fit"; }
part gain2:Gain { attribute :>> key="preserve DONE reuse"; attribute :>> avoided="Avoid an unnecessary whole-graph weak-phase reset/rescan"; attribute :>> added="Keep existing will repair and reached-table list adapters"; attribute :>> condition="Existing source benefit is baseline reuse, not new speedup"; }
part gain3:Gain { attribute :>> key="authorization cost"; attribute :>> avoided="Same object-state transitions can be retained with later READY"; attribute :>> added="Queue seals may add work; no extra state CAS is inherently required by model"; attribute :>> condition="C11 operation/footprint refinement before selecting representation"; }
part gain4:Gain { attribute :>> key="modern C retirement"; attribute :>> avoided="Retire early frame READY and unconditional publish for overlapping mutable frames"; attribute :>> added="New producer-owned readiness seal; keep forwarding frame decode weak cleanup and barriers"; attribute :>> condition="Only after both frame publishers/fixup branches and all consumers migrate"; }
part def Binding { attribute actionName:String; attribute lemma:String; attribute scope:String; }
part binding0:Binding { attribute :>> actionName="frame_publish_seal.rollInitial"; attribute :>> lemma="FrameSeal.rollInitialPreserves"; attribute :>> scope="Actual projected guard and update; native source refinement open"; }
part binding1:Binding { attribute :>> actionName="frame_publish_seal.copyA"; attribute :>> lemma="FrameSeal.copyAPreserves"; attribute :>> scope="Actual projected guard and update; native source refinement open"; }
part binding2:Binding { attribute :>> actionName="frame_publish_seal.readyEarly"; attribute :>> lemma="FrameSeal.readyEarlyPreserves"; attribute :>> scope="Actual projected guard and update; native source refinement open"; }
part binding3:Binding { attribute :>> actionName="frame_publish_seal.publishEarly"; attribute :>> lemma="FrameSeal.publishEarlyPreserves"; attribute :>> scope="Actual projected guard and update; native source refinement open"; }
part binding4:Binding { attribute :>> actionName="frame_publish_seal.deferChunk"; attribute :>> lemma="FrameSeal.deferChunkPreserves"; attribute :>> scope="Actual projected guard and update; native source refinement open"; }
part binding5:Binding { attribute :>> actionName="frame_publish_seal.fillLink"; attribute :>> lemma="FrameSeal.fillLinkPreserves"; attribute :>> scope="Actual projected guard and update; native source refinement open"; }
part binding6:Binding { attribute :>> actionName="frame_publish_seal.sealReady"; attribute :>> lemma="FrameSeal.sealReadyPreserves"; attribute :>> scope="Actual projected guard and update; native source refinement open"; }
part binding7:Binding { attribute :>> actionName="frame_publish_seal.publishDeferred"; attribute :>> lemma="FrameSeal.publishDeferredPreserves"; attribute :>> scope="Actual projected guard and update; native source refinement open"; }
part binding8:Binding { attribute :>> actionName="frame_publish_seal.claim"; attribute :>> lemma="FrameSeal.claimPreserves"; attribute :>> scope="Actual projected guard and update; native source refinement open"; }
part binding9:Binding { attribute :>> actionName="frame_publish_seal.readLink"; attribute :>> lemma="FrameSeal.readLinkPreserves"; attribute :>> scope="Actual projected guard and update; native source refinement open"; }
part binding10:Binding { attribute :>> actionName="frame_publish_seal.hideLink"; attribute :>> lemma="FrameSeal.hideLinkPreserves"; attribute :>> scope="Actual projected guard and update; native source refinement open"; }
part binding11:Binding { attribute :>> actionName="frame_publish_seal.restoreOld"; attribute :>> lemma="FrameSeal.restoreOldPreserves"; attribute :>> scope="Actual projected guard and update; native source refinement open"; }
part binding12:Binding { attribute :>> actionName="frame_publish_seal.restoreFixed"; attribute :>> lemma="FrameSeal.restoreFixedPreserves"; attribute :>> scope="Actual projected guard and update; native source refinement open"; }
part binding13:Binding { attribute :>> actionName="frame_publish_seal.releaseCopier"; attribute :>> lemma="FrameSeal.releaseCopierPreserves"; attribute :>> scope="Actual projected guard and update; native source refinement open"; }
part binding14:Binding { attribute :>> actionName="frame_publish_seal.close"; attribute :>> lemma="FrameSeal.closePreserves"; attribute :>> scope="Actual projected guard and update; native source refinement open"; }
part binding15:Binding { attribute :>> actionName="weak_done_coverage.configStrong"; attribute :>> lemma="WeakCoverage.configStrongPreserves"; attribute :>> scope="Actual projected guard and update; native source refinement open"; }
part binding16:Binding { attribute :>> actionName="weak_done_coverage.configWeakKey"; attribute :>> lemma="WeakCoverage.configWeakKeyPreserves"; attribute :>> scope="Actual projected guard and update; native source refinement open"; }
part binding17:Binding { attribute :>> actionName="weak_done_coverage.configWeakVal"; attribute :>> lemma="WeakCoverage.configWeakValPreserves"; attribute :>> scope="Actual projected guard and update; native source refinement open"; }
part binding18:Binding { attribute :>> actionName="weak_done_coverage.configWeakBoth"; attribute :>> lemma="WeakCoverage.configWeakBothPreserves"; attribute :>> scope="Actual projected guard and update; native source refinement open"; }
part binding19:Binding { attribute :>> actionName="weak_done_coverage.configRawKey"; attribute :>> lemma="WeakCoverage.configRawKeyPreserves"; attribute :>> scope="Actual projected guard and update; native source refinement open"; }
part binding20:Binding { attribute :>> actionName="weak_done_coverage.deadKey"; attribute :>> lemma="WeakCoverage.deadKeyPreserves"; attribute :>> scope="Actual projected guard and update; native source refinement open"; }
part binding21:Binding { attribute :>> actionName="weak_done_coverage.deadVal"; attribute :>> lemma="WeakCoverage.deadValPreserves"; attribute :>> scope="Actual projected guard and update; native source refinement open"; }
part binding22:Binding { attribute :>> actionName="weak_done_coverage.traceKey"; attribute :>> lemma="WeakCoverage.traceKeyPreserves"; attribute :>> scope="Actual projected guard and update; native source refinement open"; }
part binding23:Binding { attribute :>> actionName="weak_done_coverage.traceVal"; attribute :>> lemma="WeakCoverage.traceValPreserves"; attribute :>> scope="Actual projected guard and update; native source refinement open"; }
part binding24:Binding { attribute :>> actionName="weak_done_coverage.tableScanDone"; attribute :>> lemma="WeakCoverage.tableScanDonePreserves"; attribute :>> scope="Actual projected guard and update; native source refinement open"; }
part binding25:Binding { attribute :>> actionName="weak_done_coverage.strongWill"; attribute :>> lemma="WeakCoverage.strongWillPreserves"; attribute :>> scope="Actual projected guard and update; native source refinement open"; }
part binding26:Binding { attribute :>> actionName="weak_done_coverage.enterWeak"; attribute :>> lemma="WeakCoverage.enterWeakPreserves"; attribute :>> scope="Actual projected guard and update; native source refinement open"; }
part binding27:Binding { attribute :>> actionName="weak_done_coverage.repairWill"; attribute :>> lemma="WeakCoverage.repairWillPreserves"; attribute :>> scope="Actual projected guard and update; native source refinement open"; }
part binding28:Binding { attribute :>> actionName="weak_done_coverage.freshWeakWill"; attribute :>> lemma="WeakCoverage.freshWeakWillPreserves"; attribute :>> scope="Actual projected guard and update; native source refinement open"; }
part binding29:Binding { attribute :>> actionName="weak_done_coverage.skipDone"; attribute :>> lemma="WeakCoverage.skipDonePreserves"; attribute :>> scope="Actual projected guard and update; native source refinement open"; }
part binding30:Binding { attribute :>> actionName="weak_done_coverage.finishWeak"; attribute :>> lemma="WeakCoverage.finishWeakPreserves"; attribute :>> scope="Actual projected guard and update; native source refinement open"; }
part binding31:Binding { attribute :>> actionName="weak_done_coverage.cleanupTable"; attribute :>> lemma="WeakCoverage.cleanupTablePreserves"; attribute :>> scope="Actual projected guard and update; native source refinement open"; }
part binding32:Binding { attribute :>> actionName="weak_done_coverage.close"; attribute :>> lemma="WeakCoverage.closePreserves"; attribute :>> scope="Actual projected guard and update; native source refinement open"; }
part def Composition { attribute key:String; attribute lemma:String; attribute scope:String; }
part composition0:Composition { attribute :>> key="frame-induction"; attribute :>> lemma="FrameSeal.reachableSafe"; attribute :>> scope="All managed frame actions"; }
part composition1:Composition { attribute :>> key="frame-mode"; attribute :>> lemma="FrameSeal.reachableManaged"; attribute :>> scope="Managed mode remains enabled along modeled reachability"; }
part composition2:Composition { attribute :>> key="legacy-witness"; attribute :>> lemma="FrameSeal.legacyLostFixup"; attribute :>> scope="Exact projected SC update trace; source admissibility premises separate"; }
part composition3:Composition { attribute :>> key="weak-induction"; attribute :>> lemma="WeakCoverage.reachableSafe"; attribute :>> scope="All weak coverage actions"; }
part composition4:Composition { attribute :>> key="repair-reuse"; attribute :>> lemma="WeakCoverage.repairKeepsObjectDone"; attribute :>> scope="Testator repair does not reset object DONE"; }
part composition5:Composition { attribute :>> key="table-phase"; attribute :>> lemma="WeakCoverage.hashFootprintPhaseIndependent"; attribute :>> scope="Generic table footprint independent of phase"; }
part frameHistory:GambitAssuranceRouting::ModelNeed { ref part :>> owner=GambitBuildAssurance::planner.component; attribute :>> obligationId="FW-frameHistory"; attribute :>> kind="interleaving"; attribute :>> subjectPath="dev/refactoring/modern-c/models/quint/frame_publish_seal.qnt"; attribute :>> subjectScope="Managed frame protocol and legacy two-cut source schedule"; attribute :>> premise="Design and formal models only; no native qualification"; }
part weakHistory:GambitAssuranceRouting::ModelNeed { ref part :>> owner=GambitBuildAssurance::planner.component; attribute :>> obligationId="FW-weakHistory"; attribute :>> kind="interleaving"; attribute :>> subjectPath="dev/refactoring/modern-c/models/quint/weak_done_coverage.qnt"; attribute :>> subjectScope="One will one table flags and field obligations"; attribute :>> premise="Design and formal models only; no native qualification"; }
part frameInduction:GambitAssuranceRouting::ModelNeed { ref part :>> owner=GambitBuildAssurance::planner.component; attribute :>> obligationId="FW-frameInduction"; attribute :>> kind="induction"; attribute :>> subjectPath="dev/refactoring/modern-c/models/lean/FrameSeal.lean"; attribute :>> subjectScope="All projected managed steps and reachability"; attribute :>> premise="Design and formal models only; no native qualification"; }
part weakInduction:GambitAssuranceRouting::ModelNeed { ref part :>> owner=GambitBuildAssurance::planner.component; attribute :>> obligationId="FW-weakInduction"; attribute :>> kind="induction"; attribute :>> subjectPath="dev/refactoring/modern-c/models/lean/WeakCoverage.lean"; attribute :>> subjectScope="All projected weak coverage steps and reachability"; attribute :>> premise="Design and formal models only; no native qualification"; }
part projection:GambitAssuranceRouting::ModelNeed { ref part :>> owner=GambitBuildAssurance::planner.component; attribute :>> obligationId="FW-projection"; attribute :>> kind="restricted-projection"; attribute :>> subjectPath="dev/refactoring/modern-c/models/lean/FrameSealAst.lean"; attribute :>> subjectScope="Both scalar typed IR models with trusted emitter and exact rosters"; attribute :>> premise="Design and formal models only; no native qualification"; }
part source:GambitAssuranceRouting::ModelNeed { ref part :>> owner=GambitBuildAssurance::planner.component; attribute :>> obligationId="FW-source"; attribute :>> kind="source-refinement"; attribute :>> subjectPath="dev/refactoring/modern-c/frame-weak-coverage-design.org"; attribute :>> subjectScope="Source control-flow premises descriptor and producer closure open"; attribute :>> premise="Design and formal models only; no native qualification"; }
part platform:GambitAssuranceRouting::ModelNeed { ref part :>> owner=GambitBuildAssurance::planner.component; attribute :>> obligationId="FW-platform"; attribute :>> kind="c11-refinement"; attribute :>> subjectPath="dev/refactoring/modern-c/frame-weak-coverage-design.org"; attribute :>> subjectScope="Effective config release/acquire reset and lifecycle open"; attribute :>> premise="Design and formal models only; no native qualification"; }
part def Seam { ref part producer:GambitRuntimeComposition::BlueprintModule; ref part consumer:GambitRuntimeComposition::BlueprintModule; attribute contract:String; attribute modelNeed:String; }
part seam0:Seam { ref part :>> producer=GambitRuntimeComposition::blueprintModule4; ref part :>> consumer=GambitRuntimeComposition::blueprintModule4; attribute :>> contract="copier seal to scanner admission"; attribute :>> modelNeed="FW-frameHistory"; }
part seam1:Seam { ref part :>> producer=GambitRuntimeComposition::blueprintModule3; ref part :>> consumer=GambitRuntimeComposition::blueprintModule4; attribute :>> contract="frozen valid frame coordinates"; attribute :>> modelNeed="FW-source"; }
part seam2:Seam { ref part :>> producer=GambitRuntimeComposition::blueprintModule4; ref part :>> consumer=GambitRuntimeComposition::blueprintModule5; attribute :>> contract="weak field closure and collective phase transition"; attribute :>> modelNeed="FW-weakInduction"; }
part seam3:Seam { ref part :>> producer=GambitRuntimeComposition::blueprintModule4; ref part :>> consumer=GambitRuntimeComposition::blueprintModule1; attribute :>> contract="payload link and queue C11 publication"; attribute :>> modelNeed="FW-platform"; }

part source22:Source { attribute :>> key="frame-slot-coordinates"; attribute :>> path="vendor/gambit/include/gambit.h.in"; attribute :>> needle="#define ___FP_STK(fp,fpo)fp[-(fpo)]"; attribute :>> obligation="Copier end pointer and scanner body plus extra plus fs address the same link under matching descriptors"; }
part source23:Source { attribute :>> key="frame-extra"; attribute :>> path="vendor/gambit/include/gambit.h.in"; attribute :>> needle="#define ___FRAME_EXTRA_SLOTS 1"; attribute :>> obligation="Heap frame extra slot is used consistently by copy size and scanner base"; }
part composition6:Composition { attribute :>> key="frame-coordinate"; attribute :>> lemma="FrameSeal.frameLinkCoordinate"; attribute :>> scope="Heap pointer arithmetic alias conditional on matched RETI RETN descriptors and in-bounds storage"; }
}
