package GambitEntryAdmissionAudit {
 private import ScalarValues::*;
 attribute scope:String="Complete RC source/activation authority source/model/evidence companion. No independent SMP or universal speedup credit.";
 attribute stage:String="entry-admission-audit";
 attribute formalDuty:String="Native SDK and ASCENT bind seven obligations and three real source adapters. Existing QNT alone owns logical revocation, freeze and physical exit; unchanged Lean arithmetic only. Framework tests prove source custody, not native semantics.";
 part submission:GambitCommitGates::SubmissionUnit {
 attribute :>> kind="support"; attribute :>> result=""; attribute :>> progressDelta=0;
 attribute :>> supportPaths="dev/refactoring/modern-c/diagrams/entry-admission.d2;dev/refactoring/modern-c/diagrams/entry-admission.svg;dev/refactoring/modern-c/entry-admission.org;dev/refactoring/modern-c/index.org;dev/refactoring/modern-c/models/quint/native_entry_admission.qnt;dev/refactoring/modern-c/models/sysml/delivery-outcomes.sysml;dev/refactoring/modern-c/models/sysml/entry-admission-audit.sysml;dev/refactoring/modern-c/models/sysml/entry-admission.sysml;dev/refactoring/modern-c/models/sysml/pending-cuts.sysml;dev/refactoring/modern-c/revision-checklist.org;evidence/research/retained/modern-c/entry-admission/ascent-observation.json;evidence/research/retained/modern-c/entry-admission/assembly-analysis.json;evidence/research/retained/modern-c/entry-admission/baseline-source.json;evidence/research/retained/modern-c/entry-admission/delivery.json;evidence/research/retained/modern-c/entry-admission/framework-submission/review.json;evidence/research/retained/modern-c/entry-admission/framework-submission/validation.json;evidence/research/retained/modern-c/entry-admission/initial-model.json;evidence/research/retained/modern-c/entry-admission/metrics.json;evidence/research/retained/modern-c/entry-admission/model-binding.json;evidence/research/retained/modern-c/entry-admission/model-sources/dev/modeling/models/sysml/commit-gates.sysml;evidence/research/retained/modern-c/entry-admission/model-sources/dev/refactoring/modern-c/models/sysml/binding-activation.sysml;evidence/research/retained/modern-c/entry-admission/model-sources/dev/refactoring/modern-c/models/sysml/delivery-outcomes.sysml;evidence/research/retained/modern-c/entry-admission/model-sources/dev/refactoring/modern-c/models/sysml/delivery-plan.sysml;evidence/research/retained/modern-c/entry-admission/model-sources/dev/refactoring/modern-c/models/sysml/entry-admission.sysml;evidence/research/retained/modern-c/entry-admission/model-sources/dev/refactoring/modern-c/models/sysml/header-organization.sysml;evidence/research/retained/modern-c/entry-admission/model-sources/dev/refactoring/modern-c/models/sysml/pending-cuts.sysml;evidence/research/retained/modern-c/entry-admission/model-sources/dev/refactoring/modern-c/models/sysml/request-product.sysml;evidence/research/retained/modern-c/entry-admission/model-sources/dev/refactoring/modern-c/models/sysml/revision-delivery.sysml;evidence/research/retained/modern-c/entry-admission/model-sources/dev/refactoring/modern-c/models/sysml/root-write.sysml;evidence/research/retained/modern-c/entry-admission/model-sources/dev/refactoring/modern-c/models/sysml/sfun-entry.sysml;evidence/research/retained/modern-c/entry-admission/packet-normalization.json;evidence/research/retained/modern-c/entry-admission/pending-after.json;evidence/research/retained/modern-c/entry-admission/pending-inventory.json;evidence/research/retained/modern-c/entry-admission/post-ascent-observation.json;evidence/research/retained/modern-c/entry-admission/post-model-binding.json;evidence/research/retained/modern-c/entry-admission/post-model-sources/dev/modeling/models/sysml/commit-gates.sysml;evidence/research/retained/modern-c/entry-admission/post-model-sources/dev/refactoring/modern-c/models/sysml/binding-activation.sysml;evidence/research/retained/modern-c/entry-admission/post-model-sources/dev/refactoring/modern-c/models/sysml/delivery-outcomes.sysml;evidence/research/retained/modern-c/entry-admission/post-model-sources/dev/refactoring/modern-c/models/sysml/delivery-plan.sysml;evidence/research/retained/modern-c/entry-admission/post-model-sources/dev/refactoring/modern-c/models/sysml/entry-admission.sysml;evidence/research/retained/modern-c/entry-admission/post-model-sources/dev/refactoring/modern-c/models/sysml/header-organization.sysml;evidence/research/retained/modern-c/entry-admission/post-model-sources/dev/refactoring/modern-c/models/sysml/pending-cuts.sysml;evidence/research/retained/modern-c/entry-admission/post-model-sources/dev/refactoring/modern-c/models/sysml/request-product.sysml;evidence/research/retained/modern-c/entry-admission/post-model-sources/dev/refactoring/modern-c/models/sysml/revision-delivery.sysml;evidence/research/retained/modern-c/entry-admission/post-model-sources/dev/refactoring/modern-c/models/sysml/root-write.sysml;evidence/research/retained/modern-c/entry-admission/post-model-sources/dev/refactoring/modern-c/models/sysml/sfun-entry.sysml;evidence/research/retained/modern-c/entry-admission/qualification.json;evidence/research/retained/modern-c/entry-admission/runs/entry-admission-consumers-1.json;evidence/research/retained/modern-c/entry-admission/runs/entry-admission-cost-1.json;evidence/research/retained/modern-c/entry-admission/runs/entry-admission-native-1.json;evidence/research/retained/modern-c/entry-admission/selected-source.json;evidence/research/retained/modern-c/entry-admission/source-review.json;evidence/research/retained/modern-c/entry-admission/submission/admission.json;evidence/research/retained/modern-c/entry-admission/submission/comment.json;evidence/research/retained/modern-c/entry-admission/submission/model-contract.json;evidence/research/retained/modern-c/entry-admission/submission/revision.json;evidence/research/retained/modern-c/entry-admission/submission/source-manifest.json;evidence/research/retained/modern-c/entry-admission/submission/source.json;src/gambit_smp/native_development.py;src/gambit_smp/runtime_binding.py;tests/test_native_development.py;tests/test_runtime_binding.py";
 attribute :>> testModules="tests/test_native_development.py;tests/test_runtime_binding.py";
 }
 part def Need { ref part gate:GambitCommitGates::Gate; attribute id:String; attribute method:String; attribute artifact:String; attribute scope:String; }
 part tests:Need { ref part :>> gate=GambitCommitGates::tests; attribute :>> id="ENTRY-ADMISSION-AUDIT-TESTS"; attribute :>> method="native"; attribute :>> artifact="evidence/research/retained/modern-c/entry-admission/framework-submission/validation.json"; attribute :>> scope="39 unchanged source-selected framework tests reused by exact identity; independent runtime five-gate admission and17 native consumer checks retained."; }
 part learning:Need { ref part :>> gate=GambitCommitGates::learning; attribute :>> id="ENTRY-ADMISSION-AUDIT-LEARNING"; attribute :>> method="source-analysis"; attribute :>> artifact="dev/refactoring/modern-c/entry-admission.org"; attribute :>> scope="Borrowed storage lifetime is not activation permission; duplicate registration must respect the common source owner gate."; }
 part process:Need { ref part :>> gate=GambitCommitGates::process; attribute :>> id="ENTRY-ADMISSION-AUDIT-PROCESS"; attribute :>> method="source-analysis"; attribute :>> artifact="dev/refactoring/modern-c/entry-admission.org"; attribute :>> scope="One complete four-path RC/SFUN responsibility. Forty-eight original pending paths/nine groups remain separately owned; SMP stays1/12."; }
 part models:Need { ref part :>> gate=GambitCommitGates::models; attribute :>> id="ENTRY-ADMISSION-AUDIT-MODELS"; attribute :>> method="native"; attribute :>> artifact="evidence/research/retained/modern-c/entry-admission/framework-submission/review.json"; attribute :>> scope="Native SDK7 obligations/3 adapters, ASCENT missing/stale controls. Existing QNT13+13 cases/1000 entry traces; no duplicated Lean protocol."; }
 part questions:Need { ref part :>> gate=GambitCommitGates::questions; attribute :>> id="ENTRY-ADMISSION-AUDIT-QUESTIONS"; attribute :>> method="source-analysis"; attribute :>> artifact="dev/refactoring/modern-c/entry-admission.org"; attribute :>> scope="Actual retained-scope negative, valid pointer/stop premises, physical exit, ABI reuse and mixed native costs addressed conditionally."; }
}
