package GambitPrGsiAudit {
 private import ScalarValues::*;
 attribute scope:String="Complete fourth-family native acceptance, producer-owned private-constructor test refinement, exact ledger and generic foundation-versus-efficiency claim policy. No runtime source or later-family promotion.";
 attribute stage:String="pr-gsi-complete";
 attribute formalDuty:String="OpenSysML Python SDK resolves exact native populations and source identities. Existing ASCENT rules admit the fourth family and reject unsupported efficiency labels. QNT and Lean retain their existing distinct runtime ownership/frame duties.";
 part submission:GambitCommitGates::SubmissionUnit {
  attribute :>> kind="support"; attribute :>> result=""; attribute :>> progressDelta=0;
  attribute :>> supportPaths="dev/modeling/ascent/commit-admission.rules.scm;dev/refactoring/modern-c/branch-checklist.org;dev/refactoring/modern-c/diagrams/post-delivery.d2;dev/refactoring/modern-c/diagrams/pr-gsi.d2;dev/refactoring/modern-c/models/sysml/efficiency-claims.sysml;dev/refactoring/modern-c/models/sysml/pr-gsi-acceptance.sysml;dev/refactoring/modern-c/models/sysml/pr-gsi-audit.sysml;dev/refactoring/modern-c/pr-gsi.org;evidence/research/retained/modern-c/delivery-plan/current/accepted-smp-progress.json;evidence/research/retained/modern-c/pr-gsi/acceptance-reviewed.json;evidence/research/retained/modern-c/pr-gsi/acceptance.json;evidence/research/retained/modern-c/pr-gsi/ci-observation.json;evidence/research/retained/modern-c/pr-gsi/legacy-manifest.json;evidence/research/retained/modern-c/pr-gsi/legacy-request-failure.json;evidence/research/retained/modern-c/pr-gsi/manifest.json;evidence/research/retained/modern-c/pr-gsi/model-binding.json;evidence/research/retained/modern-c/pr-gsi/native-result.json;evidence/research/retained/modern-c/pr-gsi/original-full-suite.recipe.json;evidence/research/retained/modern-c/pr-gsi/original-pr-selection.recipe.json;evidence/research/retained/modern-c/pr-gsi/qualified-native.json;evidence/research/retained/modern-c/pr-gsi/request-constructor-refinement.json;evidence/research/retained/modern-c/pr-gsi/submission/review.json;evidence/research/retained/modern-c/pr-gsi/submission/tests.json;src/gambit_smp/revision_matrix.py;src/gambit_smp/revision_submission.py;src/gambit_smp/suite_coverage.py;src/gambit_smp/suite_primitives.py;tests/test_assertion_runtime.py;tests/test_native_suite.py;tests/test_revision_matrix.py;tests/test_revision_submission.py;tests/test_smp_completion.py;tests/test_suite_coverage.py";
  attribute :>> testModules="tests/test_native_suite.py;tests/test_suite_coverage.py;tests/test_assertion_runtime.py;tests/test_smp_completion.py;tests/test_revision_matrix.py;tests/test_revision_submission.py";
 }
 part def Need { ref part gate:GambitCommitGates::Gate; attribute id:String; attribute method:String; attribute artifact:String; attribute scope:String; }
 part tests:Need { ref part :>> gate=GambitCommitGates::tests; attribute :>> id="PR-GSI-TESTS"; attribute :>> method="native"; attribute :>> artifact="evidence/research/retained/modern-c/pr-gsi/submission/tests.json"; attribute :>> scope="Exact selected unittest modules and all new tampering controls pass with zero skips; full native p1/p2 PR populations independently complete."; }
 part learning:Need { ref part :>> gate=GambitCommitGates::learning; attribute :>> id="PR-GSI-LEARNING"; attribute :>> method="source-analysis"; attribute :>> artifact="dev/refactoring/modern-c/pr-gsi.org"; attribute :>> scope="Keep the runtime as the single request-layout owner and distinguish functional foundation from measured efficiency upgrades."; }
 part process:Need { ref part :>> gate=GambitCommitGates::process; attribute :>> id="PR-GSI-PROCESS"; attribute :>> method="source-analysis"; attribute :>> artifact="dev/refactoring/modern-c/branch-checklist.org"; attribute :>> scope="Independent4/12, eight later families; old1/12,2/12,3/12 remain immutable. Vendor stays32028f5d and39 pending paths stay unqualified."; }
 part models:Need { ref part :>> gate=GambitCommitGates::models; attribute :>> id="PR-GSI-MODELS"; attribute :>> method="native"; attribute :>> artifact="evidence/research/retained/modern-c/pr-gsi/submission/review.json"; attribute :>> scope="Real OpenSysML Python SDK projection, source-bound whole native population and shared ASCENT claim/benchmark refusal controls."; }
 part questions:Need { ref part :>> gate=GambitCommitGates::questions; attribute :>> id="PR-GSI-QUESTIONS"; attribute :>> method="source-analysis"; attribute :>> artifact="dev/refactoring/modern-c/pr-gsi.org"; attribute :>> scope="Prove the private constructor refinement, retain counterexamples and all assertions, state added costs and unmeasured pause/throughput/RSS."; }
}
