package GambitCacheReadyPublication { private import ScalarValues::*;
part def SourceRow { attribute key:String; attribute path:String; attribute needle:String; attribute limit:String; }
part source0:SourceRow { attribute :>> key="runtime-locks"; attribute :>> path="evidence/research/source-references/tcl/cbf86d62348d6b052e1961b4df995960fb21545f/generic/tclThreadAlloc.c"; attribute :>> needle="listLockPtr = TclpNewAllocMutex();"; attribute :>> limit="global init publishes this pointer before objLockPtr and bucket table complete"; }
part source1:SourceRow { attribute :>> key="runtime-buckets"; attribute :>> path="evidence/research/source-references/tcl/cbf86d62348d6b052e1961b4df995960fb21545f/generic/tclThreadAlloc.c"; attribute :>> needle="bucketInfo[i].blockSize = MINALLOC << i;"; attribute :>> limit="RuntimeServiceReady is a separate prerequisite"; }
part source2:SourceRow { attribute :>> key="tls-read"; attribute :>> path="evidence/research/source-references/tcl/cbf86d62348d6b052e1961b4df995960fb21545f/generic/tclThreadAlloc.c"; attribute :>> needle="cachePtr = TclpGetAllocCache();"; attribute :>> limit="no Constructing/Closing result in existing raw Cache pointer path"; }
part source3:SourceRow { attribute :>> key="cache-allocate"; attribute :>> path="evidence/research/source-references/tcl/cbf86d62348d6b052e1961b4df995960fb21545f/generic/tclThreadAlloc.c"; attribute :>> needle="cachePtr = TclpSysAlloc(sizeof(Cache), 0);"; attribute :>> limit="allocation success needs stable pre-reserved owner guard"; }
part source4:SourceRow { attribute :>> key="cache-panic"; attribute :>> path="evidence/research/source-references/tcl/cbf86d62348d6b052e1961b4df995960fb21545f/generic/tclThreadAlloc.c"; attribute :>> needle="Tcl_Panic(\"alloc: could not allocate new cache\");"; attribute :>> limit="existing allocation failure panics; no proposed typed error implementation"; }
part source5:SourceRow { attribute :>> key="cache-zero"; attribute :>> path="evidence/research/source-references/tcl/cbf86d62348d6b052e1961b4df995960fb21545f/generic/tclThreadAlloc.c"; attribute :>> needle="memset(cachePtr, 0, sizeof(Cache));"; attribute :>> limit="private payload initialization"; }
part source6:SourceRow { attribute :>> key="list-publish"; attribute :>> path="evidence/research/source-references/tcl/cbf86d62348d6b052e1961b4df995960fb21545f/generic/tclThreadAlloc.c"; attribute :>> needle="firstCachePtr = cachePtr;"; attribute :>> limit="source links list before owner and TLS installation"; }
part source7:SourceRow { attribute :>> key="cache-owner"; attribute :>> path="evidence/research/source-references/tcl/cbf86d62348d6b052e1961b4df995960fb21545f/generic/tclThreadAlloc.c"; attribute :>> needle="cachePtr->owner = Tcl_GetCurrentThread();"; attribute :>> limit="actual owner writer follows list unlock"; }
part source8:SourceRow { attribute :>> key="tls-write"; attribute :>> path="evidence/research/source-references/tcl/cbf86d62348d6b052e1961b4df995960fb21545f/generic/tclThreadAlloc.c"; attribute :>> needle="TclpSetAllocCache(cachePtr);"; attribute :>> limit="platform binding body not captured; void declaration is not failure receipt"; }
part source9:SourceRow { attribute :>> key="tls-prototype"; attribute :>> path="evidence/research/source-references/tcl/cbf86d62348d6b052e1961b4df995960fb21545f/generic/tclInt.h"; attribute :>> needle="MODULE_SCOPE void\tTclpSetAllocCache(void *);"; attribute :>> limit="no integer success/failure returned in captured interface"; }
part source10:SourceRow { attribute :>> key="fast-slot"; attribute :>> path="evidence/research/source-references/tcl/cbf86d62348d6b052e1961b4df995960fb21545f/generic/tclThreadAlloc.c"; attribute :>> needle="tcachePtr = GetCache();"; attribute :>> limit="HAVE_FAST_TSD direct TLS assignment after GetCache returns"; }
part source11:SourceRow { attribute :>> key="diagnostic-lock"; attribute :>> path="evidence/research/source-references/tcl/cbf86d62348d6b052e1961b4df995960fb21545f/generic/tclThreadAlloc.c"; attribute :>> needle="Tcl_MutexLock(listLockPtr);"; attribute :>> limit="Tcl_GetMemoryInfo holds list lock across output helpers"; }
part source12:SourceRow { attribute :>> key="diagnostic-callout"; attribute :>> path="evidence/research/source-references/tcl/cbf86d62348d6b052e1961b4df995960fb21545f/generic/tclThreadAlloc.c"; attribute :>> needle="Tcl_DStringAppendElement(dsPtr, buf);"; attribute :>> limit="formatter/append may allocate or call providers; no native closure proof"; }
part source13:SourceRow { attribute :>> key="stats-read"; attribute :>> path="evidence/research/source-references/tcl/cbf86d62348d6b052e1961b4df995960fb21545f/generic/tclThreadAlloc.c"; attribute :>> needle="cachePtr->buckets[n].numFree,"; attribute :>> limit="list lock does not alone prove synchronization with owner bucket writes"; }
part source14:SourceRow { attribute :>> key="list-unlink"; attribute :>> path="evidence/research/source-references/tcl/cbf86d62348d6b052e1961b4df995960fb21545f/generic/tclThreadAlloc.c"; attribute :>> needle="*nextPtrPtr = cachePtr->nextPtr;"; attribute :>> limit="actual unlink is under listLockPtr"; }
part source15:SourceRow { attribute :>> key="cache-free"; attribute :>> path="evidence/research/source-references/tcl/cbf86d62348d6b052e1961b4df995960fb21545f/generic/tclThreadAlloc.c"; attribute :>> needle="TclpSysFree(cachePtr);"; attribute :>> limit="known/unknown backend release must not be retried as absent"; }
part source16:SourceRow { attribute :>> key="tls-cleanup"; attribute :>> path="evidence/research/source-references/tcl/cbf86d62348d6b052e1961b4df995960fb21545f/generic/tclThreadAlloc.c"; attribute :>> needle="TclpFreeAllocCache(cachePtr);"; attribute :>> limit="thread finalization delegates platform TLS/free effects"; }
part source17:SourceRow { attribute :>> key="interp-cache"; attribute :>> path="evidence/research/source-references/tcl/cbf86d62348d6b052e1961b4df995960fb21545f/generic/tclBasic.c"; attribute :>> needle="iPtr->allocCache = (AllocCache *)TclpGetAllocCache();"; attribute :>> limit="interpreter prefix consumer must migrate with TLS getter contract"; }
part source18:SourceRow { attribute :>> key="prior"; attribute :>> path="dev/refactoring/modern-c/models/quint/node_storage_authority.qnt"; attribute :>> needle="action probeCurrentCache="; attribute :>> limit="actual parent metadata lease guard; layout/caller mirror is external"; }
part def ObligationRow { attribute key:String; attribute status:String; attribute condition:String; }
part obligation0:ObligationRow { attribute :>> key="ready-safety"; attribute :>> status="conditional-model"; attribute :>> condition="pre-reserved native guard, single builder epoch, stable record and atomic admission/pin domain"; }
part obligation1:ObligationRow { attribute :>> key="source-order"; attribute :>> status="source-bound"; attribute :>> condition="actual list-before-owner/TLS, void setter, fast TLS caller and diagnostic callouts captured"; }
part obligation2:ObligationRow { attribute :>> key="global-runtime"; attribute :>> status="unresolved"; attribute :>> condition="all allocator locks/bucket tables and bootstrap TLS ready before per-cache builder; no early pointer shortcut"; }
part obligation3:ObligationRow { attribute :>> key="tls-provider"; attribute :>> status="unresolved"; attribute :>> condition="same-thread install/clear/destructor receipts for platform TLS and fast handles; no silent pointer/descriptor ABI change"; }
part obligation4:ObligationRow { attribute :>> key="reentry"; attribute :>> status="unresolved"; attribute :>> condition="all allocator/owner/TLS/panic/format callbacks qualified; Constructing/Closing cannot wait on self or silently use private cache"; }
part obligation5:ObligationRow { attribute :>> key="diagnostic-snapshot"; attribute :>> status="unresolved"; attribute :>> condition="race-free owner snapshot or all-atomic payload plus defined consistency, owner-label lifetime and independent buffer cleanup"; }
part obligation6:ObligationRow { attribute :>> key="rollback-retirement"; attribute :>> status="unresolved"; attribute :>> condition="exact publication and free outcomes, alias detachment, native return domain and cleanup guard"; }
part obligation7:ObligationRow { attribute :>> key="c23-refinement"; attribute :>> status="unresolved"; attribute :>> condition="matching release/acquire epoch, atomic check-and-pin/close, all raw consumers and source-CFG/product refinement"; }
part def RouteRow { attribute actionName:String; attribute lemma:String; attribute source:String; attribute obligation:String; }
part route0:RouteRow { attribute :>> actionName="reserveConstruction"; attribute :>> lemma="CacheReadyPublication.reserveConstructionPreserves"; attribute :>> source="tls-read"; attribute :>> obligation="ready-safety"; }
part route1:RouteRow { attribute :>> actionName="allocateCandidate"; attribute :>> lemma="CacheReadyPublication.allocateCandidatePreserves"; attribute :>> source="cache-allocate"; attribute :>> obligation="ready-safety"; }
part route2:RouteRow { attribute :>> actionName="allocationRejected"; attribute :>> lemma="CacheReadyPublication.allocationRejectedPreserves"; attribute :>> source="cache-panic"; attribute :>> obligation="ready-safety"; }
part route3:RouteRow { attribute :>> actionName="initializeOwner"; attribute :>> lemma="CacheReadyPublication.initializeOwnerPreserves"; attribute :>> source="cache-owner"; attribute :>> obligation="ready-safety"; }
part route4:RouteRow { attribute :>> actionName="installTlsKnown"; attribute :>> lemma="CacheReadyPublication.installTlsKnownPreserves"; attribute :>> source="tls-write"; attribute :>> obligation="ready-safety"; }
part route5:RouteRow { attribute :>> actionName="installTlsUnknown"; attribute :>> lemma="CacheReadyPublication.installTlsUnknownPreserves"; attribute :>> source="tls-write"; attribute :>> obligation="ready-safety"; }
part route6:RouteRow { attribute :>> actionName="stageRegistryEntry"; attribute :>> lemma="CacheReadyPublication.stageRegistryEntryPreserves"; attribute :>> source="list-publish"; attribute :>> obligation="ready-safety"; }
part route7:RouteRow { attribute :>> actionName="publishKnown"; attribute :>> lemma="CacheReadyPublication.publishKnownPreserves"; attribute :>> source="list-publish"; attribute :>> obligation="ready-safety"; }
part route8:RouteRow { attribute :>> actionName="publishUnknownCommitted"; attribute :>> lemma="CacheReadyPublication.publishUnknownCommittedPreserves"; attribute :>> source="list-publish"; attribute :>> obligation="ready-safety"; }
part route9:RouteRow { attribute :>> actionName="publishUnknownAbsent"; attribute :>> lemma="CacheReadyPublication.publishUnknownAbsentPreserves"; attribute :>> source="list-publish"; attribute :>> obligation="ready-safety"; }
part route10:RouteRow { attribute :>> actionName="rejectPublication"; attribute :>> lemma="CacheReadyPublication.rejectPublicationPreserves"; attribute :>> source="list-publish"; attribute :>> obligation="ready-safety"; }
part route11:RouteRow { attribute :>> actionName="reconcileCommitted"; attribute :>> lemma="CacheReadyPublication.reconcileCommittedPreserves"; attribute :>> source="prior"; attribute :>> obligation="ready-safety"; }
part route12:RouteRow { attribute :>> actionName="reconcileAbsent"; attribute :>> lemma="CacheReadyPublication.reconcileAbsentPreserves"; attribute :>> source="prior"; attribute :>> obligation="ready-safety"; }
part route13:RouteRow { attribute :>> actionName="finishBuilder"; attribute :>> lemma="CacheReadyPublication.finishBuilderPreserves"; attribute :>> source="prior"; attribute :>> obligation="ready-safety"; }
part route14:RouteRow { attribute :>> actionName="publishFastHandle"; attribute :>> lemma="CacheReadyPublication.publishFastHandlePreserves"; attribute :>> source="fast-slot"; attribute :>> obligation="ready-safety"; }
part route15:RouteRow { attribute :>> actionName="constructionReentry"; attribute :>> lemma="CacheReadyPublication.constructionReentryPreserves"; attribute :>> source="tls-read"; attribute :>> obligation="ready-safety"; }
part route16:RouteRow { attribute :>> actionName="closingReentry"; attribute :>> lemma="CacheReadyPublication.closingReentryPreserves"; attribute :>> source="tls-cleanup"; attribute :>> obligation="ready-safety"; }
part route17:RouteRow { attribute :>> actionName="acquireReader"; attribute :>> lemma="CacheReadyPublication.acquireReaderPreserves"; attribute :>> source="fast-slot"; attribute :>> obligation="ready-safety"; }
part route18:RouteRow { attribute :>> actionName="releaseReader"; attribute :>> lemma="CacheReadyPublication.releaseReaderPreserves"; attribute :>> source="prior"; attribute :>> obligation="ready-safety"; }
part route19:RouteRow { attribute :>> actionName="qualifyStats"; attribute :>> lemma="CacheReadyPublication.qualifyStatsPreserves"; attribute :>> source="stats-read"; attribute :>> obligation="ready-safety"; }
part route20:RouteRow { attribute :>> actionName="beginDiagnostic"; attribute :>> lemma="CacheReadyPublication.beginDiagnosticPreserves"; attribute :>> source="diagnostic-lock"; attribute :>> obligation="ready-safety"; }
part route21:RouteRow { attribute :>> actionName="requestOwnerSnapshot"; attribute :>> lemma="CacheReadyPublication.requestOwnerSnapshotPreserves"; attribute :>> source="stats-read"; attribute :>> obligation="ready-safety"; }
part route22:RouteRow { attribute :>> actionName="ownerSnapshotAck"; attribute :>> lemma="CacheReadyPublication.ownerSnapshotAckPreserves"; attribute :>> source="stats-read"; attribute :>> obligation="ready-safety"; }
part route23:RouteRow { attribute :>> actionName="releaseDiagnosticPin"; attribute :>> lemma="CacheReadyPublication.releaseDiagnosticPinPreserves"; attribute :>> source="diagnostic-callout"; attribute :>> obligation="ready-safety"; }
part route24:RouteRow { attribute :>> actionName="formatSnapshot"; attribute :>> lemma="CacheReadyPublication.formatSnapshotPreserves"; attribute :>> source="diagnostic-callout"; attribute :>> obligation="ready-safety"; }
part route25:RouteRow { attribute :>> actionName="closeReady"; attribute :>> lemma="CacheReadyPublication.closeReadyPreserves"; attribute :>> source="tls-cleanup"; attribute :>> obligation="ready-safety"; }
part route26:RouteRow { attribute :>> actionName="unlinkEntry"; attribute :>> lemma="CacheReadyPublication.unlinkEntryPreserves"; attribute :>> source="list-unlink"; attribute :>> obligation="ready-safety"; }
part route27:RouteRow { attribute :>> actionName="clearTlsKnown"; attribute :>> lemma="CacheReadyPublication.clearTlsKnownPreserves"; attribute :>> source="tls-cleanup"; attribute :>> obligation="ready-safety"; }
part route28:RouteRow { attribute :>> actionName="clearFastKnown"; attribute :>> lemma="CacheReadyPublication.clearFastKnownPreserves"; attribute :>> source="fast-slot"; attribute :>> obligation="ready-safety"; }
part route29:RouteRow { attribute :>> actionName="attestNativeCleanup"; attribute :>> lemma="CacheReadyPublication.attestNativeCleanupPreserves"; attribute :>> source="cache-free"; attribute :>> obligation="ready-safety"; }
part route30:RouteRow { attribute :>> actionName="retireKnown"; attribute :>> lemma="CacheReadyPublication.retireKnownPreserves"; attribute :>> source="cache-free"; attribute :>> obligation="ready-safety"; }
part route31:RouteRow { attribute :>> actionName="rollbackUnknown"; attribute :>> lemma="CacheReadyPublication.rollbackUnknownPreserves"; attribute :>> source="cache-free"; attribute :>> obligation="ready-safety"; }
part route32:RouteRow { attribute :>> actionName="rollbackKnown"; attribute :>> lemma="CacheReadyPublication.rollbackKnownPreserves"; attribute :>> source="cache-free"; attribute :>> obligation="ready-safety"; }
part def GainRow { attribute key:String; attribute saved:String; attribute added:String; attribute condition:String; attribute status:String; }
part gain0:GainRow { attribute :>> key="ready-init"; attribute :>> saved="readers cannot obtain a complete managed handle from list membership before owner/TLS setup"; attribute :>> added="one logical Ready publication and exact epoch/lifetime validation"; attribute :>> condition="all consumers migrate; current raw list path does not implement gate"; attribute :>> status="conditional-model"; }
part gain1:GainRow { attribute :>> key="reentry"; attribute :>> saved="one candidate per modeled epoch; reentry sees Pending/Closing instead of second builder or self-wait"; attribute :>> added="pre-reserved NativeThreadDomain record and typed admission/bootstrap interface"; attribute :>> condition="legacy mandatory allocator APIs cannot silently return Pending"; attribute :>> status="conditional-model"; }
part gain2:GainRow { attribute :>> key="diagnostic-lock"; attribute :>> saved="move B+3 DString helper calls per cache outside global registry lock"; attribute :>> added="immutable snapshot of owner label plus7 scalar values per bucket and copy/lease handoff"; attribute :>> condition="C caches/B buckets; O(C*B) snapshot content; race-free stats source not yet qualified"; attribute :>> status="source-bound/conditional"; }
part gain3:GainRow { attribute :>> key="hot-path"; attribute :>> saved="owner-held Ready handle can avoid a new global atomic pin on every object allocation"; attribute :>> added="scope lifetime and close/fast-handle revocation still required"; attribute :>> condition="owner NativeThreadDomain remains live; raw fast pointer cannot bypass close"; attribute :>> status="design-only"; }
part gain4:GainRow { attribute :>> key="failure"; attribute :>> saved="distinguish committed-but-ACK-lost from rejected; prevent duplicate publication/free"; attribute :>> added="unknown install/publication/free may retain stable ownership indefinitely"; attribute :>> condition="native outcome receipts/reconciliation are external; no retry on assumption"; attribute :>> status="conditional-model"; }
part gain5:GainRow { attribute :>> key="retirement"; attribute :>> saved="potentially retire raw list-as-ready, untyped TLS getter and formatting-under-list-lock paths"; attribute :>> added="global init, fast/platform TLS, interpreter access, diagnostic and cleanup caller migration"; attribute :>> condition="all native evidence still required; old retired0 and no measured speedup"; attribute :>> status="unresolved"; }
part def IssuerRow { attribute key:String; attribute source:String; attribute signature:String; attribute gap:String; }
part issuer0:IssuerRow { attribute :>> key="thread-domain"; attribute :>> source="tls-read"; attribute :>> signature="stable nonallocating builder reservation before callout, allocation and TLS installation"; attribute :>> gap="bootstrap TLS/global services may allocate; no circular self-qualification"; }
part issuer1:IssuerRow { attribute :>> key="ready-owner"; attribute :>> source="list-publish"; attribute :>> signature="owner, storage and TLS known installed; Preparing entry then matching single Ready commit"; attribute :>> gap="list/TLS writes are not one atomic operation; legacy direct pointers must migrate"; }
part issuer2:IssuerRow { attribute :>> key="snapshot-owner"; attribute :>> source="stats-read"; attribute :>> signature="owner-safe coherent copy and legal captured owner label into independent preowned buffer"; attribute :>> gap="list lock alone, or plain-data seqlock retries, do not establish C23 safety"; }
part issuer3:IssuerRow { attribute :>> key="rollback-owner"; attribute :>> source="cache-free"; attribute :>> signature="known not published, list/TLS/fast aliases detached, then exact same-operation private release"; attribute :>> gap="unknown release retains metadata duty, not permission to dereference/re-free storage"; }
part issuer4:IssuerRow { attribute :>> key="close-owner"; attribute :>> source="tls-cleanup"; attribute :>> signature="close admission, settle builder outcome, drain readers/copy, clear aliases and known cleanup"; attribute :>> gap="source OS thread/return domain and shared provider lifetime remain independent"; }
part def ConsumerRow { attribute key:String; attribute source:String; attribute access:String; attribute lifetime:String; attribute limit:String; }
part consumer0:ConsumerRow { attribute :>> key="getcache"; attribute :>> source="tls-read"; attribute :>> access="Empty/Constructing/Ready/Closing descriptor in proposed service"; attribute :>> lifetime="stable owner reservation and matching cache epoch"; attribute :>> limit="actual raw pointer getter has no such tagged ABI"; }
part consumer1:ConsumerRow { attribute :>> key="fast-getcache"; attribute :>> source="fast-slot"; attribute :>> access="Ready handle under owner scope; no stale raw fast pointer after close"; attribute :>> lifetime="current OS thread and owner NativeThreadDomain"; attribute :>> limit="captured finalizer has no explicit tcachePtr reset; platform/legal reuse closure open"; }
part consumer2:ConsumerRow { attribute :>> key="interpreter"; attribute :>> source="interp-cache"; attribute :>> access="allocCache prefix obtained after interpreter allocation initializes cache"; attribute :>> lifetime="interpreter/cache ownership and canonical typed view"; attribute :>> limit="all callers and prefix layout must migrate together"; }
part consumer3:ConsumerRow { attribute :>> key="diagnostic"; attribute :>> source="diagnostic-lock"; attribute :>> access="capture/pin handles, release registry lock, request owner snapshot, unpin, then format"; attribute :>> lifetime="cache pin until copy ACK; independent snapshot afterward"; attribute :>> limit="mutable bucket stats need separate race-free source contract"; }
part consumer4:ConsumerRow { attribute :>> key="formatter"; attribute :>> source="diagnostic-callout"; attribute :>> access="owner label and scalar copy only; no raw cache/node/TLS dereference"; attribute :>> lifetime="stable diagnostic operation and buffer through formatting failure/reentry"; attribute :>> limit="current DString/format provider closure not captured"; }
part consumer5:ConsumerRow { attribute :>> key="cleanup"; attribute :>> source="tls-cleanup"; attribute :>> access="Closing entry prevents new readers, clears platform/fast/list aliases, drains native cleanup"; attribute :>> lifetime="stable supervisor and exact native owner"; attribute :>> limit="unknown outcomes and published cache cannot take private rollback path"; }
part def EdgeRow { attribute fromNode:String; attribute toNode:String; attribute contract:String; }
part edge0:EdgeRow { attribute :>> fromNode="Runtime services qualified"; attribute :>> toNode="Reserve Constructing ticket"; attribute :>> contract="global init/bootstrap TLS is an external prerequisite"; }
part edge1:EdgeRow { attribute :>> fromNode="Reserve Constructing ticket"; attribute :>> toNode="Private allocation and owner"; attribute :>> contract="nested call sees Pending; never waits behind own builder"; }
part edge2:EdgeRow { attribute :>> fromNode="Private allocation and owner"; attribute :>> toNode="TLS Preparing binding"; attribute :>> contract="known install only; unknown retains builder record"; }
part edge3:EdgeRow { attribute :>> fromNode="TLS Preparing binding"; attribute :>> toNode="Preparing registry entry"; attribute :>> contract="neither alias serves raw cache before canonical Ready"; }
part edge4:EdgeRow { attribute :>> fromNode="Preparing registry entry"; attribute :>> toNode="Ready commit"; attribute :>> contract="single release publication after full init, exact epoch and lifetime root"; }
part edge5:EdgeRow { attribute :>> fromNode="Ready commit"; attribute :>> toNode="Ready read / pin"; attribute :>> contract="acquire matching epoch; check+pin serialized with close"; }
part edge6:EdgeRow { attribute :>> fromNode="Ready read / pin"; attribute :>> toNode="Owner snapshot ACK"; attribute :>> contract="registry lock released; independent race-free stats copy"; }
part edge7:EdgeRow { attribute :>> fromNode="Owner snapshot ACK"; attribute :>> toNode="Unpin then format"; attribute :>> contract="format copied values even if cache has retired"; }
part edge8:EdgeRow { attribute :>> fromNode="Unknown publication"; attribute :>> toNode="Stable builder owner"; attribute :>> contract="query same operation; committed and absent are distinct physical histories"; }
part edge9:EdgeRow { attribute :>> fromNode="Known rejected publication"; attribute :>> toNode="Private rollback"; attribute :>> contract="detach list/TLS/fast aliases first; unknown free cannot replay"; }
part edge10:EdgeRow { attribute :>> fromNode="Ready commit"; attribute :>> toNode="Closing and pin drain"; attribute :>> contract="no new fast/diagnostic reads; builder outcome still settles"; }
part edge11:EdgeRow { attribute :>> fromNode="Closing and pin drain"; attribute :>> toNode="Native cleanup / retire"; attribute :>> contract="clear owner aliases; exact outcome before final cache release"; }
part def RefinementRow { attribute key:String; attribute lemma:String; attribute source:String; attribute premise:String; }
part refinement0:RefinementRow { attribute :>> key="ready-fields"; attribute :>> lemma="CacheReadyPublication.readyRequiresInitialization"; attribute :>> source="cache-owner"; attribute :>> premise="Ready is modeled canonical gate, not legacy list membership"; }
part refinement1:RefinementRow { attribute :>> key="unknown-owner"; attribute :>> lemma="CacheReadyPublication.unknownRetainsBuilder"; attribute :>> source="list-publish"; attribute :>> premise="publication outcome unknown whether physically Ready or absent"; }
part refinement2:RefinementRow { attribute :>> key="tls-unknown"; attribute :>> lemma="CacheReadyPublication.unknownTlsNoRegistry"; attribute :>> source="tls-write"; attribute :>> premise="void setter needs qualified provider receipt; unknown retains constructor"; }
part refinement3:RefinementRow { attribute :>> key="detached-copy"; attribute :>> lemma="CacheReadyPublication.formatUsesDetachedCopy"; attribute :>> source="diagnostic-callout"; attribute :>> premise="owner snapshot ACK and independent buffer lifetime"; }
part refinement4:RefinementRow { attribute :>> key="late-format"; attribute :>> lemma="CacheReadyPublication.lateFormatAdmitted"; attribute :>> source="diagnostic-callout"; attribute :>> premise="format reads copy, not freed cache or stale thread-id pointer"; }
part refinement5:RefinementRow { attribute :>> key="single-candidate"; attribute :>> lemma="CacheReadyPublication.noSecondCandidate"; attribute :>> source="cache-allocate"; attribute :>> premise="one builder-authorized allocation per modeled epoch; raw recursion closure external"; }
part refinement6:RefinementRow { attribute :>> key="unknown-rollback"; attribute :>> lemma="CacheReadyPublication.rollbackUnknownRetainsDuty"; attribute :>> source="cache-free"; attribute :>> premise="metadata duty retained even if native storage effect unknown; no replay"; }
part refinement7:RefinementRow { attribute :>> key="parent-lease"; attribute :>> lemma="CacheReadyPublication.guardedPriorDiagnostic"; attribute :>> source="prior"; attribute :>> premise="explicit metadata-view mirror includes layout/generation/caller qualification; full product not proved"; }
part def WriterRow { attribute key:String; attribute source:String; attribute access:String; attribute closure:String; attribute limit:String; }
part writer0:WriterRow { attribute :>> key="runtime-init"; attribute :>> source="runtime-locks"; attribute :>> access="global init lock/listLock/objLock/bucket initialization"; attribute :>> closure="captured body"; attribute :>> limit="plain first pointer test is not complete RuntimeServiceReady proof"; }
part writer1:WriterRow { attribute :>> key="cache-builder"; attribute :>> source="cache-allocate"; attribute :>> access="allocate/zero/list-link/owner/TLS sequence"; attribute :>> closure="captured body"; attribute :>> limit="allocator/mutex/TLS/owner/panic providers and exception landing unresolved"; }
part writer2:WriterRow { attribute :>> key="fast-slot"; attribute :>> source="fast-slot"; attribute :>> access="static __thread tcachePtr assigned after GetCache return"; attribute :>> closure="captured macro"; attribute :>> limit="all readers/clear/owner exit and provider profile unresolved"; }
part writer3:WriterRow { attribute :>> key="statistics"; attribute :>> source="stats-read"; attribute :>> access="owner bucket writers versus diagnostic list-locked scalar reads"; attribute :>> closure="direct read fields identified"; attribute :>> limit="list lock alone does not serialize all mutable bucket fields"; }
part writer4:WriterRow { attribute :>> key="diagnostic-output"; attribute :>> source="diagnostic-callout"; attribute :>> access="DString start/append/end and formatting inside list lock"; attribute :>> closure="captured body"; attribute :>> limit="indirect allocation/reentry and owner-label lifetime unresolved"; }
part writer5:WriterRow { attribute :>> key="cleanup"; attribute :>> source="tls-cleanup"; attribute :>> access="thread finalization delegates platform cleanup; native free after unlink"; attribute :>> closure="captured call sites"; attribute :>> limit="same-operation clear/free outcome and platform callbacks unresolved"; }
}
