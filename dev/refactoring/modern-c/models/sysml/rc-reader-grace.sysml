package GambitRcReaderGrace { private import ScalarValues::*;
part def SourceRow { attribute key:String; attribute path:String; attribute needle:String; attribute limit:String; }
part source0:SourceRow { attribute :>> key="diagnostic-save"; attribute :>> path="vendor/gambit/lib/_mem/copy-reservations.inc"; attribute :>> needle="invalid_copy_cell = cell;"; attribute :>> limit="conditional address origin; no lawful-input RC diagnostic witness established"; }
part source1:SourceRow { attribute :>> key="diagnostic-reset"; attribute :>> path="vendor/gambit/lib/_mem/heap-sections.inc"; attribute :>> needle="gc_round.invalid_copy_cell = 0;"; attribute :>> limit="exclusive collective next-round reset; not a grace receipt"; }
part source2:SourceRow { attribute :>> key="diagnostic-fields"; attribute :>> path="vendor/gambit/include/_gambit/runtime_roles.h.in"; attribute :>> needle="___WORD *invalid_copy_cell;"; attribute :>> limit="raw VM fields exposed to native aliases; named-use closure is bounded"; }
part source3:SourceRow { attribute :>> key="fatal"; attribute :>> path="vendor/gambit/lib/os_base.c"; attribute :>> needle="___GSTATE->setup_params.fatal_error (msgs);"; attribute :>> limit="callback return continues to exit; nonlocal escape unqualified"; }
part source4:SourceRow { attribute :>> key="exit"; attribute :>> path="vendor/gambit/lib/os_base.c"; attribute :>> needle="exit (status);"; attribute :>> limit="process termination, not recoverable scanner return"; }
part source5:SourceRow { attribute :>> key="fatal-default"; attribute :>> path="vendor/gambit/lib/setup.c"; attribute :>> needle="setup_params->fatal_error         = 0;"; attribute :>> limit="default initializer only; loaded embedding profile unqualified"; }
part source6:SourceRow { attribute :>> key="fatal-api"; attribute :>> path="vendor/gambit/include/_gambit/setup_parameters.h.in"; attribute :>> needle="void (*fatal_error)"; attribute :>> limit="callback receives messages, not automatic diagnostic slot pointer"; }
part source7:SourceRow { attribute :>> key="preclaim"; attribute :>> path="vendor/gambit/lib/_mem/collection-round.inc"; attribute :>> needle="context = task->origin->context;"; attribute :>> limit="failed claim skips context pointee use; origin itself already read"; }
part source8:SourceRow { attribute :>> key="claim"; attribute :>> path="vendor/gambit/include/_gambit/vm_state.h.in"; attribute :>> needle="t->incarnation != t->origin->incarnation"; attribute :>> limit="claim reads origin before its CAS; successful claim is not lookup protection"; }
part source9:SourceRow { attribute :>> key="advance"; attribute :>> path="vendor/gambit/include/_gambit/vm_state.h.in"; attribute :>> needle="done claim alone does not exclude late readers"; attribute :>> limit="coordinator also requires physical old-phase drain"; }
part source10:SourceRow { attribute :>> key="barrier"; attribute :>> path="vendor/gambit/lib/_mem/collection-round.inc"; attribute :>> needle="no worker may retain a stopped root view past this cut"; attribute :>> limit="existing collective candidate for ghost-reader discharge"; }
part source11:SourceRow { attribute :>> key="roots"; attribute :>> path="vendor/gambit/lib/_mem/root-origins.inc"; attribute :>> needle="___GC_ROOT_CONTROL(work);"; attribute :>> limit="post-claim strong consumer and override boundary"; }
part source12:SourceRow { attribute :>> key="layout"; attribute :>> path="vendor/gambit/include/_gambit/vm_state.h.in"; attribute :>> needle="___gc_root_origin gc_origins[___MAX_PROCESSORS];"; attribute :>> limit="origins and contexts embedded in VM; no per-origin malloc lifetime inferred"; }
part source13:SourceRow { attribute :>> key="reuse"; attribute :>> path="vendor/gambit/lib/setup.c"; attribute :>> needle="___vms->gc_origins[i].incarnation++;"; attribute :>> limit="incarnation guards identity after safe reuse, not before-load lifetime"; }
part source14:SourceRow { attribute :>> key="cleanup"; attribute :>> path="vendor/gambit/lib/_mem/rc-allocation.inc"; attribute :>> needle="___SPINLOCK_DESTROY(___ps->context->mem.rc_gate_);"; attribute :>> limit="gate teardown requires readers and root-domain users drained"; }
part source15:SourceRow { attribute :>> key="parent-model"; attribute :>> path="dev/refactoring/modern-c/models/quint/rc_root_release.qnt"; attribute :>> needle="action retireDomain="; attribute :>> limit="actual earlier scalar model to receive lookup grace precondition"; }
part def ObligationRow { attribute key:String; attribute status:String; attribute condition:String; }
part obligation0:ObligationRow { attribute :>> key="reader-safety"; attribute :>> status="conditional-model"; attribute :>> condition="lookup protection begins before first metadata load; transfer to claim without zero gap"; }
part obligation1:ObligationRow { attribute :>> key="named-use-inventory"; attribute :>> status="source-bound"; attribute :>> condition="fixed local vendor lexical inventory only; does not include arbitrary native pointer arithmetic"; }
part obligation2:ObligationRow { attribute :>> key="vm-round-closure"; attribute :>> status="unresolved"; attribute :>> condition="all entry, advance, reset, reuse and teardown callers covered by live VM and closed collective"; }
part obligation3:ObligationRow { attribute :>> key="fault-recovery"; attribute :>> status="unresolved"; attribute :>> condition="no current recovery landing receipt; escaping hook keeps scanner/domain custody"; }
part obligation4:ObligationRow { attribute :>> key="external-diagnostics"; attribute :>> status="unresolved"; attribute :>> condition="native aliases and fatal hook target closure require admission policy"; }
part obligation5:ObligationRow { attribute :>> key="c23-refinement"; attribute :>> status="unresolved"; attribute :>> condition="effective atomic/barrier backend, widths and reads-from qualified"; }
part def RouteRow { attribute actionName:String; attribute lemma:String; attribute source:String; attribute obligation:String; }
part route0:RouteRow { attribute :>> actionName="enterLookup"; attribute :>> lemma="RcReaderGrace.enterLookupPreserves"; attribute :>> source="preclaim"; attribute :>> obligation="reader-safety"; }
part route1:RouteRow { attribute :>> actionName="claimLookup"; attribute :>> lemma="RcReaderGrace.claimLookupPreserves"; attribute :>> source="preclaim"; attribute :>> obligation="reader-safety"; }
part route2:RouteRow { attribute :>> actionName="failClaim"; attribute :>> lemma="RcReaderGrace.failClaimPreserves"; attribute :>> source="preclaim"; attribute :>> obligation="reader-safety"; }
part route3:RouteRow { attribute :>> actionName="completeClaim"; attribute :>> lemma="RcReaderGrace.completeClaimPreserves"; attribute :>> source="roots"; attribute :>> obligation="reader-safety"; }
part route4:RouteRow { attribute :>> actionName="closeAdmission"; attribute :>> lemma="RcReaderGrace.closeAdmissionPreserves"; attribute :>> source="preclaim"; attribute :>> obligation="reader-safety"; }
part route5:RouteRow { attribute :>> actionName="rejectLate"; attribute :>> lemma="RcReaderGrace.rejectLatePreserves"; attribute :>> source="preclaim"; attribute :>> obligation="reader-safety"; }
part route6:RouteRow { attribute :>> actionName="beginScan"; attribute :>> lemma="RcReaderGrace.beginScanPreserves"; attribute :>> source="roots"; attribute :>> obligation="reader-safety"; }
part route7:RouteRow { attribute :>> actionName="endScan"; attribute :>> lemma="RcReaderGrace.endScanPreserves"; attribute :>> source="roots"; attribute :>> obligation="reader-safety"; }
part route8:RouteRow { attribute :>> actionName="saveDiagnostic"; attribute :>> lemma="RcReaderGrace.saveDiagnosticPreserves"; attribute :>> source="diagnostic-save"; attribute :>> obligation="reader-safety"; }
part route9:RouteRow { attribute :>> actionName="borrowDiagnostic"; attribute :>> lemma="RcReaderGrace.borrowDiagnosticPreserves"; attribute :>> source="diagnostic-save"; attribute :>> obligation="reader-safety"; }
part route10:RouteRow { attribute :>> actionName="returnDiagnostic"; attribute :>> lemma="RcReaderGrace.returnDiagnosticPreserves"; attribute :>> source="diagnostic-save"; attribute :>> obligation="reader-safety"; }
part route11:RouteRow { attribute :>> actionName="closeDiagnostic"; attribute :>> lemma="RcReaderGrace.closeDiagnosticPreserves"; attribute :>> source="diagnostic-save"; attribute :>> obligation="reader-safety"; }
part route12:RouteRow { attribute :>> actionName="unlinkNode"; attribute :>> lemma="RcReaderGrace.unlinkNodePreserves"; attribute :>> source="cleanup"; attribute :>> obligation="reader-safety"; }
part route13:RouteRow { attribute :>> actionName="retireDomain"; attribute :>> lemma="RcReaderGrace.retireDomainPreserves"; attribute :>> source="cleanup"; attribute :>> obligation="reader-safety"; }
part def GainRow { attribute key:String; attribute saved:String; attribute added:String; attribute condition:String; attribute status:String; }
part gain0:GainRow { attribute :>> key="named-diagnostic"; attribute :>> saved="0 named cell/body dereference sites found; no justification for universal node hazard pin"; attribute :>> added="3 diagnostic fields retained; external alias/hook policy required"; attribute :>> condition="full local vendor named-use scan bound by source hashes"; attribute :>> status="source-bound"; }
part gain1:GainRow { attribute :>> key="metadata-grace"; attribute :>> saved="reuse phase/round collective; 0 new per-task RMW required if enclosing lifetime covers all readers"; attribute :>> added="physical reader drain and entry closure proof; existing barriers retained"; attribute :>> condition="ghost lookup count refines an already closed cohort"; attribute :>> status="conditional"; }
part gain2:GainRow { attribute :>> key="node-release"; attribute :>> saved="unrelated failed metadata lookup need not delay one RC node unlink"; attribute :>> added="origin metadata and context gate lifetime remain distinct"; attribute :>> condition="root owners/borrows already settled; no source-slot escape"; attribute :>> status="conditional-model"; }
part gain3:GainRow { attribute :>> key="fatal-path"; attribute :>> saved="0 fabricated recovery receipts; 0 allowed domain retirements after unresolved scanner escape"; attribute :>> added="retain scanner, VM/domain and dependent roots; possibly indefinite"; attribute :>> condition="default exits; only escaped/unknown continuation needs retained live-process custody"; attribute :>> status="conditional-model"; }
part gain4:GainRow { attribute :>> key="legacy-retirement"; attribute :>> saved="0 runtime paths retired by documentary/formal success"; attribute :>> added="future managed hook/read adapter and teardown integration"; attribute :>> condition="native refinement still required"; attribute :>> status="design-only"; }
part def IssuerRow { attribute key:String; attribute source:String; attribute signature:String; attribute gap:String; }
part issuer0:IssuerRow { attribute :>> key="vm-owner"; attribute :>> source="layout"; attribute :>> signature="live VM authority before task/origin load"; attribute :>> gap="public native aliases and VM teardown closure unresolved"; }
part issuer1:IssuerRow { attribute :>> key="round-coordinator"; attribute :>> source="barrier"; attribute :>> signature="all prior lookup and claim users crossed physical phase/round drain"; attribute :>> gap="DONE alone is insufficient; exported users excluded or enrolled"; }
part issuer2:IssuerRow { attribute :>> key="diagnostic-owner"; attribute :>> source="diagnostic-save"; attribute :>> signature="address-only evidence versus enrolled dereferencing observer"; attribute :>> gap="no named native dereference consumer exists; external consumers unqualified"; }
part issuer3:IssuerRow { attribute :>> key="fault-custodian"; attribute :>> source="fatal"; attribute :>> signature="process exit or retained live-process scan/domain obligation"; attribute :>> gap="no automatic unlock/landing receipt from longjmp or callback abandonment"; }
part issuer4:IssuerRow { attribute :>> key="domain-owner"; attribute :>> source="cleanup"; attribute :>> signature="combine metadata-reader grace, root-slot grace and prior origin-release obligations"; attribute :>> gap="current cleanup Boolean/counts do not issue stable combined receipt"; }
part def EdgeRow { attribute fromNode:String; attribute toNode:String; attribute contract:String; }
part edge0:EdgeRow { attribute :>> fromNode="Live VM / closed round"; attribute :>> toNode="Lookup lease"; attribute :>> contract="before task-origin-context metadata loads"; }
part edge1:EdgeRow { attribute :>> fromNode="Lookup lease"; attribute :>> toNode="Claim owner"; attribute :>> contract="no unowned interval on success"; }
part edge2:EdgeRow { attribute :>> fromNode="Lookup lease"; attribute :>> toNode="Failed-claim exit"; attribute :>> contract="no context pointee access after failure; metadata grace still required"; }
part edge3:EdgeRow { attribute :>> fromNode="Claim owner"; attribute :>> toNode="RC scan gate"; attribute :>> contract="strong phase only; normal return discharges slot access"; }
part edge4:EdgeRow { attribute :>> fromNode="RC scan gate"; attribute :>> toNode="Diagnostic capture"; attribute :>> contract="address-only record; fatal does not unwind gate normally"; }
part edge5:EdgeRow { attribute :>> fromNode="Diagnostic capture"; attribute :>> toNode="Retained fault custody"; attribute :>> contract="escaped/unknown hook cannot issue normal completion"; }
part edge6:EdgeRow { attribute :>> fromNode="Failed-claim exit"; attribute :>> toNode="Domain retirement"; attribute :>> contract="all old readers drained, not merely claim DONE"; }
part edge7:EdgeRow { attribute :>> fromNode="RC scan gate"; attribute :>> toNode="Node unlink"; attribute :>> contract="same-gate scan grace; independent of failed metadata lookup"; }
part def ConsumerRow { attribute key:String; attribute source:String; attribute access:String; attribute lifetime:String; attribute limit:String; }
part consumer0:ConsumerRow { attribute :>> key="diagnostic-cell-body"; attribute :>> source="diagnostic-save"; attribute :>> access="save raw addresses; no named dereference reader found"; attribute :>> lifetime="VM record and scanner fatal boundary"; attribute :>> limit="native aliases / debugger / custom hook outside named closure"; }
part consumer1:ConsumerRow { attribute :>> key="diagnostic-worker"; attribute :>> source="diagnostic-save"; attribute :>> access="read worker sentinel under MISC_MEM_LOCK; first-writer selection"; attribute :>> lifetime="current round record"; attribute :>> limit="record reset is collective; tuple must be read under matching synchronization"; }
part consumer2:ConsumerRow { attribute :>> key="failed-claim"; attribute :>> source="preclaim"; attribute :>> access="read task, origin and context pointer value; continue on failure"; attribute :>> lifetime="VM task/origin metadata until return"; attribute :>> limit="no subsequent context pointee access on this branch"; }
part consumer3:ConsumerRow { attribute :>> key="prepare-consumer"; attribute :>> source="preclaim"; attribute :>> access="setup_still_objs_to_scan and still deferred accounting"; attribute :>> lifetime="successful claim plus live context until normal completion"; attribute :>> limit="actual PREPARE branch, not RC slot dereference"; }
part consumer4:ConsumerRow { attribute :>> key="strong-consumer"; attribute :>> source="roots"; attribute :>> access="continuation/register/saved/cache/startup/marker/processor/RC roots"; attribute :>> lifetime="claimed context plus RC gate during mark_rc"; attribute :>> limit="override and descendant closure remain separate"; }
part consumer5:ConsumerRow { attribute :>> key="weak-consumer"; attribute :>> source="preclaim"; attribute :>> access="process_wills reads and writes context will lists"; attribute :>> lifetime="claimed context through weak phase"; attribute :>> limit="weak descendants must drain before phase advance"; }
part consumer6:ConsumerRow { attribute :>> key="host-cleanup"; attribute :>> source="preclaim"; attribute :>> access="preclaim context comparison; restored check; owner-affine still cleanup"; attribute :>> lifetime="all stopped host domains and old roster"; attribute :>> limit="not independent collector-worker authority"; }
part consumer7:ConsumerRow { attribute :>> key="claim-finish-advance"; attribute :>> source="claim"; attribute :>> access="origin incarnation/state/epoch and task claim metadata"; attribute :>> lifetime="live VM / closed phase cohort"; attribute :>> limit="DONE is not metadata reader drain"; }
part consumer8:ConsumerRow { attribute :>> key="round-reset"; attribute :>> source="diagnostic-reset"; attribute :>> access="clear diagnostic addresses; freeze origins; publish task slots"; attribute :>> lifetime="exclusive coordinator after old collective drain"; attribute :>> limit="reset does not prove fault recovery"; }
part consumer9:ConsumerRow { attribute :>> key="slot-reuse"; attribute :>> source="reuse"; attribute :>> access="increment incarnation and bind embedded execution context"; attribute :>> lifetime="exclusive setup after prior readers ended"; attribute :>> limit="generation comparison occurs after memory load"; }
part consumer10:ConsumerRow { attribute :>> key="domain-cleanup"; attribute :>> source="cleanup"; attribute :>> access="detach list, free nodes, destroy gate"; attribute :>> lifetime="root-slot grace plus metadata / owner / storage grace"; attribute :>> limit="no new aggregate completion receipt in source"; }
part source16:SourceRow { attribute :>> key="barrier-dispatch"; attribute :>> path="vendor/gambit/lib/setup.h"; attribute :>> needle="#define BARRIER() barrier_sync_noop (___PSPNC)"; attribute :>> limit="single-thread branch erases barrier; effective cohort matters"; }
part source17:SourceRow { attribute :>> key="tree-barrier"; attribute :>> path="vendor/gambit/lib/setup.c"; attribute :>> needle="int n = ___vms->processor_count; /* processor count */"; attribute :>> limit="tree collective on current roster; no arbitrary reader enrollment"; }
part source18:SourceRow { attribute :>> key="sync-handoff"; attribute :>> path="vendor/gambit/lib/setup.c"; attribute :>> needle="___SYNC_SLOT_PUBLISH(___slot,op,id);"; attribute :>> limit="send/read/ACK lifecycle; effective backend and full collective not verified here"; }
part source19:SourceRow { attribute :>> key="descendant-drain"; attribute :>> path="vendor/gambit/lib/_mem/collection-round.inc"; attribute :>> needle="mark_reachable_from_marked (work);"; attribute :>> limit="after collect_root_tasks finishes; phase barrier is stronger than DONE"; }
part route14:RouteRow { attribute :>> actionName="spawnDescendant"; attribute :>> lemma="RcReaderGrace.spawnDescendantPreserves"; attribute :>> source="descendant-drain"; attribute :>> obligation="reader-safety"; }
part route15:RouteRow { attribute :>> actionName="finishDescendant"; attribute :>> lemma="RcReaderGrace.finishDescendantPreserves"; attribute :>> source="descendant-drain"; attribute :>> obligation="reader-safety"; }
part route16:RouteRow { attribute :>> actionName="confirmCohortDrain"; attribute :>> lemma="RcReaderGrace.confirmCohortDrainPreserves"; attribute :>> source="tree-barrier"; attribute :>> obligation="reader-safety"; }
part edge8:EdgeRow { attribute :>> fromNode="Root task DONE"; attribute :>> toNode="Descendant scan work"; attribute :>> contract="DONE precedes mark_reachable_from_marked; no phase grace yet"; }
part edge9:EdgeRow { attribute :>> fromNode="Descendant scan work"; attribute :>> toNode="Physical cohort drain"; attribute :>> contract="all admitted lookups, claims and descendants must finish"; }
part edge10:EdgeRow { attribute :>> fromNode="Physical cohort drain"; attribute :>> toNode="Domain retirement"; attribute :>> contract="live coordinator issues combined metadata grace; root/origin duties remain"; }
part consumer11:ConsumerRow { attribute :>> key="post-task-descendants"; attribute :>> source="descendant-drain"; attribute :>> access="mark_reachable_from_marked follows finished root tasks"; attribute :>> lifetime="phase/round barrier beyond per-task DONE"; attribute :>> limit="descendant closure must be proved independently of claim completion"; }
}
