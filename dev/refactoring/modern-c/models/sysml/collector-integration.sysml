package GambitCollectorIntegration {
  private import ScalarValues::*;
  ref part delivery=GambitModernCOutcomes::collector;
  attribute scope:String="Complete managed C-target copy-capacity/worker/restoration integration on frozen-root REV4652db0d. Historical prototype passes are references, never current-source admission. One existing RootOrigin/RootTask population; no parallel root scheduler or new build profile.";
  attribute stage:String="QUALIFIED_LOCAL: exact-source bootstrap/original consumers, source/native case closure and bounded models pass. Synchronous C-target W-worker/R-owner adapter; remote CI and runtime performance remain separate.";
  attribute formalDuty:String="Reuse runtime_ownership for unique task/worker and retained source custody, root_store_projection for closed writers/canonical updated cells, runtime_roles for collective stage order, copy_custody for forwarding/payload/Tail/private/frontier/queue debts, round_capacity for complete census/disjoint intervals/public decision and its copy_pool module for sealed prefix/online grant histories, dedicated_copy_capacity for conditional no-fit charge. Existing Lean RoundCapacity, CopyCapacityComposition and RuntimeOwnership laws own algebraic bounds/canonical coverage/reload only. Actual producer/source layout and C memory ordering remain refinement premises; do not duplicate QNT schedules in Lean or count native tests as formal proof.";
  attribute sourceCases:String="source-epoch;root-assignment;worker-arena;forwarding-authority;payload-tail;chunk-authority;descendant-drain;source-census;largest-grant;interval-packing;restore-coverage;owner-cleanup;capacity-result;refusal-thaw;unknown-custody;consumer-products";
  attribute requiredCases:String="bootstrap;original-gsi;original-make;old-module-refusal;w-equals-r;w-less-r-one;w-less-r-many;all-root-kinds;primitive-overrides;multi-shot-map;frame-roots;owner-cleanup-thread;no-losing-grant;tail-queue-replay;preflip-refusal;unknown-not-replayed;implementation-shrink;current-profile-identity;consumer-reuse";
  attribute graph:String="freeze -> census -> reserve -> publish_decision -> flip -> roots -> descendants -> transfer -> restore -> owner_cleanup -> resize_result -> resume";
  attribute openStages:String="";
  attribute sourceKinds:String="VM;symbol/keyword;RC;globals;stack;bank";
  attribute costs:String="Initial physical grants change2R to R+W only after full interval/restore admission. R-W fewer initial heap grants is not an RSS/total-peak reduction. Fixed worker/round records, source-section ownership gate, scan-map trailer, census/layout metadata, chunk ownership and extra synchronization must be measured/accounted separately. No added heap or deadline to make a topology pass. No throughput claim without matched measurements.";
  attribute refusal:String="A known incomplete or impossible plan must be observed by all R before any parity flip or source forwarding. Only a completely unstarted round may thaw back to its old roots. An unknown allocation/commit/scan/Tail result retains its source and physical grant; never reset/requeue, refund a closed section, publish partial membership or infer death from failed join.";
  part def Source { attribute id:String; attribute path:String; attribute anchor:String; attribute obligation:String; }
  part roots:Source { attribute :>> id="root-assignment"; attribute :>> path="lib/_mem/root-tasks.inc"; attribute :>> anchor="___BOOL ___root_round_publish"; attribute :>> obligation="Frozen union publishes each canonical root descriptor and one statically assigned worker before any scan; modulo-W ownership covers every R source without making its carrier the source identity."; }
  part arena:Source { attribute :>> id="worker-arena"; attribute :>> path="lib/_mem/heap-sections.inc"; attribute :>> anchor="___HIDDEN void refill_worker_arena"; attribute :>> obligation="Worker destination refill acquires an exclusive section from the accepted physical copy prefix; context restoration intervals are never copy loans; never export/import a mutator heap cursor."; }
  part forward:Source { attribute :>> id="forwarding-authority"; attribute :>> path="lib/_mem/copy-reservations.inc"; attribute :>> anchor="___HIDDEN ___copy_reservation reserve_copy"; attribute :>> obligation="Source-section forwarding ownership precedes destination reserve. A known forwarding loser exits before reserving. A header change under the held gate is unknown and retains its grant, never a refund; initialized payload and Tail debts remain with their owner."; }
  part queue:Source { attribute :>> id="chunk-authority"; attribute :>> path="lib/_mem/object-scanning.inc"; attribute :>> anchor="scan_complete_heap_chunk"; attribute :>> obligation="Local frontier, queued link and claimed chunk have unique transport authority. Object scan ownership and first-field Tail custody remain distinct; no allocation-tip inference or same-object duplicate field repair."; }
  part carrier:Source { attribute :>> id="owner-cleanup"; attribute :>> path="lib/_mem/collection-round.inc"; attribute :>> anchor="free_unmarked_still_objs"; attribute :>> obligation="Only W carriers execute collector phases and W idle accounting; all R retain physical collective participation, restore their own active stack and execute foreign cleanup on their original native owner after restoration."; }
  part epoch:Source { attribute :>> id="source-epoch"; attribute :>> path="lib/_mem/root-tasks.inc"; attribute :>> anchor="___BOOL ___root_round_freeze"; attribute :>> obligation="Every old source holds its union lease through all-R physical restoration. Worker completion neither changes origin identity nor retires that lease."; }
  part tail:Source { attribute :>> id="payload-tail"; attribute :>> path="lib/_mem/copy-reservations.inc"; attribute :>> anchor="prepare_copy_request"; attribute :>> obligation="Source publication and payload/Tail completion are distinct debts. A canonical destination revisit cannot replay initialization or discharge another worker debt."; }
  part drain:Source { attribute :>> id="descendant-drain"; attribute :>> path="lib/_mem/object-scanning.inc"; attribute :>> anchor="scan_complete_heap_chunk"; attribute :>> obligation="W active/idle accounting covers the published and local queues through both strong and weak phases. An empty local allocation frontier is not termination."; }
  part census:Source { attribute :>> id="source-census"; attribute :>> path="lib/_mem/copy-planning.inc"; attribute :>> anchor="plan_copy_round"; attribute :>> obligation="Frozen canonical roots feed the actual typed scan/mark_frame visitor with a read-only census sink. Private source extent bits deduplicate objects/raw frames and reject overlap; no linear heap-header walk across shrink holes. Still marks are scratch; source root/header/payload and structural frame links remain unchanged."; }
  part grant:Source { attribute :>> id="largest-grant"; attribute :>> path="lib/_mem/copy-planning.inc"; attribute :>> anchor="census_claim"; attribute :>> obligation="Actual header lengths and effective RETI/RETN frame descriptors supply span and worst alignment request before flip. Each request fits H-3 or known refusal; compiler4096/runtime8192 declarations are not bounds. Shared physical extents charge once."; }
  part packing:Source { attribute :>> id="interval-packing"; attribute :>> path="lib/collector.h"; attribute :>> anchor="___gc_copy_section_bound"; attribute :>> obligation="For C=H-FUDGE-3, small sum U and maximum m, B=U+floor(U/CHUNK), K=W+2L+min(floor(B/(C-m+1)),floor(2B/C)). Actual R stack spans plus K copy sections must fit current pool. Seal copy_first/copy_past before flip; refill consumes only that prefix. Conservative false refusal is allowed and must be reported, not repaired by heap growth. Large final tail retires into a counted small grant before resume."; }
  part restore:Source { attribute :>> id="restore-coverage"; attribute :>> path="lib/_mem/rc-allocation.inc"; attribute :>> anchor="reopen_rc_roots"; attribute :>> obligation="Source owner must match the draining union member, completed assigned executor and accepted/restored same-epoch resume grant. Standalone source still requires its current owner. Never confuse scan executor with resume owner."; }
  part capacity:Source { attribute :>> id="capacity-result"; attribute :>> path="lib/_mem/collection-round.inc"; attribute :>> anchor="overflow=___COLLECTION(___vms).overflow"; attribute :>> obligation="Every R participant consumes the same coordinator-published post-GC resize result. This does not imply pre-copy physical admission."; }
  part admissionRefusal:Source { attribute :>> id="refusal-thaw"; attribute :>> path="lib/_mem/root-tasks.inc"; attribute :>> anchor="___BOOL ___root_round_refuse"; attribute :>> obligation="All R observe one refusal before flip. Only READY/unclaimed member tasks may become REFUSED with leases zero; shared global snapshot retires once, RC returns OPEN. REFUSED is not DONE. Retry uses a fresh round epoch."; }
  part custody:Source { attribute :>> id="unknown-custody"; attribute :>> path="lib/collector.h"; attribute :>> anchor="___gc_census_struct"; attribute :>> obligation="VM-owned queue/replacement/retired slots and ALLOCATING state retain an interrupted allocation/free outcome. Unknown copy/Tail also retains roots and grants. No thaw/replay/refund/free/cleanup authorization; dead-carrier safe takeover and healthy-VM isolation remain separate later duties."; }
  part consumerProducts:Source { attribute :>> id="consumer-products"; attribute :>> path="tests/makefile.in"; attribute :>> anchor="ROOT_TASK_DEPS"; attribute :>> obligation="Existing root-task/bank/primitive feature products depend on source, generated/config/private headers, actual GSC/runtime and configured Make recipe. Compile to a fixed staging filename and publish by rename only on success; retain products until existing clean. Phony tests always execute with unchanged cases. Source/profile/tool/environment/cwd/runtime identities are checked by the existing workspace qualification; bare Make timestamps are not a cross-profile cryptographic cache."; }
  part def Need { ref part gate:GambitCommitGates::Gate; attribute id:String; attribute method:String; attribute artifact:String; attribute scope:String; }
  part tests:Need { ref part :>> gate=GambitCommitGates::tests; attribute :>> id="COLLECTOR-NATIVE"; attribute :>> method="native"; attribute :>> artifact="evidence/research/retained/modern-c/collector-integration/receipt.json"; attribute :>> scope="Current-source complete bootstrap, W<R and W=R roots/map/restore, original consumers, controlled packing refusal, native owner cleanup, real PBT replay/shrink with unchanged profile and limits."; }
  part learning:Need { ref part :>> gate=GambitCommitGates::learning; attribute :>> id="COLLECTOR-LEARNING"; attribute :>> method="source-analysis"; attribute :>> artifact="dev/refactoring/modern-c/collector-integration.org"; attribute :>> scope="Distinguish root identity, source lifetime, work authority, physical interval ownership and native cleanup owner. Total bytes alone do not establish contiguous copying/restoration capacity."; }
  part process:Need { ref part :>> gate=GambitCommitGates::process; attribute :>> id="COLLECTOR-PROCESS"; attribute :>> method="source-analysis"; attribute :>> artifact="dev/refactoring/modern-c/delivery-outcomes.org"; attribute :>> scope="Second complete integration result, currently unqualified. No partial arena/source-counter commit; retain first result and keep affine retirement/request service outside this cut."; }
  part models:Need { ref part :>> gate=GambitCommitGates::models; attribute :>> id="COLLECTOR-MODELS"; attribute :>> method="source-refinement"; attribute :>> artifact="dev/refactoring/modern-c/collector-integration.org"; attribute :>> scope="SysML projects source and native cases into existing ASCENT caseNeed/caseObserved closure. Distinct existing QNT temporal duties and Lean algebraic/canonical consequences require explicit C premises; no duplicated proofs."; }
  part questions:Need { ref part :>> gate=GambitCommitGates::questions; attribute :>> id="COLLECTOR-QUESTIONS"; attribute :>> method="source-analysis"; attribute :>> artifact="dev/refactoring/modern-c/collector-integration.org"; attribute :>> scope="What closes source census and largest frame/object grant? Who owns each interval, Tail and unknown result? When can R contexts receive W tails without aliasing? Which costs disappear and which remain? Keep missing proofs and native cases open."; }
}
