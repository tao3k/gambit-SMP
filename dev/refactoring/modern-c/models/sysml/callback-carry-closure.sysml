package GambitCallbackCarryClosure { private import ScalarValues::*;
part def Owner { attribute componentId:String; }
part compiler:Owner { attribute :>> componentId="gsc-session-emission"; }
part pipe:Owner { attribute :>> componentId="string-pipe-cursor-and-roots"; }
part def SourceRow { attribute key:String; attribute path:String; attribute needle:String; attribute obligation:String; }
part source0:SourceRow { attribute :>> key="formatter-default"; attribute :>> path="vendor/gambit/lib/_io.scm"; attribute :>> needle="(define ##wr ##default-wr)"; attribute :>> obligation="Initial binding; not immutable session identity"; }
part source1:SourceRow { attribute :>> key="formatter-set"; attribute :>> path="vendor/gambit/lib/_io.scm"; attribute :>> needle="(set! ##wr x)"; attribute :>> obligation="Global replacement writer"; }
part source2:SourceRow { attribute :>> key="debug-register"; attribute :>> path="vendor/gambit/gsc/_gscdebug.scm"; attribute :>> needle="(##wr-set!"; attribute :>> obligation="One module installation and two temporary writes; special branch only"; }
part source3:SourceRow { attribute :>> key="debug-loader"; attribute :>> path="vendor/gambit/gsc/igsc.scm"; attribute :>> needle="\"_gscdebug\""; attribute :>> obligation="Explicit interpreted loader; compiled loader qualification remains open"; }
part source4:SourceRow { attribute :>> key="port-initial"; attribute :>> path="vendor/gambit/lib/_io.scm"; attribute :>> needle="#f ;; io-exception-handler"; attribute :>> obligation="Constructor default; not an immutable capability"; }
part source5:SourceRow { attribute :>> key="port-register"; attribute :>> path="vendor/gambit/lib/_io.scm"; attribute :>> needle="(macro-port-io-exception-handler-set! port handler)"; attribute :>> obligation="Public wrapper reaches internal field writer"; }
part source6:SourceRow { attribute :>> key="io-dispatch"; attribute :>> path="vendor/gambit/lib/_io.scm"; attribute :>> needle="(define-prim (##raise-io-exception port exc)"; attribute :>> obligation="Port callback or ambient dynamic handler"; }
part source7:SourceRow { attribute :>> key="dynamic-bind"; attribute :>> path="vendor/gambit/lib/_thread.scm"; attribute :>> needle="(define-prim (##with-exception-handler handler thunk)"; attribute :>> obligation="Both SMP branches bind dynamic environment"; }
part source8:SourceRow { attribute :>> key="primordial-register"; attribute :>> path="vendor/gambit/lib/_repl.scm"; attribute :>> needle="(##primordial-exception-handler-hook-set! ##repl-exception-handler-hook)"; attribute :>> obligation="Runtime module initializes primordial hook"; }
part source9:SourceRow { attribute :>> key="compiler-catcher"; attribute :>> path="vendor/gambit/gsc/_utils.scm"; attribute :>> needle="(define (with-exception-handling proc)"; attribute :>> obligation="Compiler diagnostic escape is separate from ambient I/O binding"; }
part source10:SourceRow { attribute :>> key="gc-register"; attribute :>> path="vendor/gambit/lib/_nonstd.scm"; attribute :>> needle="(##add-gc-interrupt-job! ##display-gc-report)"; attribute :>> obligation="Actual persistent GC job registration"; }
part source11:SourceRow { attribute :>> key="gc-report-enable"; attribute :>> path="vendor/gambit/lib/_nonstd.scm"; attribute :>> needle="(define ##gc-report? #f)"; attribute :>> obligation="Report also enabled by debug level >=5"; }
part source12:SourceRow { attribute :>> key="gc-report-port"; attribute :>> path="vendor/gambit/lib/_nonstd.scm"; attribute :>> needle="(##repl-output-port)"; attribute :>> obligation="Dynamically selected reporting output, invokes global writer"; }
part source13:SourceRow { attribute :>> key="gc-execute"; attribute :>> path="vendor/gambit/lib/_kernel.scm"; attribute :>> needle="(define-prim (##execute-jobs! jobs)"; attribute :>> obligation="Traverses list; no effect sandbox or removal of in-flight callbacks"; }
part source14:SourceRow { attribute :>> key="gc-job-api"; attribute :>> path="vendor/gambit/lib/_kernel.scm"; attribute :>> needle="(##add-job! ##gc-interrupt-jobs thunk)"; attribute :>> obligation="Extensible FIFO roots arbitrary procedures"; }
part source15:SourceRow { attribute :>> key="gc-before-jobs"; attribute :>> path="vendor/gambit/lib/_kernel.scm"; attribute :>> needle="(##gc-finalize!)"; attribute :>> obligation="Finalization precedes GC job list execution"; }
part source16:SourceRow { attribute :>> key="will-action"; attribute :>> path="vendor/gambit/lib/_kernel.scm"; attribute :>> needle="(action testator)"; attribute :>> obligation="Zaps will fields before action; lexical arguments survive and may capture"; }
part source17:SourceRow { attribute :>> key="reader-ready"; attribute :>> path="vendor/gambit/lib/_io.scm"; attribute :>> needle="(define-prim (##char-ready?1 port)"; attribute :>> obligation="Fill in exhausted branch only"; }
part source18:SourceRow { attribute :>> key="reader-peek"; attribute :>> path="vendor/gambit/lib/_io.scm"; attribute :>> needle="(define-prim (##peek-char1 port)"; attribute :>> obligation="Fill in exhausted branch only"; }
part source19:SourceRow { attribute :>> key="reader-char"; attribute :>> path="vendor/gambit/lib/_io.scm"; attribute :>> needle="(define-prim (##read-char1 port)"; attribute :>> obligation="Fill in exhausted branch only"; }
part source20:SourceRow { attribute :>> key="reader-bulk"; attribute :>> path="vendor/gambit/lib/_io.scm"; attribute :>> needle="(define-prim (##read-substring"; attribute :>> obligation="Positive unread count transferred before refill"; }
part source21:SourceRow { attribute :>> key="carry-test"; attribute :>> path="vendor/gambit/lib/_io.scm"; attribute :>> needle="(if (##fx= vect-rlo vect-rhi)"; attribute :>> obligation="Split exhausted/no-carry from internal unread carry"; }
part source22:SourceRow { attribute :>> key="carry-copy"; attribute :>> path="vendor/gambit/lib/_io.scm"; attribute :>> needle="(,',##subvect vect-rbuf vect-rlo vect-rhi)"; attribute :>> obligation="Copies unread slice; fresh allocation may fail after FIFO advance"; }
part source23:SourceRow { attribute :>> key="carry-fifo"; attribute :>> path="vendor/gambit/lib/_io.scm"; attribute :>> needle="(macro-fifo-elem-set!"; attribute :>> obligation="Install replacement in FIFO and reader, then writer if shared"; }
part source24:SourceRow { attribute :>> key="writer-loop"; attribute :>> path="vendor/gambit/lib/_io.scm"; attribute :>> needle="(define-prim (##write-substring str start end port)"; attribute :>> obligation="After drain loops with saved index, re-reads current buffer"; }
part source25:SourceRow { attribute :>> key="capture"; attribute :>> path="vendor/gambit/lib/_thread.scm"; attribute :>> needle="(define-prim (call-with-current-continuation"; attribute :>> obligation="Multi-shot capture; no compiled-map receipt from lexical text"; }
part source26:SourceRow { attribute :>> key="frame-decode"; attribute :>> path="vendor/gambit/include/gambit.h"; attribute :>> needle="frame.gcmap = ___IFD_GCMAP(descr);"; attribute :>> obligation="Real descriptor consumer; action-specific generated identity still open"; }
part source27:SourceRow { attribute :>> key="frame-scan"; attribute :>> path="vendor/gambit/lib/memory/continuation-roots.inc"; attribute :>> needle="while (___frame_root_next_run (&cursor, &first, &past))"; attribute :>> obligation="Captured roots consumed using frame maps"; }
part source28:SourceRow { attribute :>> key="resource-write"; attribute :>> path="vendor/gambit/gsc/_t-c-1.scm"; attribute :>> needle="(vector-set! r 1 demanders)"; attribute :>> obligation="Raw resource alias has write authority independent of callback name"; }
part source29:SourceRow { attribute :>> key="second"; attribute :>> path="vendor/gambit/gsc/_t-c-1.scm"; attribute :>> needle="(def-mod-prm-glo \"DEF_MOD_GLO\")"; attribute :>> obligation="Retirement requires complete emission equivalence, not local idempotence"; }
part def CallbackRow { attribute key:String; attribute registrant:String; attribute closure:String; attribute authority:String; attribute status:String; }
part callback0:CallbackRow { attribute :>> key="stock-writer"; attribute :>> registrant="_io module initial binding"; attribute :>> closure="default-wr recursively resolves global wr; port methods and faults"; attribute :>> authority="No direct resource setter established; globals/FFI not capability-restricted"; attribute :>> status="Direct initializer located; session closure open"; }
part callback1:CallbackRow { attribute :>> key="debug-writer"; attribute :>> registrant="_gscdebug top level; igsc explicit loader"; attribute :>> closure="VAR/PTREE conversion and saved formatter; scalar bypass"; attribute :>> authority="No direct resource write; old saved formatter can be restored after capture"; attribute :>> status="Do not transfer debug witness to default scalar route"; }
part callback2:CallbackRow { attribute :>> key="port-handler"; attribute :>> registrant="device constructor #f; public setter can replace"; attribute :>> closure="handler receives exception including procedure/args; ambient path if absent"; attribute :>> authority="Arbitrary installed procedure can hold raw aliases or reach c# globals"; attribute :>> status="No selected default setter caller found; whole-session negative not proved"; }
part callback3:CallbackRow { attribute :>> key="ambient-handler"; attribute :>> registrant="with-exception-handler; primordial hook set by _repl"; attribute :>> closure="Dynamic environment, REPL hook, error reporting, continuation"; attribute :>> authority="No lexical capability firewall; exceptions may return/capture"; attribute :>> status="Compiler diagnostic catcher does not seal this chain"; }
part callback4:CallbackRow { attribute :>> key="gc-report"; attribute :>> registrant="_nonstd installs display-gc-report via _kernel add-job"; attribute :>> closure="stats, debug settings, repl-output-port, write and I/O handlers"; attribute :>> authority="Stock body lacks direct resource write; downstream custom formatter unrestricted"; attribute :>> status="Enabled by level>=5 or gc-report flag; default flag false insufficient"; }
part callback5:CallbackRow { attribute :>> key="gc-finalizers"; attribute :>> registrant="make-will / make-final-will; gc-finalize before jobs"; attribute :>> closure="action and testator copied to locals before will fields zapped"; attribute :>> authority="Arbitrary Scheme action, global and retained alias authority"; attribute :>> status="All reachable wills and native callbacks remain qualification input"; }
part callback6:CallbackRow { attribute :>> key="registry-mutation"; attribute :>> registrant="add/clear GC jobs; wr-set; port setter; dynamic binding"; attribute :>> closure="Existing invocation retains lexical handler/list even after registry changes"; attribute :>> authority="Closing registration alone cannot revoke in-flight aliases"; attribute :>> status="Need admitted epoch, borrower drain and restoration closure"; }
part def ReaderRow { attribute key:String; attribute guard:String; attribute effect:String; attribute scope:String; }
part reader0:ReaderRow { attribute :>> key="ready"; attribute :>> guard="rlo>=rhi"; attribute :>> effect="fill with want=1, block=false"; attribute :>> scope="Direct selected character method"; }
part reader1:ReaderRow { attribute :>> key="peek"; attribute :>> guard="rlo>=rhi"; attribute :>> effect="fill with want=1, no consumption on success"; attribute :>> scope="Direct selected character method"; }
part reader2:ReaderRow { attribute :>> key="read"; attribute :>> guard="rlo>=rhi"; attribute :>> effect="fill with want=1, consumes after refill"; attribute :>> scope="Direct selected character method"; }
part reader3:ReaderRow { attribute :>> key="substring"; attribute :>> guard="chars-buffered<=0"; attribute :>> effect="fill only after available chars transferred"; attribute :>> scope="Direct selected character method; normal valid index invariant required"; }
part reader4:ReaderRow { attribute :>> key="carry"; attribute :>> guard="rlo<rhi and rhi==length(old)"; attribute :>> effect="copy prefix plus next; update writer if next==wbuf"; attribute :>> scope="Internal branch algebra; ordinary public reachability not established"; }
part def ClaimRow { attribute key:String; attribute mechanism:String; attribute condition:String; attribute result:String; attribute gap:String; }
part claim0:ClaimRow { attribute :>> key="counter"; attribute :>> mechanism="c=rhi-rlo; b=wlo; h=whi; shared next"; attribute :>> condition="b becomes b-rlo; whi becomes h+c; rlo becomes 0"; attribute :>> result="Post-minus-pre pending expression equals c; payload concatenation preserves bytes"; attribute :>> gap="Not a public bug claim; other caller/FFI reachability and counter semantics open"; }
part claim1:ClaimRow { attribute :>> key="no-carry"; attribute :>> mechanism="four direct reader guards"; attribute :>> condition="Valid rlo<=rhi and unmodified locked state"; attribute :>> result="c=0 at fill, recovers preceding no-carry conservation"; attribute :>> gap="Aliases, injected methods and reentrant/FFI mutations not closed"; }
part claim2:ClaimRow { attribute :>> key="roots"; attribute :>> mechanism="capture may retain input string, port, writer, old buffer and dynamic environment"; attribute :>> condition="Lexical locals identify candidates, not live GC slots"; attribute :>> result="Return/field zapping is insufficient for release; multi-shot capture retains custody"; attribute :>> gap="Generated program points, saved registers and map coverage unresolved"; }
part claim3:ClaimRow { attribute :>> key="failure"; attribute :>> mechanism="FIFO advance and wlo update precede append allocation"; attribute :>> condition="Allocation failure or escaping callback at intermediate point"; attribute :>> result="No full rollback/equivalence claimed; old and next storage need continued custody"; attribute :>> gap="Actual OOM/GC exception timing and compiler roots require refinement"; }
part claim4:ClaimRow { attribute :>> key="retirement"; attribute :>> mechanism="one immutable native binding plan"; attribute :>> condition="Same entry, canonical writers, admitted transitive closures and fault prefixes"; attribute :>> result="At most one second helper per qualified binding can disappear"; attribute :>> gap="Current qualified bindings=0; first demand still required"; }
part def GainRow { attribute key:String; attribute avoided:String; attribute added:String; attribute condition:String; }
part gain0:GainRow { attribute :>> key="normalization"; attribute :>> avoided="0..N second helper calls per module; first N retained"; attribute :>> added="Plan creation O(N), epoch validation and transitive effect qualification"; attribute :>> condition="Positive iff saved sum helper cost exceeds plan plus validation; no timing measured"; }
part gain1:GainRow { attribute :>> key="formatter"; attribute :>> avoided="0 direct debug temporary writes on selected scalar default route"; attribute :>> added="WriterView conversion must cover recursive dispatch and handlers"; attribute :>> condition="Do not count unrelated special-branch savings on scalar path"; }
part gain2:GainRow { attribute :>> key="carry"; attribute :>> avoided="No guaranteed fewer copies; internal carry copies c+len(next) elements"; attribute :>> added="Optional explicit logical cursor and root descriptors"; attribute :>> condition="Only useful after reachable consumer and exception semantics established"; }
part gain3:GainRow { attribute :>> key="roots"; attribute :>> avoided="0 currently admitted early releases"; attribute :>> added="Capture/activation accounting, descriptor provenance and owner drain"; attribute :>> condition="Memory saved only after last reachable capture plus native borrower retires"; }
part gain4:GainRow { attribute :>> key="language"; attribute :>> avoided="C23 representation can express scoped contexts and atomics"; attribute :>> added="Platform qualification and generated ABI work remain necessary"; attribute :>> condition="Zig does not eliminate callback effect or root coverage proof"; }
part def ContractRow { attribute fromNode:String; attribute toNode:String; attribute custody:String; }
part contract0:ContractRow { attribute :>> fromNode="SysML"; attribute :>> toNode="ASCENT"; attribute :>> custody="Source identities, component obligations and open receipts"; }
part contract1:ContractRow { attribute :>> fromNode="ASCENT"; attribute :>> toNode="QNT"; attribute :>> custody="Exact action roster and source rows; missing evidence blocks retirement"; }
part contract2:ContractRow { attribute :>> fromNode="QNT"; attribute :>> toNode="Lean"; attribute :>> custody="Restricted typed IR projection and all-step induction"; }
part contract3:ContractRow { attribute :>> fromNode="formatter"; attribute :>> toNode="output"; attribute :>> custody="Global identity plus recursive dispatch; not sealed"; }
part contract4:ContractRow { attribute :>> fromNode="GC interrupt"; attribute :>> toNode="will action"; attribute :>> custody="Arbitrary action before reporting jobs"; }
part contract5:ContractRow { attribute :>> fromNode="GC interrupt"; attribute :>> toNode="report"; attribute :>> custody="Registered stock callback and runtime enable condition"; }
part contract6:ContractRow { attribute :>> fromNode="report"; attribute :>> toNode="output"; attribute :>> custody="REPL port, global formatter and dynamic exception chain"; }
part contract7:ContractRow { attribute :>> fromNode="output"; attribute :>> toNode="metadata"; attribute :>> custody="Access only if reachable global/raw authority; absence not proved"; }
part contract8:ContractRow { attribute :>> fromNode="reader"; attribute :>> toNode="carry candidate"; attribute :>> custody="Advance FIFO then allocate; failure retains custody obligation"; }
part contract9:ContractRow { attribute :>> fromNode="carry candidate"; attribute :>> toNode="shared writer"; attribute :>> custody="Replace FIFO/reader/writer identity, preserve captured old roots"; }
part contract10:ContractRow { attribute :>> fromNode="captured continuation"; attribute :>> toNode="root retirement"; attribute :>> custody="Last reachable capture plus compiled map and native borrower receipts"; }
part contract11:ContractRow { attribute :>> fromNode="root retirement"; attribute :>> toNode="second normalization"; attribute :>> custody="Only complete admitted emission contract permits plan reuse"; }
part def BindingRow { attribute actionName:String; attribute lemma:String; attribute scope:String; }
part binding0:BindingRow { attribute :>> actionName="callback_carry_closure.beginLegal"; attribute :>> lemma="CallbackCarry.beginLegalPreserves"; attribute :>> scope="Abstract steps; attest actions are external obligations, not source receipts"; }
part binding1:BindingRow { attribute :>> actionName="callback_carry_closure.beginInternalCarry"; attribute :>> lemma="CallbackCarry.beginInternalCarryPreserves"; attribute :>> scope="Abstract steps; attest actions are external obligations, not source receipts"; }
part binding2:BindingRow { attribute :>> actionName="callback_carry_closure.advanceFifo"; attribute :>> lemma="CallbackCarry.advanceFifoPreserves"; attribute :>> scope="Abstract steps; attest actions are external obligations, not source receipts"; }
part binding3:BindingRow { attribute :>> actionName="callback_carry_closure.allocateCandidate"; attribute :>> lemma="CallbackCarry.allocateCandidatePreserves"; attribute :>> scope="Abstract steps; attest actions are external obligations, not source receipts"; }
part binding4:BindingRow { attribute :>> actionName="callback_carry_closure.installShared"; attribute :>> lemma="CallbackCarry.installSharedPreserves"; attribute :>> scope="Abstract steps; attest actions are external obligations, not source receipts"; }
part binding5:BindingRow { attribute :>> actionName="callback_carry_closure.expose"; attribute :>> lemma="CallbackCarry.exposePreserves"; attribute :>> scope="Abstract steps; attest actions are external obligations, not source receipts"; }
part binding6:BindingRow { attribute :>> actionName="callback_carry_closure.allocationFailure"; attribute :>> lemma="CallbackCarry.allocationFailurePreserves"; attribute :>> scope="Abstract steps; attest actions are external obligations, not source receipts"; }
part binding7:BindingRow { attribute :>> actionName="callback_carry_closure.capture"; attribute :>> lemma="CallbackCarry.capturePreserves"; attribute :>> scope="Abstract steps; attest actions are external obligations, not source receipts"; }
part binding8:BindingRow { attribute :>> actionName="callback_carry_closure.resume"; attribute :>> lemma="CallbackCarry.resumePreserves"; attribute :>> scope="Abstract steps; attest actions are external obligations, not source receipts"; }
part binding9:BindingRow { attribute :>> actionName="callback_carry_closure.returnActivation"; attribute :>> lemma="CallbackCarry.returnActivationPreserves"; attribute :>> scope="Abstract steps; attest actions are external obligations, not source receipts"; }
part binding10:BindingRow { attribute :>> actionName="callback_carry_closure.attestRootRetirement"; attribute :>> lemma="CallbackCarry.attestRootRetirementPreserves"; attribute :>> scope="Abstract steps; attest actions are external obligations, not source receipts"; }
part binding11:BindingRow { attribute :>> actionName="callback_carry_closure.release"; attribute :>> lemma="CallbackCarry.releasePreserves"; attribute :>> scope="Abstract steps; attest actions are external obligations, not source receipts"; }
part binding12:BindingRow { attribute :>> actionName="callback_carry_closure.changeRegistration"; attribute :>> lemma="CallbackCarry.changeRegistrationPreserves"; attribute :>> scope="Abstract steps; attest actions are external obligations, not source receipts"; }
part binding13:BindingRow { attribute :>> actionName="callback_carry_closure.unknownCallback"; attribute :>> lemma="CallbackCarry.unknownCallbackPreserves"; attribute :>> scope="Abstract steps; attest actions are external obligations, not source receipts"; }
part binding14:BindingRow { attribute :>> actionName="callback_carry_closure.attestEffects"; attribute :>> lemma="CallbackCarry.attestEffectsPreserves"; attribute :>> scope="Abstract steps; attest actions are external obligations, not source receipts"; }
part def ProofRow { attribute key:String; attribute lemma:String; }
part proof0:ProofRow { attribute :>> key="stepPreserves"; attribute :>> lemma="CallbackCarry.stepPreserves"; }
part proof1:ProofRow { attribute :>> key="reachableSafe"; attribute :>> lemma="CallbackCarry.reachableSafe"; }
part proof2:ProofRow { attribute :>> key="sharedCounterBias"; attribute :>> lemma="CallbackCarry.sharedCounterBias"; }
part proof3:ProofRow { attribute :>> key="capturePreventsRelease"; attribute :>> lemma="CallbackCarry.capturePreventsRelease"; }
part proof4:ProofRow { attribute :>> key="replayRetainsCapture"; attribute :>> lemma="CallbackCarry.replayRetainsCapture"; }
part proof5:ProofRow { attribute :>> key="releaseNeedsReceipt"; attribute :>> lemma="CallbackCarry.releaseNeedsReceipt"; }
part proof6:ProofRow { attribute :>> key="permitEpoch"; attribute :>> lemma="CallbackCarry.permitEpoch"; }
part proof7:ProofRow { attribute :>> key="failedAllocationRetainsRoots"; attribute :>> lemma="CallbackCarry.failedAllocationRetainsRoots"; }
part proof8:ProofRow { attribute :>> key="noCarryConserves"; attribute :>> lemma="CallbackCarry.noCarryConserves"; }
part def Need { attribute obligationId:String; attribute kind:String; attribute subjectPath:String; attribute subjectScope:String; ref owner:Owner; }
part formal:Need { attribute :>> obligationId="CC-formal"; attribute :>> kind="induction"; attribute :>> subjectPath="dev/refactoring/modern-c/models/lean/CallbackCarry.lean"; attribute :>> subjectScope="restricted typed IR to Lean all-step preservation"; ref :>> owner=compiler; }
part callbacks:Need { attribute :>> obligationId="CC-callbacks"; attribute :>> kind="source"; attribute :>> subjectPath="dev/refactoring/modern-c/callback-carry-closure-design.org"; attribute :>> subjectScope="complete actual-session transitive registration and alias closure"; ref :>> owner=compiler; }
part carry:Need { attribute :>> obligationId="CC-carry"; attribute :>> kind="source"; attribute :>> subjectPath="dev/refactoring/modern-c/callback-carry-closure-design.org"; attribute :>> subjectScope="legal carry producer and physical byte/counter semantics"; ref :>> owner=pipe; }
part roots:Need { attribute :>> obligationId="CC-roots"; attribute :>> kind="source"; attribute :>> subjectPath="vendor/gambit/lib/_io.scm"; attribute :>> subjectScope="generated program-point maps and multi-shot retirement"; ref :>> owner=pipe; }
part exceptions:Need { attribute :>> obligationId="CC-exceptions"; attribute :>> kind="equivalence"; attribute :>> subjectPath="dev/refactoring/modern-c/callback-carry-closure-design.org"; attribute :>> subjectScope="partial mutation allocation failure and output fault prefix equivalence"; ref :>> owner=compiler; }
part platform:Need { attribute :>> obligationId="CC-platform"; attribute :>> kind="platform"; attribute :>> subjectPath="dev/refactoring/modern-c/language-baseline-design.org"; attribute :>> subjectScope="C23 Darwin configuration ABI and native atomic qualification"; ref :>> owner=compiler; }
part emission:Need { attribute :>> obligationId="CC-emission"; attribute :>> kind="equivalence"; attribute :>> subjectPath="dev/refactoring/modern-c/emission-pipe-refinement-design.org"; attribute :>> subjectScope="full ordinary C emission fidelity and same entry"; ref :>> owner=compiler; }
part proof9:ProofRow { attribute :>> key="shared-delta"; attribute :>> lemma="CallbackCarry.sharedCarryDelta"; }
part proof10:ProofRow { attribute :>> key="nonshared-delta"; attribute :>> lemma="CallbackCarry.nonsharedCarryDelta"; }
part proof11:ProofRow { attribute :>> key="initialized-payload"; attribute :>> lemma="CallbackCarry.initializedPayload"; }
}
