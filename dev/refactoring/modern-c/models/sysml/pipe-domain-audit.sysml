package GambitPipeDomainAudit {
 private import ScalarValues::*;
 attribute scope:String="Complete peer-shared pipe ownership source/model/evidence companion. No independent SMP or universal runtime-speedup credit.";
 attribute stage:String="pipe-domain-audit";
 attribute formalDuty:String="Native SDK and ASCENT bind seven obligations and three real source adapters. QNT alone owns finite pipe exclusion/wait/close transitions; no new Lean arithmetic obligation. Framework tests prove source custody, not native semantics.";
 part submission:GambitCommitGates::SubmissionUnit {
 attribute :>> kind="support"; attribute :>> result=""; attribute :>> progressDelta=0;
 attribute :>> supportPaths="dev/refactoring/modern-c/diagrams/pipe-domain.d2;dev/refactoring/modern-c/diagrams/pipe-domain.svg;dev/refactoring/modern-c/index.org;dev/refactoring/modern-c/models/quint/pipe_domain.qnt;dev/refactoring/modern-c/models/sysml/delivery-outcomes.sysml;dev/refactoring/modern-c/models/sysml/pending-cuts.sysml;dev/refactoring/modern-c/models/sysml/pipe-domain-audit.sysml;dev/refactoring/modern-c/models/sysml/pipe-domain.sysml;dev/refactoring/modern-c/pipe-domain.org;dev/refactoring/modern-c/revision-checklist.org;evidence/research/retained/modern-c/pipe-domain/ascent-observation.json;evidence/research/retained/modern-c/pipe-domain/delivery.json;evidence/research/retained/modern-c/pipe-domain/existing-profile.json;evidence/research/retained/modern-c/pipe-domain/first-model-source.json;evidence/research/retained/modern-c/pipe-domain/first-proposal.json;evidence/research/retained/modern-c/pipe-domain/first-test-source.json;evidence/research/retained/modern-c/pipe-domain/framework-submission/review.json;evidence/research/retained/modern-c/pipe-domain/framework-submission/validation.json;evidence/research/retained/modern-c/pipe-domain/index-custody.json;evidence/research/retained/modern-c/pipe-domain/metrics.json;evidence/research/retained/modern-c/pipe-domain/model-binding.json;evidence/research/retained/modern-c/pipe-domain/model-sources/dev/modeling/models/sysml/commit-gates.sysml;evidence/research/retained/modern-c/pipe-domain/model-sources/dev/refactoring/modern-c/models/sysml/binding-activation.sysml;evidence/research/retained/modern-c/pipe-domain/model-sources/dev/refactoring/modern-c/models/sysml/delivery-outcomes.sysml;evidence/research/retained/modern-c/pipe-domain/model-sources/dev/refactoring/modern-c/models/sysml/delivery-plan.sysml;evidence/research/retained/modern-c/pipe-domain/model-sources/dev/refactoring/modern-c/models/sysml/header-organization.sysml;evidence/research/retained/modern-c/pipe-domain/model-sources/dev/refactoring/modern-c/models/sysml/pending-cuts.sysml;evidence/research/retained/modern-c/pipe-domain/model-sources/dev/refactoring/modern-c/models/sysml/pipe-domain.sysml;evidence/research/retained/modern-c/pipe-domain/model-sources/dev/refactoring/modern-c/models/sysml/request-product.sysml;evidence/research/retained/modern-c/pipe-domain/model-sources/dev/refactoring/modern-c/models/sysml/revision-delivery.sysml;evidence/research/retained/modern-c/pipe-domain/model-sources/dev/refactoring/modern-c/models/sysml/root-write.sysml;evidence/research/retained/modern-c/pipe-domain/model-sources/dev/refactoring/modern-c/models/sysml/sfun-entry.sysml;evidence/research/retained/modern-c/pipe-domain/pending-after.json;evidence/research/retained/modern-c/pipe-domain/pending-inventory.json;evidence/research/retained/modern-c/pipe-domain/post-ascent-observation.json;evidence/research/retained/modern-c/pipe-domain/post-model-binding.json;evidence/research/retained/modern-c/pipe-domain/post-model-sources/dev/modeling/models/sysml/commit-gates.sysml;evidence/research/retained/modern-c/pipe-domain/post-model-sources/dev/refactoring/modern-c/models/sysml/binding-activation.sysml;evidence/research/retained/modern-c/pipe-domain/post-model-sources/dev/refactoring/modern-c/models/sysml/delivery-outcomes.sysml;evidence/research/retained/modern-c/pipe-domain/post-model-sources/dev/refactoring/modern-c/models/sysml/delivery-plan.sysml;evidence/research/retained/modern-c/pipe-domain/post-model-sources/dev/refactoring/modern-c/models/sysml/header-organization.sysml;evidence/research/retained/modern-c/pipe-domain/post-model-sources/dev/refactoring/modern-c/models/sysml/pending-cuts.sysml;evidence/research/retained/modern-c/pipe-domain/post-model-sources/dev/refactoring/modern-c/models/sysml/pipe-domain.sysml;evidence/research/retained/modern-c/pipe-domain/post-model-sources/dev/refactoring/modern-c/models/sysml/request-product.sysml;evidence/research/retained/modern-c/pipe-domain/post-model-sources/dev/refactoring/modern-c/models/sysml/revision-delivery.sysml;evidence/research/retained/modern-c/pipe-domain/post-model-sources/dev/refactoring/modern-c/models/sysml/root-write.sysml;evidence/research/retained/modern-c/pipe-domain/post-model-sources/dev/refactoring/modern-c/models/sysml/sfun-entry.sysml;evidence/research/retained/modern-c/pipe-domain/qualification.json;evidence/research/retained/modern-c/pipe-domain/runs/pipe-accept-1.json;evidence/research/retained/modern-c/pipe-domain/runs/pipe-accept-2.json;evidence/research/retained/modern-c/pipe-domain/runs/pipe-accept-3.json;evidence/research/retained/modern-c/pipe-domain/runs/pipe-accept-4.json;evidence/research/retained/modern-c/pipe-domain/runs/pipe-baseline-1.json;evidence/research/retained/modern-c/pipe-domain/runs/pipe-baseline-compiler-1.json;evidence/research/retained/modern-c/pipe-domain/runs/pipe-baseline-population-1.json;evidence/research/retained/modern-c/pipe-domain/runs/pipe-consumers-1.json;evidence/research/retained/modern-c/pipe-domain/runs/pipe-cost-1.json;evidence/research/retained/modern-c/pipe-domain/runs/pipe-exact-profile-io-1.json;evidence/research/retained/modern-c/pipe-domain/runs/pipe-final-accept-1.json;evidence/research/retained/modern-c/pipe-domain/runs/pipe-final-accept-2.json;evidence/research/retained/modern-c/pipe-domain/runs/pipe-final-accept-3.json;evidence/research/retained/modern-c/pipe-domain/runs/pipe-final-consumers-1.json;evidence/research/retained/modern-c/pipe-domain/runs/pipe-final-cost-1.json;evidence/research/retained/modern-c/pipe-domain/runs/pipe-final-official-1.json;evidence/research/retained/modern-c/pipe-domain/runs/pipe-io-family-1.json;evidence/research/retained/modern-c/pipe-domain/runs/pipe-model-verify-1.json;evidence/research/retained/modern-c/pipe-domain/runs/pipe-model-verify-2.json;evidence/research/retained/modern-c/pipe-domain/runs/pipe-native-1.json;evidence/research/retained/modern-c/pipe-domain/runs/pipe-native-2.json;evidence/research/retained/modern-c/pipe-domain/runs/pipe-native-3.json;evidence/research/retained/modern-c/pipe-domain/runs/pipe-native-4.json;evidence/research/retained/modern-c/pipe-domain/runs/pipe-native-5.json;evidence/research/retained/modern-c/pipe-domain/runs/pipe-official-1.json;evidence/research/retained/modern-c/pipe-domain/runs/pipe-profile-io-1.json;evidence/research/retained/modern-c/pipe-domain/runs/pipe-qualified-cost-1.json;evidence/research/retained/modern-c/pipe-domain/runs/pipe-supplement-1.json;evidence/research/retained/modern-c/pipe-domain/selected-source.json;evidence/research/retained/modern-c/pipe-domain/source-review.json;evidence/research/retained/modern-c/pipe-domain/submission/admission.json;evidence/research/retained/modern-c/pipe-domain/submission/comment.json;evidence/research/retained/modern-c/pipe-domain/submission/model-contract.json;evidence/research/retained/modern-c/pipe-domain/submission/revision.json;evidence/research/retained/modern-c/pipe-domain/submission/source-manifest.json;evidence/research/retained/modern-c/pipe-domain/submission/source.json;src/gambit_smp/native_development.py;src/gambit_smp/runtime_binding.py;tests/test_native_development.py;tests/test_runtime_binding.py";
 attribute :>> testModules="tests/test_native_development.py;tests/test_runtime_binding.py";
 }
 part def Need { ref part gate:GambitCommitGates::Gate; attribute id:String; attribute method:String; attribute artifact:String; attribute scope:String; }
 part tests:Need { ref part :>> gate=GambitCommitGates::tests; attribute :>> id="PIPE-DOMAIN-AUDIT-TESTS"; attribute :>> method="native"; attribute :>> artifact="evidence/research/retained/modern-c/pipe-domain/framework-submission/validation.json"; attribute :>> scope="39 unchanged source-selected framework tests reused by exact identity; independent runtime five-gate admission and production profile tests retained."; }
 part learning:Need { ref part :>> gate=GambitCommitGates::learning; attribute :>> id="PIPE-DOMAIN-AUDIT-LEARNING"; attribute :>> method="source-analysis"; attribute :>> artifact="dev/refactoring/modern-c/pipe-domain.org"; attribute :>> scope="Shared aliased state requires a common guard; preserve ordinary constructor allocation order. Allocation counters are not literal physical bytes."; }
 part process:Need { ref part :>> gate=GambitCommitGates::process; attribute :>> id="PIPE-DOMAIN-AUDIT-PROCESS"; attribute :>> method="source-analysis"; attribute :>> artifact="dev/refactoring/modern-c/pipe-domain.org"; attribute :>> scope="One whole four-path runtime cut;48 remaining source paths/nine nonempty owners. Independent SMP remains1/12."; }
 part models:Need { ref part :>> gate=GambitCommitGates::models; attribute :>> id="PIPE-DOMAIN-AUDIT-MODELS"; attribute :>> method="native"; attribute :>> artifact="evidence/research/retained/modern-c/pipe-domain/framework-submission/review.json"; attribute :>> scope="Native SDK seven obligations/three adapters, ASCENT current/missing/stale controls, finite QNT125 states; no repeated Lean model."; }
 part questions:Need { ref part :>> gate=GambitCommitGates::questions; attribute :>> id="PIPE-DOMAIN-AUDIT-QUESTIONS"; attribute :>> method="source-analysis"; attribute :>> artifact="dev/refactoring/modern-c/pipe-domain.org"; attribute :>> scope="Owner publication, exception/wait reentry, roots, generation closure and paired cost answered conditionally. Default compiler and whole-population failures unresolved."; }
}
