package GambitOwnedLifetime {
  private import ScalarValues::*;
  ref part outcome=GambitModernCOutcomes::lifetime;
  attribute scope:String="One complete ownership replacement: rooted startup request, physical reservation, initialization and membership publication, writer/root/worker drain, owner-affine cleanup and unknown-join isolation. Keep shared multi-shot continuation and C portability. The selected private lifecycle control replaces the old resize-only owner; unrelated staged prototypes are excluded.";
  attribute stage:String="Complete22-obligation runtime delivery. The receipt and ASCENT admission own current closure; implementation, intermediate producer, shadow-link diagnostics and model checks alone do not grant a progress increment. Retain out-of-bounds argument and shared-status/barrier counterexamples.";
  attribute formalDuty:String="Use existing ownership/lifecycle QNT schedules for publication, drain and unknown custody; existing Lean conditional identity/capacity laws retain their premises. Here SysML selects the complete source/native refinement and ASCENT submission closure. Do not repeat the schedule proof in Lean or count the model as C implementation.";
  attribute sourceCases:String="request-roots;physical-members;writer-close;registry-lifetime;unknown-isolation";
  attribute requiredCases:String="partial-create-known;partial-create-unknown;nonzero-processor-roots;multi-shot-continuation;owner-cleanup;healthy-vm-gc;replay-shrink;original-consumers";
  attribute graph:String="request -> request_rc -> physical_intervals -> initialized -> launch_parked -> member_closed -> member_commit -> launch_run; launch_run -> root_tasks -> owner_restore -> writer_close -> root_drain -> owner_effects -> data_closed -> native_join -> retire; launch_parked -> abort -> descriptor_retained -> healthy_gc; descriptor_retained -> deny_slot_reuse; descriptor_retained -> deny_global_free; whole_round_end -> owner_effects; nested_host_marker -> deny_retirement; owner_request_debt -> deny_retirement; effect_unknown -> resource_retained -> deny_global_free; predecessors -> all22 -> admission; all22 -> retire;";
  attribute implementation:String="lib/lifecycle.h;lib/_setup/vm-registry.inc;lib/_setup/vm-lifecycle.inc;lib/setup.c;lib/c_intf.c;lib/_mem/startup-reservation.inc;lib/_mem/still-sweep.inc;lib/_mem/collection-round.inc";
  attribute decision:String="Each resize cut is a root-owned immutable value distributed by the existing barrier message. Capacity need is voted before GC can change its counters; reader-close and root-close decisions cannot alias later errors; join outcome is delivered to all surviving members including nonzero requesters. RC refusal exposed the former shared-status/barrier mismatch.";
  attribute publication:String="Native mutex publishes parked descriptor RUN/ABORT and generation. Existing C full-word acquire/release and CAS protect VM registry, member readers, entry leases and pending signal delivery. A failed reader also attempts pending delivery after publication, closing the open-versus-late-publish gap. No native callback executes under a registry writer or stopped collective. GC root completion never waits for arbitrary owner effects; the collector consumer obtains query-only receipts through its existing pinned-owner tasks before checking all release counts.";
  attribute retirement:String="Membership close excludes interrupt readers before OS cleanup. Root-source cleanup requires no RC borrow, scan lease, joined round or unresolved census. Only the exact rooted startup activation grants terminal stack ownership; nested host markers and unrelated entry leases reject retirement. GC-retryable affine garbage is distinct from active requests/uncertain native debt, which refuse without a GC retry. DRAINED preserves the topology/control pin and retries only final unlink/global permission, without repeating data cleanup or effects. Known constructor rollback reclaims completed stages in reverse order; unknown native/effect debt retains identity/storage and forbids global reclamation.";
  attribute modelSelection:String="Existing vm_resize_transaction.qnt owns parked/publication/abort/native-debt/refund/healthy-GC schedules. Existing vm_registry.qnt supplies borrowed-list admission and pending-notification schedules, refined separately to the member gate. Existing capacity_collective.qnt now also owns staggered cut delivery: later coordinator work cannot overwrite a delivered/consumed earlier decision. The source adapter is resize_decision over existing two-slot messages, not r->result. Existing runtime_ownership.qnt retains root tasks/multi-shot restoration. Lean root/interval arithmetic is unchanged; its C premises are source/native obligations, not another schedule proof.";
  part def Source { attribute id:String; attribute path:String; attribute anchor:String; attribute supportingPaths:String; attribute supportingAnchors:String; attribute obligation:String; }
  part adapter0:Source { attribute :>> id="request-roots"; attribute :>> path="lib/setup.c"; attribute :>> anchor="___current_vm_resize"; attribute :>> supportingPaths="lib/setup.c;lib/c_intf.c"; attribute :>> supportingAnchors="run_startup_root;___make_sfun_stack_marker_root"; attribute :>> obligation="The real request owns a registered RC cell before on_all_processors and uses that stable cell across collection. Every initialization/root handoff is reloaded. Both normal/throw paths release source leases; marker activation is reserved before its allocating constructor. No stack-local movable thunk is the collective identity."; }
  part adapter1:Source { attribute :>> id="physical-members"; attribute :>> path="lib/_mem/startup-reservation.inc"; attribute :>> anchor="___reserve_resize"; attribute :>> supportingPaths="lib/setup.c;lib/setup.c;lib/setup.c"; attribute :>> supportingAnchors="___resize_launch;RESIZE_CAPACITY_NEEDED;RESIZE_JOIN_CUSTODY"; attribute :>> obligation="The old cohort agrees on immutable capacity-needed/result messages, physical pairs and resume allowance are reserved before setup/create. Native descriptors remain PARKED until complete old-set publication; ABORT precedes refund. Generation cannot recycle uncertain native identity. Count publication and join outcome are delivered to all surviving requesters, including nonzero owner."; }
  part adapter2:Source { attribute :>> id="writer-close"; attribute :>> path="lib/_setup/vm-registry.inc"; attribute :>> anchor="___lifecycle_enter"; attribute :>> supportingPaths="lib/_mem/still-sweep.inc;lib/_setup/vm-lifecycle.inc;lib/setup.c"; attribute :>> supportingAnchors="___lifecycle_can_handoff;lifecycle_close_context;startup=1"; attribute :>> obligation="Existing owner/TLS entry leases, RC borrow/scan/joined-round closure and member-reader gate exclude physical teardown. Only run_startup_root grants terminal activation capability; nested host marker/unrelated entry refuses. HANDOFF_GC permits one full owner-drained collection retry, HANDOFF_BUSY never turns uncertain native/control debt into a GC-completable debt. Under the managed entry/collective contract, retiring owners close markers, transfer ordinary still ownership, cleanup their own OS state and publish data_closed before native exit."; }
  part adapter3:Source { attribute :>> id="registry-lifetime"; attribute :>> path="lib/_setup/vm-registry.inc"; attribute :>> anchor="___lifecycle_registry_begin"; attribute :>> supportingPaths="lib/_setup/vm-lifecycle.inc;lib/_setup/vm-lifecycle.inc;lib/_setup/vm-lifecycle.inc"; attribute :>> supportingAnchors="abort_vm_setup;cleanup_runtime;___VM_DRAINED"; attribute :>> obligation="Allocator insertion/removal is retired. Private pinned registry publishes only fully initialized LIVE VMs and reverses completed constructor stages on known failure. Shutdown prevents new VM publication; refused per-VM cleanup never authorizes global release. No arbitrary user effect runs with a registry writer or stopped collective. Reader/pending-bit CAS uses existing sequential/full-word acquire/release primitives; C weak-memory completeness outside supported backend primitives is not claimed."; }
  part adapter4:Source { attribute :>> id="unknown-isolation"; attribute :>> path="lib/setup.c"; attribute :>> anchor="___LAUNCH_ABORT"; attribute :>> supportingPaths="lib/lifecycle.h;lib/_mem/still-sweep.inc;lib/_setup/vm-lifecycle.inc"; attribute :>> supportingAnchors="data_closed;___lifecycle_drain;___VM_RETAINED"; attribute :>> obligation="Pre-RUN unknown create/join retains the descriptor but can refund roots/physical grants because ABORT forbids PSTATE acquisition. RUN loss needs owner data closure before healthy surviving members collect. Native identity remains quarantined, slot reuse and global free refuse. Unknown foreign result preserves the original in-flight resource/function/payload and charge with no automatic replay. The affected VM may remain retained; a distinct healthy VM still performs moving GC and multi-shot map restores."; }
  part submission:GambitCommitGates::SubmissionUnit {
    attribute :>> kind="integration";
    attribute :>> result=GambitModernCOutcomes::lifetime.id;
    attribute :>> progressDelta=1; attribute :>> supportPaths="";
  }
  part def Need { ref part gate:GambitCommitGates::Gate; attribute id:String; attribute method:String; attribute artifact:String; attribute scope:String; }
  part tests:Need { ref part :>> gate=GambitCommitGates::tests; attribute :>> id="LIFETIME-NATIVE"; attribute :>> method="native"; attribute :>> artifact="evidence/research/retained/modern-c/owned-lifetime/receipt.json"; attribute :>> scope="Final exact-source native producer, complete current root/worker regressions, startup/retirement/cleanup/unknown isolation, implementation PBT replay/shrink and original consumers on the unchanged cache/profile/limits. Require the final receipt; intermediate diagnostic runs never count."; }
  part learning:Need { ref part :>> gate=GambitCommitGates::learning; attribute :>> id="LIFETIME-LEARNING"; attribute :>> method="source-analysis"; attribute :>> artifact="dev/refactoring/modern-c/delivery-contract.org"; attribute :>> scope="Replace carrier lifetime assumptions by explicit roots, execution participation, worker debts and resource-specific retirement; no copied repair patch."; }
  part process:Need { ref part :>> gate=GambitCommitGates::process; attribute :>> id="LIFETIME-PROCESS"; attribute :>> method="source-analysis"; attribute :>> artifact="dev/refactoring/modern-c/delivery-contract.org"; attribute :>> scope="All9 programme obligations across current result and its two predecessors plus5 source/8 native cases gate one result. Scheduler/request-product is the next result, not part of this one."; }
  part models:Need { ref part :>> gate=GambitCommitGates::models; attribute :>> id="LIFETIME-MODELS"; attribute :>> method="source-refinement"; attribute :>> artifact="evidence/research/retained/modern-c/owned-lifetime/source-review.json"; attribute :>> scope="Current source/receipt adapters must establish actual ownership and C ordering premises before existing model consequences apply. Prototype observation cannot qualify these adapters."; }
  part questions:Need { ref part :>> gate=GambitCommitGates::questions; attribute :>> id="LIFETIME-QUESTIONS"; attribute :>> method="source-analysis"; attribute :>> artifact="dev/refactoring/modern-c/delivery-contract.org"; attribute :>> scope="Which stopped/closed facts authorize each free? Who owns uncertain native effects and roots? Can a retained VM avoid blocking healthy VM GC without permitting global reclamation? How are shared multi-shot frames preserved?"; }
}
