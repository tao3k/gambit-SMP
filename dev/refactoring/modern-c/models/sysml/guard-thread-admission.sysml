package GambitGuardThreadAdmission { private import ScalarValues::*;
part def Owner { attribute componentId:String; }
part admissionOwner:Owner { attribute :>> componentId="admission"; }
part rootsOwner:Owner { attribute :>> componentId="roots"; }
part controlOwner:Owner { attribute :>> componentId="control"; }
part def SourceRow { attribute key:String; attribute path:String; attribute needle:String; attribute obligation:String; }
part source0:SourceRow { attribute :>> key="allocate"; attribute :>> path="vendor/gambit/lib/_mem/rc-allocation.inc"; attribute :>> needle="___ALLOC_MEM(bytes + sizeof (___rc_header))"; attribute :>> obligation="Checked extent and stable allocation attempt must precede this effect"; }
part source1:SourceRow { attribute :>> key="register"; attribute :>> path="vendor/gambit/lib/_mem/rc-allocation.inc"; attribute :>> needle="tail->next = h;"; attribute :>> obligation="Current append has no result ledger or admission transaction"; }
part source2:SourceRow { attribute :>> key="cleanup"; attribute :>> path="vendor/gambit/lib/_mem/rc-allocation.inc"; attribute :>> needle="___HIDDEN void cleanup_rc"; attribute :>> obligation="Current bulk free has no stable attempt or outstanding ticket census"; }
part source3:SourceRow { attribute :>> key="root-scan"; attribute :>> path="vendor/gambit/lib/_mem/rc-roots.inc"; attribute :>> needle="mark_array (work, &h->data, 1);"; attribute :>> obligation="New ticket root carrier not automatically covered by old RC chain"; }
part source4:SourceRow { attribute :>> key="tcl"; attribute :>> path="vendor/gambit/examples/tcltk/tcltk.scm"; attribute :>> needle="void *cd = ___EXT(___alloc_rc) (0);"; attribute :>> obligation="Real zero payload caller still owns header and later allocates Scheme vector"; }
part source5:SourceRow { attribute :>> key="throw"; attribute :>> path="vendor/gambit/include/_gambit/foreign_conversion.h.in"; attribute :>> needle="#define ___THROW(e)do { ___ps->longjmp_err = e;"; attribute :>> obligation="C nonlocal exit has no automatic ticket cleanup; reject unmediated crossing"; }
part source6:SourceRow { attribute :>> key="call"; attribute :>> path="vendor/gambit/lib/setup.c"; attribute :>> needle="___EXP_FUNC(___SCMOBJ,___call)"; attribute :>> obligation="Existing catcher and marker paths do not create stable allocation attempt records"; }
part source7:SourceRow { attribute :>> key="export"; attribute :>> path="vendor/gambit/lib/setup.c"; attribute :>> needle="= ___alloc_rc_no_register;"; attribute :>> obligation="Public indirect allocation callers not closed by literal inventory"; }
part source8:SourceRow { attribute :>> key="teardown"; attribute :>> path="vendor/gambit/lib/_mem/memory-lifecycle.inc"; attribute :>> needle="free_still_objs (___ps);"; attribute :>> obligation="Source Scheme roots must survive cleanup ordering before RC bulk free"; }
part source9:SourceRow { attribute :>> key="mask-root-request"; attribute :>> path="vendor/gambit/lib/setup.c"; attribute :>> needle="if (pthread_setcancelstate(PTHREAD_CANCEL_DISABLE, &cancel_state) != 0)"; attribute :>> obligation="Root request caller checks mask result before control transfer"; }
part source10:SourceRow { attribute :>> key="restore-root-request"; attribute :>> path="vendor/gambit/lib/setup.c"; attribute :>> needle="pthread_setcancelstate(cancel_state, NULL);"; attribute :>> obligation="Restore is a separate edge; successful earlier disable is not permanent authority"; }
part source11:SourceRow { attribute :>> key="sfun-marker"; attribute :>> path="vendor/gambit/include/_gambit/foreign_conversion.h.in"; attribute :>> needle="#define ___BEGIN_SFUN(proc,decl)"; attribute :>> obligation="Generated entry allocates marker before Scheme call; not stable allocation guard"; }
part source12:SourceRow { attribute :>> key="marker-new"; attribute :>> path="vendor/gambit/lib/c_intf.c"; attribute :>> needle="stack_marker = ___make_vector (___ps, 2, ___FAL);"; attribute :>> obligation="Marker may allocate Scheme storage; disallow in unrecorded native-return segment"; }
part source13:SourceRow { attribute :>> key="marker-root"; attribute :>> path="vendor/gambit/lib/c_intf.c"; attribute :>> needle="proc_or_false = *proc_root; /* reload after allocating the marker */"; attribute :>> obligation="Root slot must actually remain registered; local raw wrapper alone is not registration"; }
part source14:SourceRow { attribute :>> key="marker-kill"; attribute :>> path="vendor/gambit/lib/c_intf.c"; attribute :>> needle="___VECTORELEM(marker, 0) = ___FAL; /* invalidate the C stack frame */"; attribute :>> obligation="Invalidation protects C return extent; cannot settle an allocation ticket"; }
part source15:SourceRow { attribute :>> key="sfun-emitter"; attribute :>> path="vendor/gambit/gsc/_ptree2.scm"; attribute :>> needle="(define (c-function param-typs result-typ proc-name c-defined? scope)"; attribute :>> obligation="Real Scheme generator for SFUN_CALL and marker macros"; }
part source16:SourceRow { attribute :>> key="tcl-apply"; attribute :>> path="vendor/gambit/examples/tcltk/tcltk.scm"; attribute :>> needle="(let ((result (##apply proc args)))"; attribute :>> obligation="Arbitrary exported Scheme procedure can nest Tcl evaluation and allocation"; }
part source17:SourceRow { attribute :>> key="tcl-eval"; attribute :>> path="vendor/gambit/examples/tcltk/tcltk.scm"; attribute :>> needle="Tcl_Eval (tcl_interp, cmd)"; attribute :>> obligation="Real native evaluation invokes registered command callbacks"; }
part source18:SourceRow { attribute :>> key="self-thread"; attribute :>> path="vendor/gambit/lib/os_thread.c"; attribute :>> needle="thread->thread_id = pthread_self ();"; attribute :>> obligation="OS thread identity assignment does not register guard roots or cancellation custody"; }
part source19:SourceRow { attribute :>> key="tls-publish"; attribute :>> path="vendor/gambit/lib/os_thread.c"; attribute :>> needle="pthread_setspecific (___thread_mod.tls_ptr_key, ptr); /* ignore error */"; attribute :>> obligation="Selected fallback ignores publication failure; cannot sign a checked thread-admission receipt"; }
part source20:SourceRow { attribute :>> key="tls-direct"; attribute :>> path="vendor/gambit/lib/os_thread.c"; attribute :>> needle="___tls_ptr = ptr;"; attribute :>> obligation="Direct TLS branch exists; effective backend and runtime work must be qualified"; }
part source21:SourceRow { attribute :>> key="thread-bind"; attribute :>> path="vendor/gambit/lib/os_thread.c"; attribute :>> needle="___thread_affinity_set (___ps);"; attribute :>> obligation="Binding helper also invokes affinity logic; it is not a leaf root registration primitive"; }
part source22:SourceRow { attribute :>> key="tls-key"; attribute :>> path="vendor/gambit/lib/os_thread.c"; attribute :>> needle="pthread_key_create (&___thread_mod.tls_ptr_key, NULL)"; attribute :>> obligation="Thread-module initialization creates key with no destructor; not stable cancellation cleanup ownership"; }
part source23:SourceRow { attribute :>> key="tls-delete"; attribute :>> path="vendor/gambit/lib/os_thread.c"; attribute :>> needle="pthread_key_delete (___thread_mod.tls_ptr_key); /* ignore error */"; attribute :>> obligation="Module shutdown requires absence of late users before deleting native lookup facility"; }
part source24:SourceRow { attribute :>> key="main-bind"; attribute :>> path="vendor/gambit/lib/setup.c"; attribute :>> needle="___thread_init_from_self (&___ps->os_thread)"; attribute :>> obligation="Real main setup caller binds after VM setup; not generic foreign-thread enrollment"; }
part source25:SourceRow { attribute :>> key="native-pstate"; attribute :>> path="vendor/gambit/include/_gambit/module_generation.h.in"; attribute :>> needle="#define ___GET_REAL_PSTATE() ___CAST(___processor_state,___EXT(___get_tls_ptr) ())"; attribute :>> obligation="Lookup alone does not prove native thread or execution context ownership"; }
part source26:SourceRow { attribute :>> key="retire-refusal"; attribute :>> path="vendor/gambit/lib/_mem/capacity-resize.inc"; attribute :>> needle="return 0; /* no freeze receipt for external RC/native borrowers */"; attribute :>> obligation="Real retirement refusal preserves external native debt rather than inventing admission"; }
part source27:SourceRow { attribute :>> key="paper-fulltext"; attribute :>> path="evidence/research/source-references/feeley-sfp/8bb2fae8ae4b54d3a86206596f90e9cf73da39846af0f39244a476074cf81ed4.txt"; attribute :>> needle="We have not yet implemented this approa h in Gambit-C."; attribute :>> obligation="Official SFP2000 PostScript text extraction has missing glyphs; exact source and PDF hashes retained; proposed C-thread stacks are not current code"; }
part def IssuerRow { attribute key:String; attribute proposedIssuer:String; attribute actualSource:String; attribute status:String; attribute responsibility:String; }
part issuer0:IssuerRow { attribute :>> key="offer"; attribute :>> proposedIssuer="VM lifecycle and native-source owner"; attribute :>> actualSource="Tcl alloc_rc and command registration"; attribute :>> status="new envelope issuer absent"; attribute :>> responsibility="Preissue native descriptor and source root responsibility before recipient arrival"; }
part issuer1:IssuerRow { attribute :>> key="thread"; attribute :>> proposedIssuer="NativeThreadDomain owner"; attribute :>> actualSource="thread_init_from_self thread_set_pstate TLS helpers"; attribute :>> status="OS identity and binding exist; checked enrollment absent"; attribute :>> responsibility="Confirm cancellation profile then bind exact VM context with lifetime lease"; }
part issuer2:IssuerRow { attribute :>> key="guard"; attribute :>> proposedIssuer="VM AttemptRegistry"; attribute :>> actualSource="context RC list insertion"; attribute :>> status="nonallocating registry signer absent"; attribute :>> responsibility="Claim preallocated slot and root carrier without callback allocation or implicit TLS bootstrap"; }
part issuer3:IssuerRow { attribute :>> key="root"; attribute :>> proposedIssuer="VM RootRegistry round owner"; attribute :>> actualSource="mark_rc on context RC chain"; attribute :>> status="generic VM carrier round adapter absent"; attribute :>> responsibility="Acknowledge exact target root in collector round before source root release"; }
part issuer4:IssuerRow { attribute :>> key="exit"; attribute :>> proposedIssuer="stable completion owner"; attribute :>> actualSource="BEGIN_TRY and kill_sfun_stack_marker"; attribute :>> status="catcher marker exist; stable completion signer absent"; attribute :>> responsibility="Own root TLS and return-domain debt before restoring cancellation"; }
part issuer5:IssuerRow { attribute :>> key="nested"; attribute :>> proposedIssuer="generated FFI entry owner"; attribute :>> actualSource="c-function and BEGIN_SFUN macros"; attribute :>> status="legacy marker issuer exists; new guard identity absent"; attribute :>> responsibility="Separate activation identity and preserve outer disabled cancellation state"; }
part issuer6:IssuerRow { attribute :>> key="segment"; attribute :>> proposedIssuer="NativeReturnDomain and segment lifecycle owner"; attribute :>> actualSource="call frame marker and actual C stack"; attribute :>> status="paper C-thread segment proposal not established in checkout"; attribute :>> responsibility="Separate Scheme continuation reachability from live native-frame return rights"; }
part issuer7:IssuerRow { attribute :>> key="retirement"; attribute :>> proposedIssuer="VM domain and scanner owners"; attribute :>> actualSource="cleanup_rc cleanup_thread_module retirement refusal"; attribute :>> status="joint guard retirement issuer absent"; attribute :>> responsibility="Require context detach scan grace resolved child and closed replay admission"; }
part def NeedRow { attribute key:String; attribute kind:String; attribute path:String; attribute scope:String; ref owner:Owner; }
part need0:NeedRow { attribute :>> key="Admission-formal"; attribute :>> kind="formal"; attribute :>> path="dev/refactoring/modern-c/models/quint/guard_thread_admission.qnt"; attribute :>> scope="one source offer one outer and one nested admission; finite safety"; ref :>> owner=admissionOwner; }
part need1:NeedRow { attribute :>> key="Admission-bridge"; attribute :>> kind="bridge"; attribute :>> path="dev/refactoring/modern-c/models/lean/GuardAdmission.lean"; attribute :>> scope="typed IR mirror all-step induction; root and enrollment events trusted premises"; ref :>> owner=admissionOwner; }
part need2:NeedRow { attribute :>> key="Admission-bootstrap"; attribute :>> kind="native"; attribute :>> path="vendor/gambit/examples/tcltk/tcltk.scm"; attribute :>> scope="source offer pin before cancellation or raw data_rc access unresolved"; ref :>> owner=admissionOwner; }
part need3:NeedRow { attribute :>> key="Admission-registry"; attribute :>> kind="native"; attribute :>> path="vendor/gambit/lib/_mem/rc-roots.inc"; attribute :>> scope="nonallocating root registration every-GC membership and transfer acknowledgment unresolved"; ref :>> owner=rootsOwner; }
part need4:NeedRow { attribute :>> key="Admission-TLS"; attribute :>> kind="native"; attribute :>> path="vendor/gambit/lib/os_thread.c"; attribute :>> scope="checked native-thread VM context and selected TLS backend unresolved"; ref :>> owner=admissionOwner; }
part need5:NeedRow { attribute :>> key="Admission-exit"; attribute :>> kind="native"; attribute :>> path="vendor/gambit/include/_gambit/foreign_conversion.h.in"; attribute :>> scope="stable owner before cancellation restore including no-return outcomes unresolved"; ref :>> owner=controlOwner; }
part need6:NeedRow { attribute :>> key="Admission-nesting"; attribute :>> kind="native"; attribute :>> path="vendor/gambit/lib/setup.c"; attribute :>> scope="native-frame return domains multi-shot continuation and arbitrary nesting unresolved"; ref :>> owner=controlOwner; }
part need7:NeedRow { attribute :>> key="Admission-retirement"; attribute :>> kind="native"; attribute :>> path="vendor/gambit/lib/_mem/memory-lifecycle.inc"; attribute :>> scope="late observers native frame borrowers root grace and thread registry shutdown unresolved"; ref :>> owner=admissionOwner; }
part def BindingRow { attribute actionName:String; attribute lemma:String; }
part binding0:BindingRow { attribute :>> actionName="guard_thread_admission.arrive"; attribute :>> lemma="GuardAdmission.arrivePreserves"; }
part binding1:BindingRow { attribute :>> actionName="guard_thread_admission.cancelBeforeRegistration"; attribute :>> lemma="GuardAdmission.cancelBeforeRegistrationPreserves"; }
part binding2:BindingRow { attribute :>> actionName="guard_thread_admission.maskConfirmed"; attribute :>> lemma="GuardAdmission.maskConfirmedPreserves"; }
part binding3:BindingRow { attribute :>> actionName="guard_thread_admission.maskOutcomeUnknown"; attribute :>> lemma="GuardAdmission.maskOutcomeUnknownPreserves"; }
part binding4:BindingRow { attribute :>> actionName="guard_thread_admission.reserveGuard"; attribute :>> lemma="GuardAdmission.reserveGuardPreserves"; }
part binding5:BindingRow { attribute :>> actionName="guard_thread_admission.capacityReject"; attribute :>> lemma="GuardAdmission.capacityRejectPreserves"; }
part binding6:BindingRow { attribute :>> actionName="guard_thread_admission.publishRegistry"; attribute :>> lemma="GuardAdmission.publishRegistryPreserves"; }
part binding7:BindingRow { attribute :>> actionName="guard_thread_admission.publicationUnknown"; attribute :>> lemma="GuardAdmission.publicationUnknownPreserves"; }
part binding8:BindingRow { attribute :>> actionName="guard_thread_admission.queryCommitted"; attribute :>> lemma="GuardAdmission.queryCommittedPreserves"; }
part binding9:BindingRow { attribute :>> actionName="guard_thread_admission.queryAbsent"; attribute :>> lemma="GuardAdmission.queryAbsentPreserves"; }
part binding10:BindingRow { attribute :>> actionName="guard_thread_admission.roundAcknowledged"; attribute :>> lemma="GuardAdmission.roundAcknowledgedPreserves"; }
part binding11:BindingRow { attribute :>> actionName="guard_thread_admission.releaseSourceRoot"; attribute :>> lemma="GuardAdmission.releaseSourceRootPreserves"; }
part binding12:BindingRow { attribute :>> actionName="guard_thread_admission.bindContext"; attribute :>> lemma="GuardAdmission.bindContextPreserves"; }
part binding13:BindingRow { attribute :>> actionName="guard_thread_admission.bindingUnknown"; attribute :>> lemma="GuardAdmission.bindingUnknownPreserves"; }
part binding14:BindingRow { attribute :>> actionName="guard_thread_admission.enterApplication"; attribute :>> lemma="GuardAdmission.enterApplicationPreserves"; }
part binding15:BindingRow { attribute :>> actionName="guard_thread_admission.beginNested"; attribute :>> lemma="GuardAdmission.beginNestedPreserves"; }
part binding16:BindingRow { attribute :>> actionName="guard_thread_admission.nestedPublish"; attribute :>> lemma="GuardAdmission.nestedPublishPreserves"; }
part binding17:BindingRow { attribute :>> actionName="guard_thread_admission.nestedRoundAcknowledged"; attribute :>> lemma="GuardAdmission.nestedRoundAcknowledgedPreserves"; }
part binding18:BindingRow { attribute :>> actionName="guard_thread_admission.nestedPublicationUnknown"; attribute :>> lemma="GuardAdmission.nestedPublicationUnknownPreserves"; }
part binding19:BindingRow { attribute :>> actionName="guard_thread_admission.queryNestedCommitted"; attribute :>> lemma="GuardAdmission.queryNestedCommittedPreserves"; }
part binding20:BindingRow { attribute :>> actionName="guard_thread_admission.returnNested"; attribute :>> lemma="GuardAdmission.returnNestedPreserves"; }
part binding21:BindingRow { attribute :>> actionName="guard_thread_admission.nestedExitUnknown"; attribute :>> lemma="GuardAdmission.nestedExitUnknownPreserves"; }
part binding22:BindingRow { attribute :>> actionName="guard_thread_admission.armOuterExit"; attribute :>> lemma="GuardAdmission.armOuterExitPreserves"; }
part binding23:BindingRow { attribute :>> actionName="guard_thread_admission.armAfterNested"; attribute :>> lemma="GuardAdmission.armAfterNestedPreserves"; }
part binding24:BindingRow { attribute :>> actionName="guard_thread_admission.restoreReturns"; attribute :>> lemma="GuardAdmission.restoreReturnsPreserves"; }
part binding25:BindingRow { attribute :>> actionName="guard_thread_admission.restoreDoesNotReturn"; attribute :>> lemma="GuardAdmission.restoreDoesNotReturnPreserves"; }
part binding26:BindingRow { attribute :>> actionName="guard_thread_admission.restoreUnknown"; attribute :>> lemma="GuardAdmission.restoreUnknownPreserves"; }
part binding27:BindingRow { attribute :>> actionName="guard_thread_admission.closeAdmission"; attribute :>> lemma="GuardAdmission.closeAdmissionPreserves"; }
part binding28:BindingRow { attribute :>> actionName="guard_thread_admission.tlsDetachKnown"; attribute :>> lemma="GuardAdmission.tlsDetachKnownPreserves"; }
part binding29:BindingRow { attribute :>> actionName="guard_thread_admission.scanGraceKnown"; attribute :>> lemma="GuardAdmission.scanGraceKnownPreserves"; }
part binding30:BindingRow { attribute :>> actionName="guard_thread_admission.retireActiveGuard"; attribute :>> lemma="GuardAdmission.retireActiveGuardPreserves"; }
part def RouteRow { attribute component:String; attribute actionName:String; attribute lemma:String; attribute producerAnchor:String; attribute obligationId:String; }
part route0:RouteRow { attribute :>> component="admission"; attribute :>> actionName="guard_thread_admission.arrive"; attribute :>> lemma="GuardAdmission.arrivePreserves"; attribute :>> producerAnchor="tcl"; attribute :>> obligationId="Admission-bootstrap"; }
part route1:RouteRow { attribute :>> component="admission"; attribute :>> actionName="guard_thread_admission.cancelBeforeRegistration"; attribute :>> lemma="GuardAdmission.cancelBeforeRegistrationPreserves"; attribute :>> producerAnchor="tcl"; attribute :>> obligationId="Admission-bootstrap"; }
part route2:RouteRow { attribute :>> component="admission"; attribute :>> actionName="guard_thread_admission.maskConfirmed"; attribute :>> lemma="GuardAdmission.maskConfirmedPreserves"; attribute :>> producerAnchor="tcl"; attribute :>> obligationId="Admission-bootstrap"; }
part route3:RouteRow { attribute :>> component="admission"; attribute :>> actionName="guard_thread_admission.maskOutcomeUnknown"; attribute :>> lemma="GuardAdmission.maskOutcomeUnknownPreserves"; attribute :>> producerAnchor="tcl"; attribute :>> obligationId="Admission-bootstrap"; }
part route4:RouteRow { attribute :>> component="admission"; attribute :>> actionName="guard_thread_admission.reserveGuard"; attribute :>> lemma="GuardAdmission.reserveGuardPreserves"; attribute :>> producerAnchor="tcl"; attribute :>> obligationId="Admission-bootstrap"; }
part route5:RouteRow { attribute :>> component="admission"; attribute :>> actionName="guard_thread_admission.capacityReject"; attribute :>> lemma="GuardAdmission.capacityRejectPreserves"; attribute :>> producerAnchor="tcl"; attribute :>> obligationId="Admission-bootstrap"; }
part route6:RouteRow { attribute :>> component="roots"; attribute :>> actionName="guard_thread_admission.publishRegistry"; attribute :>> lemma="GuardAdmission.publishRegistryPreserves"; attribute :>> producerAnchor="root-scan"; attribute :>> obligationId="Admission-registry"; }
part route7:RouteRow { attribute :>> component="roots"; attribute :>> actionName="guard_thread_admission.publicationUnknown"; attribute :>> lemma="GuardAdmission.publicationUnknownPreserves"; attribute :>> producerAnchor="root-scan"; attribute :>> obligationId="Admission-registry"; }
part route8:RouteRow { attribute :>> component="roots"; attribute :>> actionName="guard_thread_admission.queryCommitted"; attribute :>> lemma="GuardAdmission.queryCommittedPreserves"; attribute :>> producerAnchor="root-scan"; attribute :>> obligationId="Admission-registry"; }
part route9:RouteRow { attribute :>> component="roots"; attribute :>> actionName="guard_thread_admission.queryAbsent"; attribute :>> lemma="GuardAdmission.queryAbsentPreserves"; attribute :>> producerAnchor="root-scan"; attribute :>> obligationId="Admission-registry"; }
part route10:RouteRow { attribute :>> component="roots"; attribute :>> actionName="guard_thread_admission.roundAcknowledged"; attribute :>> lemma="GuardAdmission.roundAcknowledgedPreserves"; attribute :>> producerAnchor="root-scan"; attribute :>> obligationId="Admission-registry"; }
part route11:RouteRow { attribute :>> component="roots"; attribute :>> actionName="guard_thread_admission.releaseSourceRoot"; attribute :>> lemma="GuardAdmission.releaseSourceRootPreserves"; attribute :>> producerAnchor="root-scan"; attribute :>> obligationId="Admission-registry"; }
part route12:RouteRow { attribute :>> component="admission"; attribute :>> actionName="guard_thread_admission.bindContext"; attribute :>> lemma="GuardAdmission.bindContextPreserves"; attribute :>> producerAnchor="thread-bind"; attribute :>> obligationId="Admission-TLS"; }
part route13:RouteRow { attribute :>> component="admission"; attribute :>> actionName="guard_thread_admission.bindingUnknown"; attribute :>> lemma="GuardAdmission.bindingUnknownPreserves"; attribute :>> producerAnchor="thread-bind"; attribute :>> obligationId="Admission-TLS"; }
part route14:RouteRow { attribute :>> component="admission"; attribute :>> actionName="guard_thread_admission.enterApplication"; attribute :>> lemma="GuardAdmission.enterApplicationPreserves"; attribute :>> producerAnchor="tcl"; attribute :>> obligationId="Admission-bootstrap"; }
part route15:RouteRow { attribute :>> component="control"; attribute :>> actionName="guard_thread_admission.beginNested"; attribute :>> lemma="GuardAdmission.beginNestedPreserves"; attribute :>> producerAnchor="sfun-marker"; attribute :>> obligationId="Admission-nesting"; }
part route16:RouteRow { attribute :>> component="roots"; attribute :>> actionName="guard_thread_admission.nestedPublish"; attribute :>> lemma="GuardAdmission.nestedPublishPreserves"; attribute :>> producerAnchor="root-scan"; attribute :>> obligationId="Admission-registry"; }
part route17:RouteRow { attribute :>> component="roots"; attribute :>> actionName="guard_thread_admission.nestedRoundAcknowledged"; attribute :>> lemma="GuardAdmission.nestedRoundAcknowledgedPreserves"; attribute :>> producerAnchor="root-scan"; attribute :>> obligationId="Admission-registry"; }
part route18:RouteRow { attribute :>> component="roots"; attribute :>> actionName="guard_thread_admission.nestedPublicationUnknown"; attribute :>> lemma="GuardAdmission.nestedPublicationUnknownPreserves"; attribute :>> producerAnchor="root-scan"; attribute :>> obligationId="Admission-registry"; }
part route19:RouteRow { attribute :>> component="roots"; attribute :>> actionName="guard_thread_admission.queryNestedCommitted"; attribute :>> lemma="GuardAdmission.queryNestedCommittedPreserves"; attribute :>> producerAnchor="root-scan"; attribute :>> obligationId="Admission-registry"; }
part route20:RouteRow { attribute :>> component="control"; attribute :>> actionName="guard_thread_admission.returnNested"; attribute :>> lemma="GuardAdmission.returnNestedPreserves"; attribute :>> producerAnchor="sfun-marker"; attribute :>> obligationId="Admission-nesting"; }
part route21:RouteRow { attribute :>> component="control"; attribute :>> actionName="guard_thread_admission.nestedExitUnknown"; attribute :>> lemma="GuardAdmission.nestedExitUnknownPreserves"; attribute :>> producerAnchor="sfun-marker"; attribute :>> obligationId="Admission-nesting"; }
part route22:RouteRow { attribute :>> component="control"; attribute :>> actionName="guard_thread_admission.armOuterExit"; attribute :>> lemma="GuardAdmission.armOuterExitPreserves"; attribute :>> producerAnchor="restore-root-request"; attribute :>> obligationId="Admission-exit"; }
part route23:RouteRow { attribute :>> component="control"; attribute :>> actionName="guard_thread_admission.armAfterNested"; attribute :>> lemma="GuardAdmission.armAfterNestedPreserves"; attribute :>> producerAnchor="sfun-marker"; attribute :>> obligationId="Admission-nesting"; }
part route24:RouteRow { attribute :>> component="control"; attribute :>> actionName="guard_thread_admission.restoreReturns"; attribute :>> lemma="GuardAdmission.restoreReturnsPreserves"; attribute :>> producerAnchor="restore-root-request"; attribute :>> obligationId="Admission-exit"; }
part route25:RouteRow { attribute :>> component="control"; attribute :>> actionName="guard_thread_admission.restoreDoesNotReturn"; attribute :>> lemma="GuardAdmission.restoreDoesNotReturnPreserves"; attribute :>> producerAnchor="restore-root-request"; attribute :>> obligationId="Admission-exit"; }
part route26:RouteRow { attribute :>> component="control"; attribute :>> actionName="guard_thread_admission.restoreUnknown"; attribute :>> lemma="GuardAdmission.restoreUnknownPreserves"; attribute :>> producerAnchor="restore-root-request"; attribute :>> obligationId="Admission-exit"; }
part route27:RouteRow { attribute :>> component="admission"; attribute :>> actionName="guard_thread_admission.closeAdmission"; attribute :>> lemma="GuardAdmission.closeAdmissionPreserves"; attribute :>> producerAnchor="retire-refusal"; attribute :>> obligationId="Admission-retirement"; }
part route28:RouteRow { attribute :>> component="admission"; attribute :>> actionName="guard_thread_admission.tlsDetachKnown"; attribute :>> lemma="GuardAdmission.tlsDetachKnownPreserves"; attribute :>> producerAnchor="thread-bind"; attribute :>> obligationId="Admission-TLS"; }
part route29:RouteRow { attribute :>> component="admission"; attribute :>> actionName="guard_thread_admission.scanGraceKnown"; attribute :>> lemma="GuardAdmission.scanGraceKnownPreserves"; attribute :>> producerAnchor="retire-refusal"; attribute :>> obligationId="Admission-retirement"; }
part route30:RouteRow { attribute :>> component="admission"; attribute :>> actionName="guard_thread_admission.retireActiveGuard"; attribute :>> lemma="GuardAdmission.retireActiveGuardPreserves"; attribute :>> producerAnchor="retire-refusal"; attribute :>> obligationId="Admission-retirement"; }
part def ProofRow { attribute key:String; attribute lemma:String; }
part proof0:ProofRow { attribute :>> key="all-step"; attribute :>> lemma="GuardAdmission.stepPreserves"; }
part proof1:ProofRow { attribute :>> key="reachable"; attribute :>> lemma="GuardAdmission.reachableSafe"; }
part proof2:ProofRow { attribute :>> key="root-coverage"; attribute :>> lemma="GuardAdmission.guardRootCoverage"; }
part proof3:ProofRow { attribute :>> key="cancel-before-register"; attribute :>> lemma="GuardAdmission.preRegistrationCancellationCustody"; }
part proof4:ProofRow { attribute :>> key="entry-cut"; attribute :>> lemma="GuardAdmission.applicationEntryHasRoots"; }
part proof5:ProofRow { attribute :>> key="no-return"; attribute :>> lemma="GuardAdmission.restorationRetainsOwner"; }
part proof6:ProofRow { attribute :>> key="nested-parent"; attribute :>> lemma="GuardAdmission.nestedParentRetained"; }
part proof7:ProofRow { attribute :>> key="nested-root"; attribute :>> lemma="GuardAdmission.nestedRootCoverage"; }
part proof8:ProofRow { attribute :>> key="restore-inner"; attribute :>> lemma="GuardAdmission.nestedReturnsDisabled"; }
part proof9:ProofRow { attribute :>> key="unknown-publish"; attribute :>> lemma="GuardAdmission.unknownPublicationRetainsSource"; }
part proof10:ProofRow { attribute :>> key="retirement"; attribute :>> lemma="GuardAdmission.retirementCut"; }
part def PaperRow { attribute key:String; attribute title:String; attribute url:String; attribute section:String; attribute basis:String; attribute boundary:String; }
part paper0:PaperRow { attribute :>> key="Gambit-PVM"; attribute :>> title="A Parallel Virtual Machine for Efficient Scheme Compilation"; attribute :>> url="https://www.iro.umontreal.ca/~feeley/papers/FeeleyMillerLFP90.pdf"; attribute :>> section="2"; attribute :>> basis="Gambit primary paper; section reviewed"; attribute :>> boundary="Target call and representation information motivates generated entry contracts; not guard proof"; }
part paper1:PaperRow { attribute :>> key="Gambit-FFI"; attribute :>> title="A Portable Implementation of First-Class Continuations for Unrestricted Interoperability with C in a Multithreaded Scheme"; attribute :>> url="https://www.schemeworkshop.org/2000/feeley.ps"; attribute :>> section="1 3 4 5"; attribute :>> basis="Gambit primary paper; full official PostScript read and hashed"; attribute :>> boundary="Separate existing lazy C-frame treatment proposed native-thread stacks and paper implementation status"; }
part paper2:PaperRow { attribute :>> key="OCaml"; attribute :>> title="OCaml 5.4 C interface"; attribute :>> url="https://ocaml.org/manual/5.4/intfc.html"; attribute :>> section="12.1 12.2"; attribute :>> basis="secondary comparator; official manual reviewed"; attribute :>> boundary="Thread registration and runtime acquire/release are distinct; no source allocation-free claim"; }
part paper3:PaperRow { attribute :>> key="Chez"; attribute :>> title="Chez Scheme 10.3 foreign interface"; attribute :>> url="https://cisco.github.io/ChezScheme/csug10.3.0/foreign.html"; attribute :>> section="4.4 4.9"; attribute :>> basis="secondary comparator; official manual reviewed"; attribute :>> boundary="Activation GC eligibility and stale native return contexts remain separate responsibilities"; }
part paper4:PaperRow { attribute :>> key="Erlang"; attribute :>> title="Erlang erl_nif reference"; attribute :>> url="https://www.erlang.org/doc/apps/erts/erl_nif.html"; attribute :>> section="Dirty NIF ErlNifEnv enif_keep_resource"; attribute :>> basis="secondary comparator; official manual reviewed"; attribute :>> boundary="Process termination does not stop dirty native work; resource references are not Scheme movable roots"; }
part def GroundingRow { attribute component:String; attribute producerAnchor:String; attribute paperKey:String; attribute obligationId:String; }
part grounding0:GroundingRow { attribute :>> component="control"; attribute :>> producerAnchor="paper-fulltext"; attribute :>> paperKey="Gambit-FFI"; attribute :>> obligationId="Admission-nesting"; }
part grounding1:GroundingRow { attribute :>> component="control"; attribute :>> producerAnchor="marker-kill"; attribute :>> paperKey="Gambit-FFI"; attribute :>> obligationId="Admission-exit"; }
part grounding2:GroundingRow { attribute :>> component="admission"; attribute :>> producerAnchor="sfun-emitter"; attribute :>> paperKey="Gambit-PVM"; attribute :>> obligationId="Admission-bootstrap"; }
part grounding3:GroundingRow { attribute :>> component="admission"; attribute :>> producerAnchor="thread-bind"; attribute :>> paperKey="Gambit-FFI"; attribute :>> obligationId="Admission-TLS"; }
part grounding4:GroundingRow { attribute :>> component="roots"; attribute :>> producerAnchor="root-scan"; attribute :>> paperKey="Gambit-FFI"; attribute :>> obligationId="Admission-registry"; }
part def GainRow { attribute key:String; attribute avoided:String; attribute added:String; attribute condition:String; }
part gain0:GainRow { attribute :>> key="source ownership"; attribute :>> avoided="0 guard ownership transfers before successful mask confirmation"; attribute :>> added="preissued offer root and native descriptor remain source-owned"; attribute :>> condition="source producer already retained responsibility; not a free first pin"; }
part gain1:GainRow { attribute :>> key="root handoff"; attribute :>> avoided="0 intervals without an abstract source or target root in finite model"; attribute :>> added="overlap of 2 root authorities until round acknowledgment"; attribute :>> condition="actual root slots and collector membership must refine abstract bits"; }
part gain2:GainRow { attribute :>> key="warm registration"; attribute :>> avoided="0 allocator calls allowed inside guard registration by contract"; attribute :>> added="bounded preallocated slots carrier and result capacity; no native nonallocation receipt"; attribute :>> condition="cold thread and TLS bootstrap excluded; selected library internals must be qualified"; }
part gain3:GainRow { attribute :>> key="nested masks"; attribute :>> avoided="inner known exit restores DISABLE in this modeled nesting profile"; attribute :>> added="separate child guard root acknowledgment and saved-state stack"; attribute :>> condition="one nested activation under disabled outer; arbitrary state stack still unproved"; }
part gain4:GainRow { attribute :>> key="nonreturn restoration"; attribute :>> avoided="known root debt retains stable completion owner"; attribute :>> added="unknown outcome consumes capacity until settled"; attribute :>> condition="no metadata recovery action depends on restore returning"; }
part gain5:GainRow { attribute :>> key="C portability"; attribute :>> avoided="1 generated native entry contract can serve all declared C23 FFI profiles"; attribute :>> added="generator metadata ABI and checked TLS/context adapters"; attribute :>> condition="current wrappers migrate fully; preserve native return domains and Scheme continuation semantics"; }
part gain6:GainRow { attribute :>> key="paper amplification"; attribute :>> avoided="Separate execution context native return domain guard and collector roles"; attribute :>> added="native segment lifetime and scheduling require independent design"; attribute :>> condition="SFP2000 C-thread proposal not implemented by these guard models"; }
part gain7:GainRow { attribute :>> key="retirement"; attribute :>> avoided="0 native paths retired and no measured CPU speedup"; attribute :>> added="registration masking root overlap queries and grace costs"; attribute :>> condition="avoidance of unsafe/repeated work must exceed new costs; Zig advantage unestablished"; }
part def MemoryRow { attribute key:String; attribute publication:String; attribute observation:String; attribute obligation:String; }
part memory0:MemoryRow { attribute :>> key="offer"; attribute :>> publication="source publishes immutable generation-bearing descriptor"; attribute :>> observation="recipient acquires only after mask and control-domain lookup"; attribute :>> obligation="raw ClientData pointer is not safe lifetime authority"; }
part memory1:MemoryRow { attribute :>> key="registry"; attribute :>> publication="initialize entry before release-publishing active generation"; attribute :>> observation="root owner acquires and acknowledges collector-visible slot"; attribute :>> obligation="publication does not itself add a root to an already frozen GC roster"; }
part memory2:MemoryRow { attribute :>> key="root-transfer"; attribute :>> publication="keep source until target round acknowledgment known"; attribute :>> observation="release source only after same operation receipt"; attribute :>> obligation="unknown publication preserves source and prevents slot reuse"; }
part memory3:MemoryRow { attribute :>> key="TLS"; attribute :>> publication="publish exact leased context through qualified backend"; attribute :>> observation="checked readback or provider receipt before marker allocation"; attribute :>> obligation="selected pthread_setspecific fallback currently ignores error; affinity helper not leaf"; }
part memory4:MemoryRow { attribute :>> key="restore"; attribute :>> publication="commit supervisor custody before cancellation restore"; attribute :>> observation="owner can recover record without abandoned thread-local variables"; attribute :>> obligation="restore no-return and restore unknown keep roots and slot generation"; }
part memory5:MemoryRow { attribute :>> key="retirement"; attribute :>> publication="close entry and detach TLS before scanner grace"; attribute :>> observation="only known closure permits retiring active root binding"; attribute :>> obligation="record replay authority and native stack return rights have separate lifetimes"; }
part def ContractRow { attribute fromNode:String; attribute toNode:String; attribute custody:String; }
part contract0:ContractRow { attribute :>> fromNode="GambitPaper"; attribute :>> toNode="EntrySpec"; attribute :>> custody="PVM calling contract plus separate Scheme and native return lifetimes"; }
part contract1:ContractRow { attribute :>> fromNode="SourceOwner"; attribute :>> toNode="IngressOffer"; attribute :>> custody="preissued stable descriptor and source roots; recipient owns nothing yet"; }
part contract2:ContractRow { attribute :>> fromNode="IngressOffer"; attribute :>> toNode="MaskConfirmed"; attribute :>> custody="cancellation before confirmation leaves source responsibility intact"; }
part contract3:ContractRow { attribute :>> fromNode="MaskConfirmed"; attribute :>> toNode="GuardReserved"; attribute :>> custody="claim preallocated capacity; no callback allocation or implicit thread bootstrap"; }
part contract4:ContractRow { attribute :>> fromNode="GuardReserved"; attribute :>> toNode="RootRegistry"; attribute :>> custody="publish with source roots retained until same-round acknowledgment"; }
part contract5:ContractRow { attribute :>> fromNode="RootRegistry"; attribute :>> toNode="ContextLease"; attribute :>> custody="known root coverage before checked VM context and TLS binding"; }
part contract6:ContractRow { attribute :>> fromNode="ContextLease"; attribute :>> toNode="SchemeEntry"; attribute :>> custody="only now may generated SFUN allocate marker and invoke Scheme"; }
part contract7:ContractRow { attribute :>> fromNode="SchemeEntry"; attribute :>> toNode="NestedEntry"; attribute :>> custody="distinct guard; outer root retained and inner saved mask is DISABLE"; }
part contract8:ContractRow { attribute :>> fromNode="NestedEntry"; attribute :>> toNode="StableExitOwner"; attribute :>> custody="resolve child before outer completion; unknown child retains both"; }
part contract9:ContractRow { attribute :>> fromNode="SchemeEntry"; attribute :>> toNode="StableExitOwner"; attribute :>> custody="stable supervisor owns roots TLS and return-domain debt before restore"; }
part contract10:ContractRow { attribute :>> fromNode="StableExitOwner"; attribute :>> toNode="Restoration"; attribute :>> custody="restore may fail or never return; custody already stable"; }
part contract11:ContractRow { attribute :>> fromNode="Restoration"; attribute :>> toNode="Retirement"; attribute :>> custody="known return then admission closure TLS detach and scan grace"; }
part contract12:ContractRow { attribute :>> fromNode="Restoration"; attribute :>> toNode="Quarantine"; attribute :>> custody="nonreturn or unknown restoration retains root and metadata; no automatic replay"; }
part contract13:ContractRow { attribute :>> fromNode="EntrySpec"; attribute :>> toNode="GuardReserved"; attribute :>> custody="Generate checked enrollment before PSTATE lookup or marker allocation"; }
part contract14:ContractRow { attribute :>> fromNode="GambitPaper"; attribute :>> toNode="NativeReturnDomain"; attribute :>> custody="Native frame lifetime remains separate; stack-segment design is open"; }
part contract15:ContractRow { attribute :>> fromNode="NativeReturnDomain"; attribute :>> toNode="StableExitOwner"; attribute :>> custody="Proposed native return-domain hold; qualification remains open"; }
}
