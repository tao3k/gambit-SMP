package GambitRegistrySlotIssuance { private import ScalarValues::*;
part def Owner { attribute componentId:String; }
part storageOwner:Owner { attribute :>> componentId="storage"; }
part registryOwner:Owner { attribute :>> componentId="registry"; }
part writerOwner:Owner { attribute :>> componentId="writer"; }
part leaseOwner:Owner { attribute :>> componentId="lease"; }
part generationOwner:Owner { attribute :>> componentId="generation"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-register"; attribute :>> path="vendor/gambit/lib/_mem/rc-allocation.inc"; attribute :>> needle="tail->next = h;"; attribute :>> obligation="Plain list insertion requires owner and collector exclusion"; }
part source4:SourceRow { attribute :>> key="rc-free"; attribute :>> path="vendor/gambit/lib/_mem/rc-allocation.inc"; attribute :>> needle="if (--h->refcount == 0)"; attribute :>> obligation="Nonatomic decrement and unlink are not safe arbitrary-thread admission"; }
part source5:SourceRow { attribute :>> key="rc-read"; attribute :>> path="vendor/gambit/lib/_mem/rc-allocation.inc"; attribute :>> needle="return h->data;"; attribute :>> obligation="Raw native copy is not a registered update slot"; }
part source6:SourceRow { attribute :>> key="rc-write"; attribute :>> path="vendor/gambit/lib/_mem/rc-allocation.inc"; attribute :>> needle="h->data = val;"; attribute :>> obligation="All semantic writers must join freeze/generation protocol or deny admission"; }
part source7:SourceRow { attribute :>> key="rc-cleanup"; attribute :>> path="vendor/gambit/lib/_mem/rc-allocation.inc"; attribute :>> needle="___HIDDEN void cleanup_rc"; attribute :>> obligation="Bulk cleanup frees chain independent of per-entry leases"; }
part source8:SourceRow { attribute :>> key="rc-scan"; attribute :>> path="vendor/gambit/lib/_mem/rc-roots.inc"; attribute :>> needle="mark_array (work, &h->data, 1);"; attribute :>> obligation="Actual GC slot update; target private carrier is not implicitly scanned"; }
part source9:SourceRow { attribute :>> key="retire-refuse"; attribute :>> path="vendor/gambit/lib/_mem/capacity-resize.inc"; attribute :>> needle="return 0; /* no freeze receipt for external RC/native borrowers */"; attribute :>> obligation="Current processor retirement refuses nonempty RC rather than manufacturing a lease"; }
part source10:SourceRow { attribute :>> key="pstate-cleanup"; attribute :>> path="vendor/gambit/lib/_mem/memory-lifecycle.inc"; attribute :>> needle="free_still_objs (___ps);"; attribute :>> obligation="cleanup_mem_pstate frees still storage before cleanup_rc; not an active-lease release helper"; }
part source11:SourceRow { attribute :>> key="setter-export"; attribute :>> path="vendor/gambit/lib/setup.c"; attribute :>> needle="= ___set_data_rc;"; attribute :>> obligation="Public GSTATE function pointer permits indirect/out-of-tree callers; lexical sites do not close writer authority"; }
part source12:SourceRow { attribute :>> key="register-export"; attribute :>> path="vendor/gambit/lib/setup.c"; attribute :>> needle="= ___register_rc;"; attribute :>> obligation="Public registration ABI is not a stable VM SourceOwner registry"; }
part source13:SourceRow { attribute :>> key="closure-writer"; attribute :>> path="vendor/gambit/lib/os_dyn.c"; attribute :>> needle="___set_data_rc (c_closure, proc);"; attribute :>> obligation="Concrete semantic payload installer, architecture conditional"; }
part source14:SourceRow { attribute :>> key="epoch-limit"; attribute :>> path="vendor/gambit/lib/_mem/heap-sections.inc"; attribute :>> needle="if (___vms->gc_round.epoch >= ___MAX_FIX)"; attribute :>> obligation="Existing round identity refuses exhaustion; no unchecked wrapping receipt"; }
part source15:SourceRow { attribute :>> key="epoch-new"; attribute :>> path="vendor/gambit/lib/_mem/heap-sections.inc"; attribute :>> needle="___vms->gc_round.epoch++;"; attribute :>> obligation="Round number created at setup, distinct from semantic payload generation"; }
part source16:SourceRow { attribute :>> key="origin-publish"; attribute :>> path="vendor/gambit/lib/_mem/heap-sections.inc"; attribute :>> needle="!___gc_root_task_publish(&___vms->gc_root_tasks[i],"; attribute :>> obligation="Publish follows frozen origin; not generic new-source enrollment"; }
part source17:SourceRow { attribute :>> key="origin-claim"; attribute :>> path="vendor/gambit/lib/_mem/collection-round.inc"; attribute :>> needle="if (___gc_root_task_claim(task,___vms->gc_round.epoch,owner))"; attribute :>> obligation="Actual claim checks current round and worker owner"; }
part source18:SourceRow { attribute :>> key="origin-finish"; attribute :>> path="vendor/gambit/lib/_mem/collection-round.inc"; attribute :>> needle="if (!___gc_root_task_finish(task,___vms->gc_round.epoch,owner))"; attribute :>> obligation="Task finish has exact owner and epoch boundary"; }
part source19:SourceRow { attribute :>> key="origin-thaw"; attribute :>> path="vendor/gambit/lib/_mem/collection-round.inc"; attribute :>> needle="if (!___gc_origin_thaw(&___vms->gc_root_tasks[id],___vms->gc_round.epoch))"; attribute :>> obligation="Resume requires completed origin; not a payload-version receipt"; }
part source20:SourceRow { attribute :>> key="view-drain"; attribute :>> path="vendor/gambit/lib/_mem/collection-round.inc"; attribute :>> needle="BARRIER(); /* no worker may retain a stopped root view past this cut */"; attribute :>> obligation="Root view grace cut precedes ordinary execution"; }
part source21:SourceRow { attribute :>> key="shrink-cleanup"; attribute :>> path="vendor/gambit/lib/setup.c"; attribute :>> needle="___transfer_retired_still (ps, ___ps);"; attribute :>> obligation="Shrink known join transfers still before cleanup; does not qualify arbitrary native roots"; }
part source22:SourceRow { attribute :>> key="vm-root-retained"; attribute :>> path="vendor/gambit/lib/setup.c"; attribute :>> needle="return; /* do not erase retained source roots through repeated setup */"; attribute :>> obligation="Whole VM cleanup checks resize source requests; generic SourceRegistry not covered"; }
part source23:SourceRow { attribute :>> key="vm-request-slots"; attribute :>> path="vendor/gambit/lib/_mem/root-origins.inc"; attribute :>> needle="&___vms->resize_requests[i].thunk"; attribute :>> obligation="All VM request slots scanned independently of participant membership; precedent not generic registry"; }
part source24:SourceRow { attribute :>> key="context-rc-roots"; attribute :>> path="vendor/gambit/lib/_mem/root-origins.inc"; attribute :>> needle="mark_rc (work, context);"; attribute :>> obligation="RC roots reached through frozen execution origin"; }
part source25:SourceRow { attribute :>> key="context-startup"; attribute :>> path="vendor/gambit/lib/_mem/root-origins.inc"; attribute :>> needle="&context->startup_thunk"; attribute :>> obligation="Startup root remains a stable update slot"; }
part source26:SourceRow { attribute :>> key="root-hook"; attribute :>> path="vendor/gambit/lib/_mem/root-origins.inc"; attribute :>> needle="___GC_ROOT_CONTROL(work);"; attribute :>> obligation="Default hook has no storage or code; not proof of generic carrier coverage"; }
part source27:SourceRow { attribute :>> key="origin-layout"; attribute :>> path="vendor/gambit/include/_gambit/runtime_roles.h.in"; attribute :>> needle="typedef struct ___gc_root_origin_struct"; attribute :>> obligation="Stable context identity and pinned origin storage, not an arbitrary host lease"; }
part source28:SourceRow { attribute :>> key="task-layout"; attribute :>> path="vendor/gambit/include/_gambit/runtime_roles.h.in"; attribute :>> needle="typedef struct ___gc_root_task_struct"; attribute :>> obligation="Task contains origin pointer, incarnation, epoch, claim state"; }
part source29:SourceRow { attribute :>> key="origin-freeze-body"; attribute :>> path="vendor/gambit/include/_gambit/vm_state.h.in"; attribute :>> needle="___STARTUP_INLINE int ___gc_origin_freeze"; attribute :>> obligation="Real publisher requires physical root-writer stop and exclusive round admission"; }
part source30:SourceRow { attribute :>> key="task-publish-body"; attribute :>> path="vendor/gambit/include/_gambit/vm_state.h.in"; attribute :>> needle="t->origin = o; t->incarnation = o->incarnation; t->epoch = epoch;"; attribute :>> obligation="Descriptor publication assumes exclusive slot reuse and drained prior readers"; }
part source31:SourceRow { attribute :>> key="task-claim-body"; attribute :>> path="vendor/gambit/include/_gambit/vm_state.h.in"; attribute :>> needle="t->incarnation != t->origin->incarnation"; attribute :>> obligation="Claim dereferences descriptor/origin before CAS; not a safe retain of freed storage"; }
part source32:SourceRow { attribute :>> key="task-finish-body"; attribute :>> path="vendor/gambit/include/_gambit/vm_state.h.in"; attribute :>> needle="___gc_cas(&t->claim,owner,2) == owner"; attribute :>> obligation="Exact owner completion within a stable pinned round"; }
part source33:SourceRow { attribute :>> key="origin-thaw-body"; attribute :>> path="vendor/gambit/include/_gambit/vm_state.h.in"; attribute :>> needle="___gc_atomic_load(&t->claim) == 2"; attribute :>> obligation="Completion does not itself supply whole-round resume permission"; }
part source34:SourceRow { attribute :>> key="vm-root-layout"; attribute :>> path="vendor/gambit/include/_gambit/vm_state.h.in"; attribute :>> needle="___gc_root_task gc_root_tasks[___MAX_PROCESSORS];"; attribute :>> obligation="VM allocation stores task descriptors; current task census is processor origins"; }
part source35:SourceRow { attribute :>> key="incarnation-issuer"; attribute :>> path="vendor/gambit/lib/setup.c"; attribute :>> needle="___vms->gc_origins[i].incarnation++;"; attribute :>> obligation="Real context incarnation signer after finite exhaustion check"; }
part source36:SourceRow { attribute :>> key="cas-wrapper"; attribute :>> path="vendor/gambit/include/_gambit/vm_state.h.in"; attribute :>> needle="return ___COMPARE_AND_SWAP_WORD(p,old_value,new_value);"; attribute :>> obligation="Platform-selecting CAS is not an explicit C23 atomic ABI"; }
part source37:SourceRow { attribute :>> key="cas-sync-builtins"; attribute :>> path="vendor/gambit/include/_gambit/activity_log.h.in"; attribute :>> needle="__sync_val_compare_and_swap(p,oldval,newval)"; attribute :>> obligation="One alternative implementation; effective Darwin selection remains open"; }
part source38:SourceRow { attribute :>> key="slot-read"; attribute :>> path="vendor/gambit/lib/_mem/copy-reservations.inc"; attribute :>> needle="___WORD obj = *cell;"; attribute :>> obligation="Ordinary root-slot load requires writer and duplicate-scanner exclusion"; }
part source39:SourceRow { attribute :>> key="copy-loser-slot-write"; attribute :>> path="vendor/gambit/lib/_mem/copy-reservations.inc"; attribute :>> needle="*cell = ___TAG(___UNTAG_AS(head_now, ___FORW), ___TYP(obj));"; attribute :>> obligation="Forwarding loser still writes the root slot"; }
part source40:SourceRow { attribute :>> key="copy-winner-slot-write"; attribute :>> path="vendor/gambit/lib/_mem/copy-reservations.inc"; attribute :>> needle="*cell = ___TAG(alloc - ___REFERENCE_TO_BODY, ___TYP(obj));"; attribute :>> obligation="Forwarding winner writes the root slot before copying all payload"; }
part source41:SourceRow { attribute :>> key="already-forwarded-slot-write"; attribute :>> path="vendor/gambit/lib/_mem/copy-reservations.inc"; attribute :>> needle="*cell = ___TAG(___UNTAG_AS(head, ___FORW), ___TYP(obj));"; attribute :>> obligation="Same object in two cells still needs both cell updates"; }
part source42:SourceRow { attribute :>> key="default-root-hook"; attribute :>> path="vendor/gambit/lib/_mem/copy-reservations.inc"; attribute :>> needle="#define ___GC_ROOT_CONTROL(work) ((void)0)"; attribute :>> obligation="No general VM carrier registry consumer is supplied by this hook"; }
part source43:SourceRow { attribute :>> key="umbrella"; attribute :>> path="vendor/gambit/include/gambit.h.in"; attribute :>> needle="#include \"_gambit/memory_state.h.in\""; attribute :>> obligation="Bind modular umbrella and layout producer"; }
part source44:SourceRow { attribute :>> key="header-config"; attribute :>> path="vendor/gambit/include/makefile.in"; attribute :>> needle="HEADER_CONFIG ="; attribute :>> obligation="Ordered configured header composition; generated artifact provenance open"; }
part source45:SourceRow { attribute :>> key="header-target"; attribute :>> path="vendor/gambit/include/makefile.in"; attribute :>> needle="gambit.h: gambit.h.in $(HEADER_TEMPLATES)"; attribute :>> obligation="All template inputs matter; do not run configuration"; }
part source46:SourceRow { attribute :>> key="mem-order"; attribute :>> path="vendor/gambit/lib/mem.c"; attribute :>> needle="#include \"_mem/rc-allocation.inc\""; attribute :>> obligation="Bind new implementation inclusion path/order"; }
part source47:SourceRow { attribute :>> key="rc-layout"; attribute :>> path="vendor/gambit/include/_gambit/memory_state.h.in"; attribute :>> needle="typedef struct ___rc_header_struct"; attribute :>> obligation="Links/refcount/data do not contain VM storage identity or extent"; }
part source48:SourceRow { attribute :>> key="root-field"; attribute :>> path="vendor/gambit/include/_gambit/memory_state.h.in"; attribute :>> needle="___SCMOBJ data; /* needed for C closures */"; attribute :>> obligation="Root coordinate comes from schema field, not payload address"; }
part source49:SourceRow { attribute :>> key="rc-allocation"; attribute :>> path="vendor/gambit/lib/_mem/rc-allocation.inc"; attribute :>> needle="___ALLOC_MEM(bytes + sizeof (___rc_header))"; attribute :>> obligation="Allocation lacks durable identity and checked-extent receipt"; }
part source50:SourceRow { attribute :>> key="rc-address"; attribute :>> path="vendor/gambit/lib/_mem/rc-allocation.inc"; attribute :>> needle="return ___CAST(void*,h+1);"; attribute :>> obligation="Native payload address is not root-cell address"; }
part source51:SourceRow { attribute :>> key="allocator-export"; attribute :>> path="vendor/gambit/lib/setup.c"; attribute :>> needle="= ___alloc_rc_no_register;"; attribute :>> obligation="Indirect allocation authority remains public"; }
part source52:SourceRow { attribute :>> key="public-register"; attribute :>> path="vendor/gambit/include/_gambit/runtime_protocols.h.in"; attribute :>> needle="___IMP_FUNC(void*,___register_rc)"; attribute :>> obligation="Public declaration and implementation spelling require effective ABI qualification"; }
part source53:SourceRow { attribute :>> key="tcl-allocation"; attribute :>> path="vendor/gambit/examples/tcltk/tcltk.scm"; attribute :>> needle="void *cd = ___EXT(___alloc_rc) (0);"; attribute :>> obligation="Zero payload allocation still owns a root-bearing header"; }
part source54:SourceRow { attribute :>> key="string-resource"; attribute :>> path="vendor/gambit/lib/c_intf.c"; attribute :>> needle="___EXP_FUNC(void,___release_string)"; attribute :>> obligation="Native strings share RC allocator; classify Scheme payload separately"; }
part source55:SourceRow { attribute :>> key="os-resource"; attribute :>> path="vendor/gambit/lib/os_io.c"; attribute :>> needle="void *ev = ___alloc_rc"; attribute :>> obligation="OS resource user is not implicitly a Scheme root source"; }
part source56:SourceRow { attribute :>> key="file-resource"; attribute :>> path="vendor/gambit/lib/os_files.c"; attribute :>> needle="___alloc_rc (___PSA(___PSTATE)"; attribute :>> obligation="Directory/native resource ownership survives allocator redesign"; }
part def ModuleRow { attribute key:String; attribute path:String; attribute responsibility:String; attribute modelOwner:String; }
part module0:ModuleRow { attribute :>> key="layout"; attribute :>> path="vendor/gambit/include/_gambit/memory_state.h.in"; attribute :>> responsibility="RC header, field coordinates, context memory"; attribute :>> modelOwner="storage"; }
part module1:ModuleRow { attribute :>> key="roles"; attribute :>> path="vendor/gambit/include/_gambit/runtime_roles.h.in"; attribute :>> responsibility="Execution/root/task/worker types"; attribute :>> modelOwner="registry"; }
part module2:ModuleRow { attribute :>> key="protocol"; attribute :>> path="vendor/gambit/include/_gambit/vm_state.h.in"; attribute :>> responsibility="VM root arrays and origin/round publication"; attribute :>> modelOwner="registry"; }
part module3:ModuleRow { attribute :>> key="sync-current"; attribute :>> path="vendor/gambit/include/_gambit/activity_log.h.in"; attribute :>> responsibility="Current CAS alternatives are here; filename is not a semantic boundary"; attribute :>> modelOwner="generation"; }
part module4:ModuleRow { attribute :>> key="exports"; attribute :>> path="vendor/gambit/include/_gambit/global_state.h.in"; attribute :>> responsibility="Indirect native function table"; attribute :>> modelOwner="writer"; }
part module5:ModuleRow { attribute :>> key="declarations"; attribute :>> path="vendor/gambit/include/_gambit/runtime_protocols.h.in"; attribute :>> responsibility="Public native ABI declarations"; attribute :>> modelOwner="registry"; }
part module6:ModuleRow { attribute :>> key="allocator"; attribute :>> path="vendor/gambit/lib/_mem/rc-allocation.inc"; attribute :>> responsibility="Allocate, register, set, retain and free"; attribute :>> modelOwner="storage"; }
part module7:ModuleRow { attribute :>> key="cleanup"; attribute :>> path="vendor/gambit/lib/_mem/memory-lifecycle.inc"; attribute :>> responsibility="Still/RC destructive cleanup ordering"; attribute :>> modelOwner="storage"; }
part def IdentityRow { attribute key:String; attribute structure:String; attribute rule:String; attribute caveat:String; }
part identity0:IdentityRow { attribute :>> key="allocation"; attribute :>> structure="VM + StorageId + generation + checked extent"; attribute :>> rule="Allocator owner publishes identity before any derived keys"; attribute :>> caveat="Raw address and refcount cannot issue ownership"; }
part identity1:IdentityRow { attribute :>> key="view"; attribute :>> structure="Parent StorageId/generation + offset/count + provenance"; attribute :>> rule="Known contained view shares parent identity"; attribute :>> caveat="Containment without provenance is insufficient"; }
part identity2:IdentityRow { attribute :>> key="slot"; attribute :>> structure="Allocation key + schema word offset"; attribute :>> rule="Physical aliases receive one canonical key"; attribute :>> caveat="Native pointer/key adequacy, process/VM ownership and concurrent overlap completeness open"; }
part identity3:IdentityRow { attribute :>> key="registry"; attribute :>> structure="EntryId + entry generation + immutable SlotUseSpec"; attribute :>> rule="Publish roots, owners and metadata together"; attribute :>> caveat="Arbitrary idempotency ledger and entry reuse not modeled"; }
part identity4:IdentityRow { attribute :>> key="payload"; attribute :>> structure="Semantic binding generation, separate from storage/GC"; attribute :>> rule="Alias freezes source; independent copy preserves old binding"; attribute :>> caveat="GC relocation is not semantic setter execution"; }
part identity5:IdentityRow { attribute :>> key="lease"; attribute :>> structure="SourceId/generation + LeaseId + binding policy"; attribute :>> rule="Exact old lease completion releases writer exclusion"; attribute :>> caveat="Fixed model identities do not prove arbitrary concurrent lease accounting"; }
part def IssuerRow { attribute key:String; attribute proposedIssuer:String; attribute actualSource:String; attribute status:String; attribute responsibility:String; }
part issuer0:IssuerRow { attribute :>> key="storage"; attribute :>> proposedIssuer="VM allocator/storage owner"; attribute :>> actualSource="alloc_rc_no_register and RC header layout"; attribute :>> status="No canonical VM StorageId issuer found"; attribute :>> responsibility="Issue extent/provenance and reject contradictory live overlaps"; }
part issuer1:IssuerRow { attribute :>> key="registry"; attribute :>> proposedIssuer="VM registry commit owner"; attribute :>> actualSource="Context register_rc and fixed resize request roots"; attribute :>> status="No generic VM root registry signer found"; attribute :>> responsibility="Commit complete rooted bundle and same-identity result record"; }
part issuer2:IssuerRow { attribute :>> key="view"; attribute :>> proposedIssuer="Storage provenance owner and schema generator"; attribute :>> actualSource="RC data field and fixed context array layouts"; attribute :>> status="Subview certificate absent"; attribute :>> responsibility="Check extent arithmetic alignment policy and parent generation"; }
part issuer3:IssuerRow { attribute :>> key="generation"; attribute :>> proposedIssuer="Stable storage index retirement owner"; attribute :>> actualSource="setup_pstate incarnation and collector epoch have exhaustion checks"; attribute :>> status="Existing counters belong to other identity domains"; attribute :>> responsibility="Drain old accepted users then strictly advance; never wrap"; }
part issuer4:IssuerRow { attribute :>> key="writer"; attribute :>> proposedIssuer="Managed source setter owner"; attribute :>> actualSource="Tcl/C closure installs and GSTATE setter export"; attribute :>> status="Complete writer authority unclosed"; attribute :>> responsibility="Serialize all semantic writes against alias/source leases"; }
part issuer5:IssuerRow { attribute :>> key="release"; attribute :>> proposedIssuer="Source lease completion plus root/grace owners"; attribute :>> actualSource="Current native callers have no generic alias lease receipt"; attribute :>> status="Native signer absent"; attribute :>> responsibility="Copy needs known persistent root; alias needs final user and scan drain"; }
part issuer6:IssuerRow { attribute :>> key="cleanup"; attribute :>> proposedIssuer="Root-cell arena and foreign-resource owners"; attribute :>> actualSource="Still transfer plus free_still_objs then cleanup_rc"; attribute :>> status="Whole-registry settlement absent"; attribute :>> responsibility="Separate header root-cell ownership from Scheme payload backing/code/context"; }
part def ClaimRow { attribute key:String; attribute mechanism:String; attribute condition:String; attribute result:String; attribute gap:String; }
part claim0:ClaimRow { attribute :>> key="overlap"; attribute :>> mechanism="Known subviews normalize; unowned overlap rejects"; attribute :>> condition="Complete live/pending/retained allocation authority and proven parent provenance"; attribute :>> result="No second storage identity for same cell"; attribute :>> gap="Finite interval examples do not prove native allocator census"; }
part claim1:ClaimRow { attribute :>> key="generation"; attribute :>> mechanism="Close/drain before strict generation advance"; attribute :>> condition="Checked representation; no accepted old user or scan"; attribute :>> result="Saved old key cannot match reused record"; attribute :>> gap="Two modeled incarnations; native ABA/index proof open"; }
part claim2:ClaimRow { attribute :>> key="alias-lease"; attribute :>> mechanism="Freeze semantic source binding through alias lifetime"; attribute :>> condition="Every setter mediated; lookups users scans settled"; attribute :>> result="Bound payload equals source while alias remains"; attribute :>> gap="Actual FFI and writer closure missing"; }
part claim3:ClaimRow { attribute :>> key="copy-lease"; attribute :>> mechanism="Keep source until independent registered root is known"; attribute :>> condition="Private rooting and every-GC coverage plus backing ownership"; attribute :>> result="Source may change while old copy stays bound"; attribute :>> gap="Native initialization/root/payload product open"; }
part claim4:ClaimRow { attribute :>> key="unknown"; attribute :>> mechanism="Unknown publication blocks lease return and retirement"; attribute :>> condition="Exact keyed query and stable owner can settle"; attribute :>> result="No timeout inferred release"; attribute :>> gap="No liveness or bounded-retention proof"; }
part claim5:ClaimRow { attribute :>> key="modularity"; attribute :>> mechanism="Bind current header and memory fragments"; attribute :>> condition="Include order and configured header inputs are hashed"; attribute :>> result="Evidence follows actual module locations"; attribute :>> gap="Lexical graph is not preprocessing or native ABI proof"; }
part def MemoryRow { attribute key:String; attribute publication:String; attribute observation:String; attribute obligation:String; attribute overhead:String; }
part memory0:MemoryRow { attribute :>> key="allocate"; attribute :>> publication="Publish initialized storage record"; attribute :>> observation="Acquire before SlotKey validation"; attribute :>> obligation="Pin actual block; check byte extent and complete overlap domain"; attribute :>> overhead="Extent index and allocation record"; }
part memory1:MemoryRow { attribute :>> key="commit"; attribute :>> publication="Publish rooted metadata and owners together"; attribute :>> observation="Acquire immutable complete bundle"; attribute :>> obligation="No root/metadata split; lost ack retains source"; attribute :>> overhead="Commit record and query path"; }
part memory2:MemoryRow { attribute :>> key="write"; attribute :>> publication="Setter checks exact source generation and lease"; attribute :>> observation="Collector updates relocation under root protocol"; attribute :>> obligation="Atomic metadata alone cannot legalize unmediated root writes"; attribute :>> overhead="Writer gate plus rooted candidate"; }
part memory3:MemoryRow { attribute :>> key="close"; attribute :>> publication="Close admission atomically with accepted-user accounting"; attribute :>> observation="Acquire all last-use completions before reclaim"; attribute :>> obligation="No separate zero-count snapshot as quiescence evidence"; attribute :>> overhead="Tombstone and grace retention"; }
part memory4:MemoryRow { attribute :>> key="return"; attribute :>> publication="Copy observes known target; alias observes final drain"; attribute :>> observation="Only old LeaseId completion may settle old writer exclusion"; attribute :>> obligation="Continuation replay cannot release a later lease"; attribute :>> overhead="Stable completion record"; }
part memory5:MemoryRow { attribute :>> key="reuse"; attribute :>> publication="Reclaim then publish strictly newer generation"; attribute :>> observation="Reject stale handle through stable index before dereference"; attribute :>> obligation="No wrap; exhaustion refuses reuse"; attribute :>> overhead="Checked counters and retained unknown outcomes"; }
part def GainRow { attribute key:String; attribute avoided:String; attribute added:String; attribute condition:String; }
part gain0:GainRow { attribute :>> key="canonical"; attribute :>> avoided="Duplicate allocation identities/root work"; attribute :>> added="Authoritative extent/provenance index"; attribute :>> condition="All allocator and FFI imports mediated"; }
part gain1:GainRow { attribute :>> key="alias"; attribute :>> avoided="Target root copy allocation and scan"; attribute :>> added="Source write stall, header/arena retention"; attribute :>> condition="Immutable source binding appropriate for alias lifetime"; }
part gain2:GainRow { attribute :>> key="copy"; attribute :>> avoided="Source lifecycle/write coupling after known transfer"; attribute :>> added="Independent root cell and per-GC scan; backing settlement"; attribute :>> condition="Actual target every-round coverage; payload arena separate"; }
part gain3:GainRow { attribute :>> key="reuse"; attribute :>> avoided="Whole-context retention due solely to local metadata"; attribute :>> added="Storage generations, exact drain and stable index"; attribute :>> condition="Other context/arena/code/native users independently settled"; }
part gain4:GainRow { attribute :>> key="language"; attribute :>> avoided="Shared generated C23 root/layout/FFI contract"; attribute :>> added="Storage and GC protocols remain necessary in C and Zig"; attribute :>> condition="Extra Zig return requires actual support retirement; not established"; }
part def CostRow { attribute key:String; attribute avoided:String; attribute added:String; attribute positiveCondition:String; attribute boundary:String; }
part cost0:CostRow { attribute :>> key="index"; attribute :>> avoided="K*(M-S)*visit_cost plus duplicate identity work"; attribute :>> added="validate + normalize + pin + grace"; attribute :>> positiveCondition="avoided > added"; attribute :>> boundary="No measured duplicate rate; required S slot updates remain"; }
part cost1:CostRow { attribute :>> key="alias"; attribute :>> avoided="One target slot plus K scans"; attribute :>> added="source_write_stall + retained_header + retained_arena + unknowns"; attribute :>> positiveCondition="saved target cost > source coupling"; attribute :>> boundary="Zero-copy can be negative or indefinitely stall a setter"; }
part cost2:CostRow { attribute :>> key="copy"; attribute :>> avoided="Source-write stalls and source-header/context retention"; attribute :>> added="target_slot + K scans + backing transfer + grace"; attribute :>> positiveCondition="coupling removed > independent ownership work"; attribute :>> boundary="Root copy alone does not authorize still/foreign cleanup"; }
part cost3:CostRow { attribute :>> key="generation"; attribute :>> avoided="Accidental aliasing/ABA and lifetime rediscovery"; attribute :>> added="generation index + tombstones + reuse delay"; attribute :>> positiveCondition="native acceptance and all old-user drains proved"; attribute :>> boundary="No native retirement or performance percentage"; }
part def ContractRow { attribute fromNode:String; attribute toNode:String; attribute custody:String; }
part contract0:ContractRow { attribute :>> fromNode="AllocatorOwner"; attribute :>> toNode="StorageRecord"; attribute :>> custody="Checked VM identity and extent"; }
part contract1:ContractRow { attribute :>> fromNode="StorageRecord"; attribute :>> toNode="SubviewCertificate"; attribute :>> custody="Proven parent and containment"; }
part contract2:ContractRow { attribute :>> fromNode="UnknownOverlap"; attribute :>> toNode="RefuseKey"; attribute :>> custody="No conflicting new identity"; }
part contract3:ContractRow { attribute :>> fromNode="SubviewCertificate"; attribute :>> toNode="SlotKey"; attribute :>> custody="Same parent generation and schema"; }
part contract4:ContractRow { attribute :>> fromNode="SlotKey"; attribute :>> toNode="RegistryCandidate"; attribute :>> custody="Complete rooted slot runs"; }
part contract5:ContractRow { attribute :>> fromNode="SourceWriteLease"; attribute :>> toNode="RegistryCandidate"; attribute :>> custody="Freeze old semantic binding"; }
part contract6:ContractRow { attribute :>> fromNode="RegistryCandidate"; attribute :>> toNode="CommitRecord"; attribute :>> custody="Publish rooted bundle"; }
part contract7:ContractRow { attribute :>> fromNode="CommitRecord"; attribute :>> toNode="KnownCoverage"; attribute :>> custody="Exact result query"; }
part contract8:ContractRow { attribute :>> fromNode="KnownCoverage"; attribute :>> toNode="CopyLeaseRelease"; attribute :>> custody="Independent persistent target root"; }
part contract9:ContractRow { attribute :>> fromNode="CopyLeaseRelease"; attribute :>> toNode="SourceLeaseLedger"; attribute :>> custody="Settle exact copied-source lease"; }
part contract10:ContractRow { attribute :>> fromNode="CloseAliasAdmission"; attribute :>> toNode="AliasDrain"; attribute :>> custody="Drain lookup users and scans"; }
part contract11:ContractRow { attribute :>> fromNode="AliasDrain"; attribute :>> toNode="AliasLeaseRelease"; attribute :>> custody="Exact old lease completion"; }
part contract12:ContractRow { attribute :>> fromNode="AliasLeaseRelease"; attribute :>> toNode="SourceLeaseLedger"; attribute :>> custody="Settle exact drained alias lease"; }
part contract13:ContractRow { attribute :>> fromNode="SourceClose"; attribute :>> toNode="StorageClose"; attribute :>> custody="Close writers and native borrow admission"; }
part contract14:ContractRow { attribute :>> fromNode="StorageClose"; attribute :>> toNode="BackingSettlement"; attribute :>> custody="Root cell and payload arena separate"; }
part contract15:ContractRow { attribute :>> fromNode="BackingSettlement"; attribute :>> toNode="StorageReclaimPermit"; attribute :>> custody="Backing ownership settled"; }
part contract16:ContractRow { attribute :>> fromNode="ReclaimStorage"; attribute :>> toNode="NextGeneration"; attribute :>> custody="Strict advance or refuse exhaustion"; }
part contract17:ContractRow { attribute :>> fromNode="NextGeneration"; attribute :>> toNode="RejectStaleKey"; attribute :>> custody="Validate before pointer access"; }
part contract18:ContractRow { attribute :>> fromNode="UnknownOutcome"; attribute :>> toNode="RetainedCustody"; attribute :>> custody="No timeout inferred release"; }
part def BindingRow { attribute actionName:String; attribute lemma:String; attribute scope:String; }
part binding0:BindingRow { attribute :>> actionName="registry_slot_issuance.probeSubview"; attribute :>> lemma="SlotIssuance.probeSubviewPreserves"; attribute :>> scope="one registry entry; fixed lease/users; two storage incarnations; native fidelity open"; }
part binding1:BindingRow { attribute :>> actionName="registry_slot_issuance.probeAdjacent"; attribute :>> lemma="SlotIssuance.probeAdjacentPreserves"; attribute :>> scope="one registry entry; fixed lease/users; two storage incarnations; native fidelity open"; }
part binding2:BindingRow { attribute :>> actionName="registry_slot_issuance.probeOverlap"; attribute :>> lemma="SlotIssuance.probeOverlapPreserves"; attribute :>> scope="one registry entry; fixed lease/users; two storage incarnations; native fidelity open"; }
part binding3:BindingRow { attribute :>> actionName="registry_slot_issuance.probeUnownedExact"; attribute :>> lemma="SlotIssuance.probeUnownedExactPreserves"; attribute :>> scope="one registry entry; fixed lease/users; two storage incarnations; native fidelity open"; }
part binding4:BindingRow { attribute :>> actionName="registry_slot_issuance.issueSubview"; attribute :>> lemma="SlotIssuance.issueSubviewPreserves"; attribute :>> scope="one registry entry; fixed lease/users; two storage incarnations; native fidelity open"; }
part binding5:BindingRow { attribute :>> actionName="registry_slot_issuance.issueFresh"; attribute :>> lemma="SlotIssuance.issueFreshPreserves"; attribute :>> scope="one registry entry; fixed lease/users; two storage incarnations; native fidelity open"; }
part binding6:BindingRow { attribute :>> actionName="registry_slot_issuance.rejectOverlap"; attribute :>> lemma="SlotIssuance.rejectOverlapPreserves"; attribute :>> scope="one registry entry; fixed lease/users; two storage incarnations; native fidelity open"; }
part binding7:BindingRow { attribute :>> actionName="registry_slot_issuance.rejectUnownedExact"; attribute :>> lemma="SlotIssuance.rejectUnownedExactPreserves"; attribute :>> scope="one registry entry; fixed lease/users; two storage incarnations; native fidelity open"; }
part binding8:BindingRow { attribute :>> actionName="registry_slot_issuance.saveKey"; attribute :>> lemma="SlotIssuance.saveKeyPreserves"; attribute :>> scope="one registry entry; fixed lease/users; two storage incarnations; native fidelity open"; }
part binding9:BindingRow { attribute :>> actionName="registry_slot_issuance.prepareAlias"; attribute :>> lemma="SlotIssuance.prepareAliasPreserves"; attribute :>> scope="one registry entry; fixed lease/users; two storage incarnations; native fidelity open"; }
part binding10:BindingRow { attribute :>> actionName="registry_slot_issuance.prepareCopy"; attribute :>> lemma="SlotIssuance.prepareCopyPreserves"; attribute :>> scope="one registry entry; fixed lease/users; two storage incarnations; native fidelity open"; }
part binding11:BindingRow { attribute :>> actionName="registry_slot_issuance.materializeCopy"; attribute :>> lemma="SlotIssuance.materializeCopyPreserves"; attribute :>> scope="one registry entry; fixed lease/users; two storage incarnations; native fidelity open"; }
part binding12:BindingRow { attribute :>> actionName="registry_slot_issuance.publishAlias"; attribute :>> lemma="SlotIssuance.publishAliasPreserves"; attribute :>> scope="one registry entry; fixed lease/users; two storage incarnations; native fidelity open"; }
part binding13:BindingRow { attribute :>> actionName="registry_slot_issuance.publishCopy"; attribute :>> lemma="SlotIssuance.publishCopyPreserves"; attribute :>> scope="one registry entry; fixed lease/users; two storage incarnations; native fidelity open"; }
part binding14:BindingRow { attribute :>> actionName="registry_slot_issuance.queryCommit"; attribute :>> lemma="SlotIssuance.queryCommitPreserves"; attribute :>> scope="one registry entry; fixed lease/users; two storage incarnations; native fidelity open"; }
part binding15:BindingRow { attribute :>> actionName="registry_slot_issuance.releaseCopyLease"; attribute :>> lemma="SlotIssuance.releaseCopyLeasePreserves"; attribute :>> scope="one registry entry; fixed lease/users; two storage incarnations; native fidelity open"; }
part binding16:BindingRow { attribute :>> actionName="registry_slot_issuance.beginLookup"; attribute :>> lemma="SlotIssuance.beginLookupPreserves"; attribute :>> scope="one registry entry; fixed lease/users; two storage incarnations; native fidelity open"; }
part binding17:BindingRow { attribute :>> actionName="registry_slot_issuance.acceptBorrow"; attribute :>> lemma="SlotIssuance.acceptBorrowPreserves"; attribute :>> scope="one registry entry; fixed lease/users; two storage incarnations; native fidelity open"; }
part binding18:BindingRow { attribute :>> actionName="registry_slot_issuance.lookupUnknown"; attribute :>> lemma="SlotIssuance.lookupUnknownPreserves"; attribute :>> scope="one registry entry; fixed lease/users; two storage incarnations; native fidelity open"; }
part binding19:BindingRow { attribute :>> actionName="registry_slot_issuance.resolveLookup"; attribute :>> lemma="SlotIssuance.resolveLookupPreserves"; attribute :>> scope="one registry entry; fixed lease/users; two storage incarnations; native fidelity open"; }
part binding20:BindingRow { attribute :>> actionName="registry_slot_issuance.rejectLookup"; attribute :>> lemma="SlotIssuance.rejectLookupPreserves"; attribute :>> scope="one registry entry; fixed lease/users; two storage incarnations; native fidelity open"; }
part binding21:BindingRow { attribute :>> actionName="registry_slot_issuance.returnBorrow"; attribute :>> lemma="SlotIssuance.returnBorrowPreserves"; attribute :>> scope="one registry entry; fixed lease/users; two storage incarnations; native fidelity open"; }
part binding22:BindingRow { attribute :>> actionName="registry_slot_issuance.closeRegistry"; attribute :>> lemma="SlotIssuance.closeRegistryPreserves"; attribute :>> scope="one registry entry; fixed lease/users; two storage incarnations; native fidelity open"; }
part binding23:BindingRow { attribute :>> actionName="registry_slot_issuance.beginScan"; attribute :>> lemma="SlotIssuance.beginScanPreserves"; attribute :>> scope="one registry entry; fixed lease/users; two storage incarnations; native fidelity open"; }
part binding24:BindingRow { attribute :>> actionName="registry_slot_issuance.finishScan"; attribute :>> lemma="SlotIssuance.finishScanPreserves"; attribute :>> scope="one registry entry; fixed lease/users; two storage incarnations; native fidelity open"; }
part binding25:BindingRow { attribute :>> actionName="registry_slot_issuance.scanUnknown"; attribute :>> lemma="SlotIssuance.scanUnknownPreserves"; attribute :>> scope="one registry entry; fixed lease/users; two storage incarnations; native fidelity open"; }
part binding26:BindingRow { attribute :>> actionName="registry_slot_issuance.resolveScan"; attribute :>> lemma="SlotIssuance.resolveScanPreserves"; attribute :>> scope="one registry entry; fixed lease/users; two storage incarnations; native fidelity open"; }
part binding27:BindingRow { attribute :>> actionName="registry_slot_issuance.retireRegistry"; attribute :>> lemma="SlotIssuance.retireRegistryPreserves"; attribute :>> scope="one registry entry; fixed lease/users; two storage incarnations; native fidelity open"; }
part binding28:BindingRow { attribute :>> actionName="registry_slot_issuance.releaseRetiredAliasLease"; attribute :>> lemma="SlotIssuance.releaseRetiredAliasLeasePreserves"; attribute :>> scope="one registry entry; fixed lease/users; two storage incarnations; native fidelity open"; }
part binding29:BindingRow { attribute :>> actionName="registry_slot_issuance.abortCandidate"; attribute :>> lemma="SlotIssuance.abortCandidatePreserves"; attribute :>> scope="one registry entry; fixed lease/users; two storage incarnations; native fidelity open"; }
part binding30:BindingRow { attribute :>> actionName="registry_slot_issuance.sourceWrite"; attribute :>> lemma="SlotIssuance.sourceWritePreserves"; attribute :>> scope="one registry entry; fixed lease/users; two storage incarnations; native fidelity open"; }
part binding31:BindingRow { attribute :>> actionName="registry_slot_issuance.sourceBorrowBegin"; attribute :>> lemma="SlotIssuance.sourceBorrowBeginPreserves"; attribute :>> scope="one registry entry; fixed lease/users; two storage incarnations; native fidelity open"; }
part binding32:BindingRow { attribute :>> actionName="registry_slot_issuance.sourceBorrowReturn"; attribute :>> lemma="SlotIssuance.sourceBorrowReturnPreserves"; attribute :>> scope="one registry entry; fixed lease/users; two storage incarnations; native fidelity open"; }
part binding33:BindingRow { attribute :>> actionName="registry_slot_issuance.closeStorage"; attribute :>> lemma="SlotIssuance.closeStoragePreserves"; attribute :>> scope="one registry entry; fixed lease/users; two storage incarnations; native fidelity open"; }
part binding34:BindingRow { attribute :>> actionName="registry_slot_issuance.settleBacking"; attribute :>> lemma="SlotIssuance.settleBackingPreserves"; attribute :>> scope="one registry entry; fixed lease/users; two storage incarnations; native fidelity open"; }
part binding35:BindingRow { attribute :>> actionName="registry_slot_issuance.reclaimStorage"; attribute :>> lemma="SlotIssuance.reclaimStoragePreserves"; attribute :>> scope="one registry entry; fixed lease/users; two storage incarnations; native fidelity open"; }
part binding36:BindingRow { attribute :>> actionName="registry_slot_issuance.reuseStorage"; attribute :>> lemma="SlotIssuance.reuseStoragePreserves"; attribute :>> scope="one registry entry; fixed lease/users; two storage incarnations; native fidelity open"; }
part binding37:BindingRow { attribute :>> actionName="registry_slot_issuance.rejectStaleKey"; attribute :>> lemma="SlotIssuance.rejectStaleKeyPreserves"; attribute :>> scope="one registry entry; fixed lease/users; two storage incarnations; native fidelity open"; }
part def ProofRow { attribute key:String; attribute lemma:String; }
part proof0:ProofRow { attribute :>> key="stepPreserves"; attribute :>> lemma="SlotIssuance.stepPreserves"; }
part proof1:ProofRow { attribute :>> key="reachableSafe"; attribute :>> lemma="SlotIssuance.reachableSafe"; }
part proof2:ProofRow { attribute :>> key="aliasBindingStable"; attribute :>> lemma="SlotIssuance.aliasBindingStable"; }
part proof3:ProofRow { attribute :>> key="publicationUnknownBlocksCopyRelease"; attribute :>> lemma="SlotIssuance.publicationUnknownBlocksCopyRelease"; }
part proof4:ProofRow { attribute :>> key="aliasBlocksSourceWrite"; attribute :>> lemma="SlotIssuance.aliasBlocksSourceWrite"; }
part proof5:ProofRow { attribute :>> key="aliasReleaseRequiresRetirement"; attribute :>> lemma="SlotIssuance.aliasReleaseRequiresRetirement"; }
part proof6:ProofRow { attribute :>> key="copyReleaseRequiresKnownRoot"; attribute :>> lemma="SlotIssuance.copyReleaseRequiresKnownRoot"; }
part proof7:ProofRow { attribute :>> key="reuseAdvancesGeneration"; attribute :>> lemma="SlotIssuance.reuseAdvancesGeneration"; }
part proof8:ProofRow { attribute :>> key="exhaustionDeniesReuse"; attribute :>> lemma="SlotIssuance.exhaustionDeniesReuse"; }
part proof9:ProofRow { attribute :>> key="staleKeyCannotPrepare"; attribute :>> lemma="SlotIssuance.staleKeyCannotPrepare"; }
part proof10:ProofRow { attribute :>> key="freshIssuedDisjoint"; attribute :>> lemma="SlotIssuance.freshIssuedDisjoint"; }
part proof11:ProofRow { attribute :>> key="unknownAckBlocksRetirement"; attribute :>> lemma="SlotIssuance.unknownAckBlocksRetirement"; }
part proof12:ProofRow { attribute :>> key="adjacencyDisjoint"; attribute :>> lemma="StorageIntervals.adjacencyDisjoint"; }
part proof13:ProofRow { attribute :>> key="overlapCannotMintFresh"; attribute :>> lemma="StorageIntervals.overlapCannotMintFresh"; }
part proof14:ProofRow { attribute :>> key="subviewOffsetInside"; attribute :>> lemma="StorageIntervals.subviewOffsetInside"; }
part proof15:ProofRow { attribute :>> key="exactUnownedRangeOverlaps"; attribute :>> lemma="StorageIntervals.exactUnownedRangeOverlaps"; }
part proof16:ProofRow { attribute :>> key="pointInBothContradictsDisjoint"; attribute :>> lemma="StorageIntervals.pointInBothContradictsDisjoint"; }
part proof17:ProofRow { attribute :>> key="generationSeparatesKey"; attribute :>> lemma="StorageIntervals.generationSeparatesKey"; }
part proof18:ProofRow { attribute :>> key="aliasKeepsBackingPremise"; attribute :>> lemma="SlotIssuanceBridge.aliasKeepsBackingPremise"; }
part proof19:ProofRow { attribute :>> key="oldParentAliasFreeDenied"; attribute :>> lemma="SlotIssuanceBridge.oldParentAliasFreeDenied"; }
part proof20:ProofRow { attribute :>> key="backingReceiptSeparate"; attribute :>> lemma="SlotIssuanceBridge.backingReceiptSeparate"; }
part proof21:ProofRow { attribute :>> key="copyLeaseDoesNotDrainTargetBorrow"; attribute :>> lemma="SlotIssuanceBridge.copyLeaseDoesNotDrainTargetBorrow"; }
part def RouteRow { attribute component:String; attribute actionName:String; attribute lemma:String; attribute producerAnchor:String; attribute obligationId:String; }
part route0:RouteRow { attribute :>> component="storage"; attribute :>> actionName="registry_slot_issuance.issueSubview"; attribute :>> lemma="SlotIssuance.issueSubviewPreserves"; attribute :>> producerAnchor="root-field"; attribute :>> obligationId="SI-source"; }
part route1:RouteRow { attribute :>> component="storage"; attribute :>> actionName="registry_slot_issuance.issueFresh"; attribute :>> lemma="SlotIssuance.issueFreshPreserves"; attribute :>> producerAnchor="rc-allocation"; attribute :>> obligationId="SI-source"; }
part route2:RouteRow { attribute :>> component="storage"; attribute :>> actionName="registry_slot_issuance.rejectOverlap"; attribute :>> lemma="SlotIssuance.rejectOverlapPreserves"; attribute :>> producerAnchor="rc-address"; attribute :>> obligationId="SI-source"; }
part route3:RouteRow { attribute :>> component="registry"; attribute :>> actionName="registry_slot_issuance.publishAlias"; attribute :>> lemma="SlotIssuance.publishAliasPreserves"; attribute :>> producerAnchor="rc-register"; attribute :>> obligationId="SI-roots"; }
part route4:RouteRow { attribute :>> component="registry"; attribute :>> actionName="registry_slot_issuance.publishCopy"; attribute :>> lemma="SlotIssuance.publishCopyPreserves"; attribute :>> producerAnchor="vm-request-slots"; attribute :>> obligationId="SI-roots"; }
part route5:RouteRow { attribute :>> component="registry"; attribute :>> actionName="registry_slot_issuance.queryCommit"; attribute :>> lemma="SlotIssuance.queryCommitPreserves"; attribute :>> producerAnchor="register-export"; attribute :>> obligationId="SI-roots"; }
part route6:RouteRow { attribute :>> component="writer"; attribute :>> actionName="registry_slot_issuance.prepareAlias"; attribute :>> lemma="SlotIssuance.prepareAliasPreserves"; attribute :>> producerAnchor="tcl-install"; attribute :>> obligationId="SI-writers"; }
part route7:RouteRow { attribute :>> component="writer"; attribute :>> actionName="registry_slot_issuance.sourceWrite"; attribute :>> lemma="SlotIssuance.sourceWritePreserves"; attribute :>> producerAnchor="rc-write"; attribute :>> obligationId="SI-writers"; }
part route8:RouteRow { attribute :>> component="lease"; attribute :>> actionName="registry_slot_issuance.releaseCopyLease"; attribute :>> lemma="SlotIssuance.releaseCopyLeasePreserves"; attribute :>> producerAnchor="tcl-call"; attribute :>> obligationId="SI-execution"; }
part route9:RouteRow { attribute :>> component="lease"; attribute :>> actionName="registry_slot_issuance.releaseRetiredAliasLease"; attribute :>> lemma="SlotIssuance.releaseRetiredAliasLeasePreserves"; attribute :>> producerAnchor="tcl-delete-native"; attribute :>> obligationId="SI-execution"; }
part route10:RouteRow { attribute :>> component="lease"; attribute :>> actionName="registry_slot_issuance.lookupUnknown"; attribute :>> lemma="SlotIssuance.lookupUnknownPreserves"; attribute :>> producerAnchor="task-claim-body"; attribute :>> obligationId="SI-execution"; }
part route11:RouteRow { attribute :>> component="storage"; attribute :>> actionName="registry_slot_issuance.reclaimStorage"; attribute :>> lemma="SlotIssuance.reclaimStoragePreserves"; attribute :>> producerAnchor="pstate-cleanup"; attribute :>> obligationId="SI-storage"; }
part route12:RouteRow { attribute :>> component="generation"; attribute :>> actionName="registry_slot_issuance.reuseStorage"; attribute :>> lemma="SlotIssuance.reuseStoragePreserves"; attribute :>> producerAnchor="incarnation-issuer"; attribute :>> obligationId="SI-platform"; }
part route13:RouteRow { attribute :>> component="generation"; attribute :>> actionName="registry_slot_issuance.rejectStaleKey"; attribute :>> lemma="SlotIssuance.rejectStaleKeyPreserves"; attribute :>> producerAnchor="task-publish-body"; attribute :>> obligationId="SI-platform"; }
part def Need { attribute obligationId:String; attribute kind:String; attribute subjectPath:String; attribute subjectScope:String; ref owner:Owner; }
part formalNeed:Need { attribute :>> obligationId="SI-formal"; attribute :>> kind="induction"; attribute :>> subjectPath="dev/refactoring/modern-c/models/lean/SlotIssuance.lean"; attribute :>> subjectScope="bounded storage/lease all-step induction; not native execution"; ref :>> owner=leaseOwner; }
part bridgeNeed:Need { attribute :>> obligationId="SI-bridge"; attribute :>> kind="composition"; attribute :>> subjectPath="dev/refactoring/modern-c/models/lean/SlotIssuanceBridge.lean"; attribute :>> subjectScope="generic interval/generation algebra and conditional parent boundaries"; ref :>> owner=leaseOwner; }
part sourceNeed:Need { attribute :>> obligationId="SI-source"; attribute :>> kind="source"; attribute :>> subjectPath="vendor/gambit/lib/_mem/rc-allocation.inc"; attribute :>> subjectScope="complete VM allocation/provenance census and canonical SlotKey issuer"; ref :>> owner=storageOwner; }
part executionNeed:Need { attribute :>> obligationId="SI-execution"; attribute :>> kind="source"; attribute :>> subjectPath="vendor/gambit/examples/tcltk/tcltk.scm"; attribute :>> subjectScope="actual LeaseId signers and every indirect/native borrower"; ref :>> owner=leaseOwner; }
part rootsNeed:Need { attribute :>> obligationId="SI-roots"; attribute :>> kind="source"; attribute :>> subjectPath="vendor/gambit/lib/_mem/root-origins.inc"; attribute :>> subjectScope="atomic registry/root publication and every-round target coverage"; ref :>> owner=registryOwner; }
part writersNeed:Need { attribute :>> obligationId="SI-writers"; attribute :>> kind="source"; attribute :>> subjectPath="vendor/gambit/include/_gambit/global_state.h.in"; attribute :>> subjectScope="all direct/indirect/native header writers mediated"; ref :>> owner=writerOwner; }
part platformNeed:Need { attribute :>> obligationId="SI-platform"; attribute :>> kind="platform"; attribute :>> subjectPath="vendor/gambit/include/_gambit/vm_state.h.in"; attribute :>> subjectScope="native finite generations index/ABA and C23 refinement"; ref :>> owner=generationOwner; }
part storageNeed:Need { attribute :>> obligationId="SI-storage"; attribute :>> kind="source"; attribute :>> subjectPath="vendor/gambit/lib/_mem/memory-lifecycle.inc"; attribute :>> subjectScope="complete root-cell/arena/code/context/foreign cleanup owners"; ref :>> owner=storageOwner; }
part def MetricRow { attribute key:String; attribute unit:String; attribute baseline:String; attribute candidate:String; attribute acceptance:String; }
part metric0:MetricRow { attribute :>> key="root-work"; attribute :>> unit="slot visits per round"; attribute :>> baseline="Legacy admitted logical references M"; attribute :>> candidate="Canonical physical cells S"; attribute :>> acceptance="Potential removed visits M-S only if current baseline actually duplicates"; }
part metric1:MetricRow { attribute :>> key="copy-storage"; attribute :>> unit="SCMOBJ words plus separately reported metadata/backing bytes"; attribute :>> baseline="Alias adds no target root word but retains source dependencies"; attribute :>> candidate="Independent copied cell adds one root word per slot plus descriptor/index storage"; attribute :>> acceptance="Do not infer total bytes without native layout and backing census"; }
part metric2:MetricRow { attribute :>> key="writer-wait"; attribute :>> unit="source setter blocked duration"; attribute :>> baseline="Alias holds until final alias drain"; attribute :>> candidate="Copy can release after known persistent coverage"; attribute :>> acceptance="Potential saving only if real source writes occur; inspected Tcl/C closure bodies only install initially"; }
part metric3:MetricRow { attribute :>> key="decision"; attribute :>> unit="cost vector: work, live bytes over time, blocked duration"; attribute :>> baseline="Matched semantic and lifetime workload"; attribute :>> candidate="Report each dimension separately"; attribute :>> acceptance="Pareto improvement or explicit workload weights; never add bytes to seconds without weights"; }
part contract19:ContractRow { attribute :>> fromNode="SourceLeaseLedger"; attribute :>> toNode="SourceWriteAdmission"; attribute :>> custody="Write only if source remains open"; }
part contract20:ContractRow { attribute :>> fromNode="StorageClose"; attribute :>> toNode="SourceWriteAdmission"; attribute :>> custody="Closed source rejects writes"; }
part contract21:ContractRow { attribute :>> fromNode="StorageClose"; attribute :>> toNode="StorageReclaimPermit"; attribute :>> custody="Admission closed"; }
part contract22:ContractRow { attribute :>> fromNode="SourceLeaseLedger"; attribute :>> toNode="StorageReclaimPermit"; attribute :>> custody="No outstanding source lease"; }
part contract23:ContractRow { attribute :>> fromNode="NativeBorrowDrain"; attribute :>> toNode="StorageReclaimPermit"; attribute :>> custody="Accepted native users settled"; }
part contract24:ContractRow { attribute :>> fromNode="ScanGrace"; attribute :>> toNode="StorageReclaimPermit"; attribute :>> custody="No frozen GC view"; }
part contract25:ContractRow { attribute :>> fromNode="StorageReclaimPermit"; attribute :>> toNode="ReclaimStorage"; attribute :>> custody="All custody conditions"; }
part contract26:ContractRow { attribute :>> fromNode="StorageClose"; attribute :>> toNode="NativeBorrowDrain"; attribute :>> custody="Drain accepted native users"; }
part contract27:ContractRow { attribute :>> fromNode="AbortReceipt"; attribute :>> toNode="SourceLeaseLedger"; attribute :>> custody="Known nonpublication only"; }
part proof22:ProofRow { attribute :>> key="copyReleaseHasDisjointTarget"; attribute :>> lemma="SlotIssuance.copyReleaseHasDisjointTarget"; }
part contract28:ContractRow { attribute :>> fromNode="FreshDisjointStorage"; attribute :>> toNode="RegistryCandidate"; attribute :>> custody="Copy mode requires valid signed target extent"; }
}
