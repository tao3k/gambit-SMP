package GambitSfunConverterUseClosure { private import ScalarValues::*;
part def Owner { attribute componentId:String; }
part controlOwner:Owner { attribute :>> componentId="control"; }
part resourcesOwner:Owner { attribute :>> componentId="resources"; }
part def SourceRow { attribute key:String; attribute path:String; attribute needle:String; attribute obligation:String; }
part source0:SourceRow { attribute :>> key="generator-wrapping"; attribute :>> path="vendor/gambit/gsc/_ptree2.scm"; attribute :>> needle="(c-convert-argument\n              sfun?"; attribute :>> obligation="nested argument conversions wrap body and initial result conversion"; }
part source1:SourceRow { attribute :>> key="generator-arg-decl"; attribute :>> path="vendor/gambit/gsc/_ptree2.scm"; attribute :>> needle="(define (c-declare-argument sfun? numbered-typ body)"; attribute :>> obligation="argument and indirect-copy scopes"; }
part source2:SourceRow { attribute :>> key="generator-arg-copy"; attribute :>> path="vendor/gambit/gsc/_ptree2.scm"; attribute :>> needle="c-id-prefix \"END_SFUN_COPY_\" tail"; attribute :>> obligation="copy scope does not itself destroy copied payload"; }
part source3:SourceRow { attribute :>> key="generator-first-result"; attribute :>> path="vendor/gambit/gsc/_ptree2.scm"; attribute :>> needle="(make-body (c-set-result sfun? result-typ) cleanup?)"; attribute :>> obligation="first conversion inside input argument scopes"; }
part source4:SourceRow { attribute :>> key="generator-error-loop"; attribute :>> path="vendor/gambit/gsc/_ptree2.scm"; attribute :>> needle="\"SFUN_ERROR\""; attribute :>> obligation="loop follows convert-param-list"; }
part source5:SourceRow { attribute :>> key="generator-last-result"; attribute :>> path="vendor/gambit/gsc/_ptree2.scm"; attribute :>> needle="(if sfun?\n                    (c-set-result sfun? result-typ)"; attribute :>> obligation="retry-loop result conversion precedes END_SFUN"; }
part source6:SourceRow { attribute :>> key="generator-scheme-first"; attribute :>> path="vendor/gambit/gsc/_ptree2.scm"; attribute :>> needle="(append (keep scmobj-typ? numbered-param-typs)"; attribute :>> obligation="Scheme-object arguments ordered first; nontrivial C conversions follow"; }
part source7:SourceRow { attribute :>> key="custom-c-type"; attribute :>> path="vendor/gambit/gsc/_ptree2.scm"; attribute :>> needle="(vector 'c-type"; attribute :>> obligation="custom converter names and cleanup boolean"; }
part source8:SourceRow { attribute :>> key="custom-cleanup-bool"; attribute :>> path="vendor/gambit/gsc/_ptree2.scm"; attribute :>> needle="\"Fifth argument to 'c-define-type' must be a boolean\""; attribute :>> obligation="cleanup bit is not a callback or escape effect summary"; }
part source9:SourceRow { attribute :>> key="custom-emit"; attribute :>> path="vendor/gambit/gsc/_ptree2.scm"; attribute :>> needle="(vector-ref def 3)"; attribute :>> obligation="custom result converter text, not semantic qualification"; }
part source10:SourceRow { attribute :>> key="release-function-selection"; attribute :>> path="vendor/gambit/gsc/_ptree2.scm"; attribute :>> needle="c-interface-release-fns"; attribute :>> obligation="explicit release function or generated release stub"; }
part source11:SourceRow { attribute :>> key="arg-int-end"; attribute :>> path="vendor/gambit/include/_gambit/foreign_conversion.h.in"; attribute :>> needle="#define ___END_SFUN_INT_TO_SCMOBJ(c,s,i)___EXT(___release_scmobj)(s);}"; attribute :>> obligation="built-in arg end drops Scheme native hold"; }
part source12:SourceRow { attribute :>> key="arg-char-end"; attribute :>> path="vendor/gambit/include/_gambit/foreign_conversion.h.in"; attribute :>> needle="#define ___END_SFUN_CHAR_TO_SCMOBJ(c,s,i)}"; attribute :>> obligation="immediate close-only argument"; }
part source13:SourceRow { attribute :>> key="arg-struct-end"; attribute :>> path="vendor/gambit/include/_gambit/foreign_conversion.h.in"; attribute :>> needle="#define ___END_SFUN_STRUCT_TO_SCMOBJ(n,c,t,r,s,i)___EXT(___release_scmobj)(s);}"; attribute :>> obligation="foreign wrapper ref drop, not payload destruction"; }
part source14:SourceRow { attribute :>> key="result-struct-end"; attribute :>> path="vendor/gambit/include/_gambit/foreign_conversion.h.in"; attribute :>> needle="#define ___END_SFUN_SCMOBJ_TO_STRUCT(n,s,c,t)"; attribute :>> obligation="typed result end has no local native cleanup"; }
part source15:SourceRow { attribute :>> key="copy-start"; attribute :>> path="vendor/gambit/include/_gambit/foreign_conversion.h.in"; attribute :>> needle="#define ___BEGIN_SFUN_COPY_STRUCT(n,r,arg){ void *r; ___ASSIGN_NEW_WITH_INIT(r,struct n,arg);"; attribute :>> obligation="private native copy exists before wrapper success"; }
part source16:SourceRow { attribute :>> key="copy-end"; attribute :>> path="vendor/gambit/include/_gambit/foreign_conversion.h.in"; attribute :>> needle="#define ___END_SFUN_COPY_STRUCT(n,r,arg)}"; attribute :>> obligation="copy scope only closes"; }
part source17:SourceRow { attribute :>> key="c-rc-copy"; attribute :>> path="vendor/gambit/include/_gambit/foreign_conversion.h.in"; attribute :>> needle="var = ___CAST(type*,___EXT(___alloc_rc) (___PSP sizeof (type)));"; attribute :>> obligation="C allocator path; C++ is not the design baseline"; }
part source18:SourceRow { attribute :>> key="final-marker"; attribute :>> path="vendor/gambit/include/_gambit/foreign_conversion.h.in"; attribute :>> needle="#define ___END_SFUN } ___EXT(___kill_sfun_stack_marker) (___marker);"; attribute :>> obligation="final normal owner release after error loop"; }
part source19:SourceRow { attribute :>> key="no-sfun-catcher"; attribute :>> path="vendor/gambit/include/_gambit/foreign_conversion.h.in"; attribute :>> needle="#define ___BEGIN_SFUN_BODY"; attribute :>> obligation="outer native unwind can bypass local arg release and END_SFUN"; }
part source20:SourceRow { attribute :>> key="release-scmobj"; attribute :>> path="vendor/gambit/lib/_mem/object-allocation.inc"; attribute :>> needle="___EXP_FUNC(___SCMOBJ,___release_scmobj)"; attribute :>> obligation="body only checks allocation kind and decrements still count"; }
part source21:SourceRow { attribute :>> key="still-dec"; attribute :>> path="vendor/gambit/lib/_mem/still-refcount.inc"; attribute :>> needle="___BODY0(obj)[___STILL_REFCOUNT-___STILL_BODY]--;"; attribute :>> obligation="physical effect is non-idempotent"; }
part source22:SourceRow { attribute :>> key="wrap-alloc"; attribute :>> path="vendor/gambit/lib/c_intf.c"; attribute :>> needle="___SCMOBJ r = ___alloc_scmobj (___ps, ___sFOREIGN, ___FOREIGN_SIZE<<___LWS);"; attribute :>> obligation="foreign-wrapper allocation can fail"; }
part source23:SourceRow { attribute :>> key="wrap-success"; attribute :>> path="vendor/gambit/lib/c_intf.c"; attribute :>> needle="___FOREIGN_RELEASE_FN_FIELD(r) = ___CAST(___SCMOBJ,release_fn);"; attribute :>> obligation="successful wrapper owns pointer and destructor registration"; }
part source24:SourceRow { attribute :>> key="struct-fail"; attribute :>> path="vendor/gambit/lib/c_intf.c"; attribute :>> needle="else if ((e = ___POINTER_to_SCMOBJ (___ps, x, tags, release_fn, obj, arg_num))\n           != ___FIX(___NO_ERR))\n    release_fn (x);"; attribute :>> obligation="struct/union/type wrappers synchronously invoke release_fn on wrapping failure"; }
part source25:SourceRow { attribute :>> key="destructor-before-call"; attribute :>> path="vendor/gambit/lib/c_intf.c"; attribute :>> needle="___FOREIGN_PTR_FIELD(obj) =\n        ___CAST(___SCMOBJ,___CAST(void*,0));"; attribute :>> obligation="release_foreign clears pointer/handler before invoking callback"; }
part source26:SourceRow { attribute :>> key="destructor-result"; attribute :>> path="vendor/gambit/lib/c_intf.c"; attribute :>> needle="if ((e = release_fn (ptr)) != ___FIX(___NO_ERR))"; attribute :>> obligation="foreign callback failure does not restore prior pointer state"; }
part source27:SourceRow { attribute :>> key="still-sweep"; attribute :>> path="vendor/gambit/lib/_mem/still-sweep.inc"; attribute :>> needle="___release_foreign"; attribute :>> obligation="real collector foreign destructor consumer; return value not checked at shown call sites"; }
part source28:SourceRow { attribute :>> key="noop-pointer-release"; attribute :>> path="vendor/gambit/lib/c_intf.c"; attribute :>> needle="pointer is under the control of the \"C world\"."; attribute :>> obligation="default raw pointer release does not own/free native payload"; }
part source29:SourceRow { attribute :>> key="root-slots"; attribute :>> path="vendor/gambit/lib/_mem/root-origins.inc"; attribute :>> needle="mark_array (work, context->r, sizeof(context->r)/sizeof(*context->r));"; attribute :>> obligation="logical root lease is not full registered-slot proof"; }
part source30:SourceRow { attribute :>> key="source-example"; attribute :>> path="vendor/gambit/examples/pthread/mylib.scm"; attribute :>> needle="(c-define (increment-counter c) (counter) void \"increment_counter\" \"\""; attribute :>> obligation="real wrapper receives Scheme-object argument; no synthetic copied-struct path claimed"; }
part source31:SourceRow { attribute :>> key="source-types"; attribute :>> path="vendor/gambit/examples/Xlib-simple/Xlib.scm"; attribute :>> needle="(c-define-type XGCValues \"XGCValues\")"; attribute :>> obligation="actual named native value type; does not alone prove SFUN struct argument reachability"; }
part source32:SourceRow { attribute :>> key="paper-fulltext"; attribute :>> path="evidence/research/source-references/feeley-sfp/8bb2fae8ae4b54d3a86206596f90e9cf73da39846af0f39244a476074cf81ed4.txt"; attribute :>> needle="3   Approa h 2:"; attribute :>> obligation="local official Gambit paper; damaged extraction not reconstructed"; }
part def RoleRow { attribute key:String; attribute identity:String; attribute retirement:String; attribute boundary:String; }
part role0:RoleRow { attribute :>> key="ConverterUsePlan"; attribute :>> identity="Direction, parameter/result position, resolved type and source fingerprint"; attribute :>> retirement="Frozen plan dominates all generated END/body/error/finalizer paths"; attribute :>> boundary="Boolean type-needs-cleanup is insufficient for effect/custody proof"; }
part role1:RoleRow { attribute :>> key="PrivateCopyCustody"; attribute :>> identity="Copy allocation identity and pending wrapper outcome"; attribute :>> retirement="Transfer to successful wrapper or certify destructor disposition"; attribute :>> boundary="Wrapping failure can call arbitrary release_fn; return alone is not disposal evidence"; }
part role2:RoleRow { attribute :>> key="InputReference"; attribute :>> identity="One still native hold produced by admitted C-to-Scheme conversion"; attribute :>> retirement="Actual END_SFUN conversion release or stable unwind guard"; attribute :>> boundary="Native hold drop is not foreign destructor and not proof of unreachability"; }
part role3:RoleRow { attribute :>> key="ForeignPayloadLease"; attribute :>> identity="Wrapper pointer/release_fn plus capture and image owners"; attribute :>> retirement="Explicit/GC destructor with reliable completion then image grace"; attribute :>> boundary="Native marker expiry does not destroy escaped Scheme payload"; }
part role4:RoleRow { attribute :>> key="OwnerFinalUse"; attribute :>> identity="Result terminal plus all native converter/arg users discharged"; attribute :>> retirement="Delegate parent owner closure protocol"; attribute :>> boundary="Do not wait for foreign GC destruction before closing native marker"; }
part def ProfileRow { attribute key:String; attribute repeatable:String; attribute actionName:String; attribute lemma:String; attribute producerAnchor:String; attribute boundary:String; }
part profile0:ProfileRow { attribute :>> key="built-in-input"; attribute :>> repeatable="one input conversion / release per successful wrapper"; attribute :>> actionName="sfun_converter_use_closure.dropInputReference"; attribute :>> lemma="ConverterUse.argumentDropIsNotDestruction"; attribute :>> producerAnchor="arg-int-end"; attribute :>> boundary="Reference-release end runs before handler retry loop; floating/bignum/string wrapper construction may allocate"; }
part profile1:ProfileRow { attribute :>> key="built-in-result"; attribute :>> repeatable="conversion repeats for typed handler results"; attribute :>> actionName="sfun_converter_use_closure.handlerBadResult"; attribute :>> lemma="ConverterUse.closureDischargesNativeUse"; attribute :>> producerAnchor="generator-last-result"; attribute :>> boundary="Retry does not recreate input conversions; custom converters need full effect contract"; }
part profile2:ProfileRow { attribute :>> key="copied-native-value"; attribute :>> repeatable="one private copy transfers into foreign wrapper"; attribute :>> actionName="sfun_converter_use_closure.wrapSuccess"; attribute :>> lemma="ConverterUse.privateAndWrappedExclusive"; attribute :>> producerAnchor="struct-fail"; attribute :>> boundary="Copy allocation/wrapping/callback failure are distinct; no success inferred from status alone"; }
part def IssuerRow { attribute key:String; attribute proposedIssuer:String; attribute actualSource:String; attribute status:String; attribute responsibility:String; }
part issuer0:IssuerRow { attribute :>> key="input-use"; attribute :>> proposedIssuer="GeneratedArgumentReleaseAdapter"; attribute :>> actualSource="END_SFUN_*_TO_SCMOBJ and release_scmobj"; attribute :>> status="source order established; managed adapter absent"; attribute :>> responsibility="Record native-hold drop while preserving payload/capture and code custody"; }
part issuer1:IssuerRow { attribute :>> key="private-disposition"; attribute :>> proposedIssuer="StableConversionAttemptOwner"; attribute :>> actualSource="BEGIN_SFUN_COPY plus STRUCT/UNION/TYPE_to_SCMOBJ failure branch"; attribute :>> status="not an existing qualified signer"; attribute :>> responsibility="Publish private allocation before callback-capable wrapping; reliable disposal receipt or retain unknown"; }
part issuer2:IssuerRow { attribute :>> key="final-use"; attribute :>> proposedIssuer="GeneratedConverterPlanFinalizer"; attribute :>> actualSource="_ptree2 convert-param-list then SFUN_ERROR and END_SFUN"; attribute :>> status="requires closed custom/built-in plan"; attribute :>> responsibility="Sign native-use closure after input uses discharged and final result successful; do not require payload destruction"; }
part issuer3:IssuerRow { attribute :>> key="payload"; attribute :>> proposedIssuer="ForeignReleaseCoordinator"; attribute :>> actualSource="release_foreign and still-sweep"; attribute :>> status="unknown-effect recovery and worker affinity open"; attribute :>> responsibility="Cleared object fields are not callback completion; stable record pins destructor code"; }
part issuer4:IssuerRow { attribute :>> key="abnormal"; attribute :>> proposedIssuer="StableNativeReturnCoordinator"; attribute :>> actualSource="source END_SFUN may be bypassed by ___call rethrow"; attribute :>> status="complete native signer unresolved"; attribute :>> responsibility="Guard adopts pending input references and private-copy attempts outside discarded C frames"; }
part def GainRow { attribute key:String; attribute avoided:String; attribute added:String; attribute condition:String; }
part gain0:GainRow { attribute :>> key="cleanup-direction"; attribute :>> avoided="Avoid charging foreign destructor at every built-in argument end"; attribute :>> added="One precise reference-use record per non-immediate input"; attribute :>> condition="43 releasing and 15 close-only C-to-Scheme END macro forms are source inventory, not dynamic call frequencies"; }
part gain1:GainRow { attribute :>> key="retry-work"; attribute :>> avoided="Input conversion/cleanup is outside the SFUN_ERROR retry loop"; attribute :>> added="Final result retries still execute and may allocate"; attribute :>> condition="Existing behavior already avoids repeated input conversion; do not count as new speedup"; }
part gain2:GainRow { attribute :>> key="split-retirement"; attribute :>> avoided="Owner can settle while captured foreign payload and code remain live"; attribute :>> added="Separate payload/destructor image lease until final real use"; attribute :>> condition="Avoid owner-waits-GC and GC-waits-native-owner dependency by design; no general liveness theorem"; }
part gain3:GainRow { attribute :>> key="remove-wrappers"; attribute :>> avoided="One generated ConverterUsePlan can replace repeated macro-time cleanup inference"; attribute :>> added="Type graph, aliases, custom converter effects and stable failure custody"; attribute :>> condition="Old C macro paths retire only after complete generator/consumer equivalence"; }
part gain4:GainRow { attribute :>> key="failure-custody"; attribute :>> avoided="Retain known native pointer on unknown destructor disposition"; attribute :>> added="Stable attempted-allocation and callback-effect records; unknowns may retain indefinitely"; attribute :>> condition="Legacy release_fn return values and cleared fields are not reliable disposal receipts"; }
part gain5:GainRow { attribute :>> key="quantities"; attribute :>> avoided="For E owner entries with a admitted nontrivial arguments, at most aE native argument-drop obligations on a fully successful path"; attribute :>> added="Transfer/retry guards and per-resource metadata; dynamic E and a must be measured later"; attribute :>> condition="Builtin macro families count=116 total conversion pairs; no measured runtime reduction"; }
part gain6:GainRow { attribute :>> key="modern-C"; attribute :>> avoided="C23 can represent separate native use, Scheme reachability and destructor completion"; attribute :>> added="Same semantic support is required with Zig"; attribute :>> condition="No Zig-specific benefit or time/byte speedup established"; }
part def MemoryRow { attribute key:String; attribute publication:String; attribute observation:String; attribute obligation:String; }
part memory0:MemoryRow { attribute :>> key="private-copy"; attribute :>> publication="Reserve stable attempt record before native allocation/callback-capable conversion"; attribute :>> observation="Pointer identity becomes owned record before wrapper creation can allocate or call release_fn"; attribute :>> obligation="The non-abandonable native-return-to-record window remains open; do not infer protection from a stack local"; }
part memory1:MemoryRow { attribute :>> key="wrapper"; attribute :>> publication="Publish complete tags/pointer/destructor fields before wrapper becomes scannable"; attribute :>> observation="Reload actual rooted wrapper after allocating safepoints"; attribute :>> obligation="Old wrapper initialization and C23 GC scanning order require independent source refinement"; }
part memory2:MemoryRow { attribute :>> key="input-hold"; attribute :>> publication="Record exactly one native-hold effect inside qualified GC/count exclusion"; attribute :>> observation="Commit argument ticket before entering error-handler/reply path"; attribute :>> obligation="Parent marker NoAbandon is not automatically proof for every converter/reference writer"; }
part memory3:MemoryRow { attribute :>> key="owner"; attribute :>> publication="Finalize native users then close admission and sign exact parent identity"; attribute :>> observation="Owner closure retains separate Scheme capture and destructor code leases"; attribute :>> obligation="Logical model step is not an instruction-level multi-store transaction"; }
part memory4:MemoryRow { attribute :>> key="destructor"; attribute :>> publication="Detach handler under stable task and pinned code before callback"; attribute :>> observation="Only reliable completion frees payload lease; unknown stays owned"; attribute :>> obligation="Current release_foreign clears fields but has no durable callback receipt; no safe replay follows"; }
part def PaperRow { attribute key:String; attribute title:String; attribute url:String; attribute section:String; attribute basis:String; attribute boundary:String; }
part paper0:PaperRow { attribute :>> key="gambit-primary"; attribute :>> title="Feeley: unrestricted continuation/C interoperability"; attribute :>> url="https://www.schemeworkshop.org/2000/feeley.ps"; attribute :>> section="1-5"; attribute :>> basis="Scheme frame lifetime and C dynamic extent differ; copied C state cannot replace store semantics"; attribute :>> boundary="Historical C-thread proposal unimplemented then; no timing transfer"; }
part paper1:PaperRow { attribute :>> key="gambit-pvm"; attribute :>> title="Feeley/Miller parallel VM"; attribute :>> url="https://www.iro.umontreal.ca/~feeley/papers/FeeleyMillerLFP90.pdf"; attribute :>> section="2"; attribute :>> basis="Compiler/runtime contract should carry frame and converter-use facts"; attribute :>> boundary="Not a current generated-C equivalence proof"; }
part paper2:PaperRow { attribute :>> key="ocaml-effects"; attribute :>> title="Retrofitting Effect Handlers onto OCaml"; attribute :>> url="https://anil.recoil.org/papers/2021-pldi-retroeff.pdf"; attribute :>> section="3.2;5.3"; attribute :>> basis="Cleanup needs explicit control and foreign callback boundaries"; attribute :>> boundary="Its one-shot restriction is not imported into Gambit"; }
part paper3:PaperRow { attribute :>> key="c23-draft"; attribute :>> title="WG14 N3096"; attribute :>> url="https://www.open-std.org/jtc1/sc22/wg14/www/docs/n3096.pdf"; attribute :>> section="5.1.2.4;7.13"; attribute :>> basis="Visibility and live/same-thread setjmp constraints"; attribute :>> boundary="No atomic flag makes decrement and receipt one transaction"; }
part def GroundingRow { attribute component:String; attribute producerAnchor:String; attribute paperKey:String; attribute obligationId:String; }
part grounding0:GroundingRow { attribute :>> component="control"; attribute :>> producerAnchor="no-sfun-catcher"; attribute :>> paperKey="gambit-primary"; attribute :>> obligationId="Converter-unwind"; }
part grounding1:GroundingRow { attribute :>> component="control"; attribute :>> producerAnchor="generator-wrapping"; attribute :>> paperKey="gambit-pvm"; attribute :>> obligationId="Converter-plan"; }
part grounding2:GroundingRow { attribute :>> component="resources"; attribute :>> producerAnchor="struct-fail"; attribute :>> paperKey="ocaml-effects"; attribute :>> obligationId="Converter-failure"; }
part grounding3:GroundingRow { attribute :>> component="control"; attribute :>> producerAnchor="still-dec"; attribute :>> paperKey="c23-draft"; attribute :>> obligationId="Converter-release"; }
part def NeedRow { attribute key:String; attribute kind:String; attribute path:String; attribute scope:String; part owner:Owner; }
part need0:NeedRow { attribute :>> key="Converter-formal"; attribute :>> kind="formal"; attribute :>> path="dev/refactoring/modern-c/models/lean/ConverterUse.lean"; attribute :>> scope="bounded custody model"; attribute :>> owner.componentId="control"; }
part need1:NeedRow { attribute :>> key="Converter-bridge"; attribute :>> kind="bridge"; attribute :>> path="dev/modeling/tools/sfun-converter-use-closure-projection.py"; attribute :>> scope="trusted typed IR projection"; attribute :>> owner.componentId="control"; }
part need2:NeedRow { attribute :>> key="Converter-plan"; attribute :>> kind="native"; attribute :>> path="vendor/gambit/gsc/_ptree2.scm"; attribute :>> scope="all builtin/custom converter effects, plan sealing and source lowering"; attribute :>> owner.componentId="control"; }
part need3:NeedRow { attribute :>> key="Converter-failure"; attribute :>> kind="native"; attribute :>> path="vendor/gambit/lib/c_intf.c"; attribute :>> scope="private allocation capture and reliable synchronous disposal completion"; attribute :>> owner.componentId="resources"; }
part need4:NeedRow { attribute :>> key="Converter-unwind"; attribute :>> kind="native"; attribute :>> path="vendor/gambit/lib/setup.c"; attribute :>> scope="stable subtree/native-input root handoff"; attribute :>> owner.componentId="control"; }
part need5:NeedRow { attribute :>> key="Converter-release"; attribute :>> kind="native"; attribute :>> path="vendor/gambit/lib/_mem/object-allocation.inc"; attribute :>> scope="NoAbandon and all argument/marker count writers under GC exclusion"; attribute :>> owner.componentId="control"; }
part need6:NeedRow { attribute :>> key="Converter-payload"; attribute :>> kind="native"; attribute :>> path="vendor/gambit/lib/_mem/still-sweep.inc"; attribute :>> scope="foreign destructor affinity, exact callback effects and global image lifetime"; attribute :>> owner.componentId="resources"; }
part def BindingRow { attribute actionName:String; attribute lemma:String; }
part binding0:BindingRow { attribute :>> actionName="sfun_converter_use_closure.reservePrivate"; attribute :>> lemma="ConverterUse.reservePrivatePreserves"; }
part binding1:BindingRow { attribute :>> actionName="sfun_converter_use_closure.beginWrap"; attribute :>> lemma="ConverterUse.beginWrapPreserves"; }
part binding2:BindingRow { attribute :>> actionName="sfun_converter_use_closure.wrapSuccess"; attribute :>> lemma="ConverterUse.wrapSuccessPreserves"; }
part binding3:BindingRow { attribute :>> actionName="sfun_converter_use_closure.wrapFailureReturned"; attribute :>> lemma="ConverterUse.wrapFailureReturnedPreserves"; }
part binding4:BindingRow { attribute :>> actionName="sfun_converter_use_closure.wrapFailureUnknown"; attribute :>> lemma="ConverterUse.wrapFailureUnknownPreserves"; }
part binding5:BindingRow { attribute :>> actionName="sfun_converter_use_closure.auditPrivateDisposed"; attribute :>> lemma="ConverterUse.auditPrivateDisposedPreserves"; }
part binding6:BindingRow { attribute :>> actionName="sfun_converter_use_closure.bodyBadResult"; attribute :>> lemma="ConverterUse.bodyBadResultPreserves"; }
part binding7:BindingRow { attribute :>> actionName="sfun_converter_use_closure.bodyGoodResult"; attribute :>> lemma="ConverterUse.bodyGoodResultPreserves"; }
part binding8:BindingRow { attribute :>> actionName="sfun_converter_use_closure.captureArgument"; attribute :>> lemma="ConverterUse.captureArgumentPreserves"; }
part binding9:BindingRow { attribute :>> actionName="sfun_converter_use_closure.dropInputReference"; attribute :>> lemma="ConverterUse.dropInputReferencePreserves"; }
part binding10:BindingRow { attribute :>> actionName="sfun_converter_use_closure.handlerCall"; attribute :>> lemma="ConverterUse.handlerCallPreserves"; }
part binding11:BindingRow { attribute :>> actionName="sfun_converter_use_closure.handlerBadResult"; attribute :>> lemma="ConverterUse.handlerBadResultPreserves"; }
part binding12:BindingRow { attribute :>> actionName="sfun_converter_use_closure.handlerGoodResult"; attribute :>> lemma="ConverterUse.handlerGoodResultPreserves"; }
part binding13:BindingRow { attribute :>> actionName="sfun_converter_use_closure.finishResult"; attribute :>> lemma="ConverterUse.finishResultPreserves"; }
part binding14:BindingRow { attribute :>> actionName="sfun_converter_use_closure.signFinalUse"; attribute :>> lemma="ConverterUse.signFinalUsePreserves"; }
part binding15:BindingRow { attribute :>> actionName="sfun_converter_use_closure.escapeOwner"; attribute :>> lemma="ConverterUse.escapeOwnerPreserves"; }
part binding16:BindingRow { attribute :>> actionName="sfun_converter_use_closure.drainInputFromGuard"; attribute :>> lemma="ConverterUse.drainInputFromGuardPreserves"; }
part binding17:BindingRow { attribute :>> actionName="sfun_converter_use_closure.ackExitedOwner"; attribute :>> lemma="ConverterUse.ackExitedOwnerPreserves"; }
part binding18:BindingRow { attribute :>> actionName="sfun_converter_use_closure.signEscapedUse"; attribute :>> lemma="ConverterUse.signEscapedUsePreserves"; }
part binding19:BindingRow { attribute :>> actionName="sfun_converter_use_closure.beginMarkerRelease"; attribute :>> lemma="ConverterUse.beginMarkerReleasePreserves"; }
part binding20:BindingRow { attribute :>> actionName="sfun_converter_use_closure.markerDrop"; attribute :>> lemma="ConverterUse.markerDropPreserves"; }
part binding21:BindingRow { attribute :>> actionName="sfun_converter_use_closure.commitMarkerRelease"; attribute :>> lemma="ConverterUse.commitMarkerReleasePreserves"; }
part binding22:BindingRow { attribute :>> actionName="sfun_converter_use_closure.loseReply"; attribute :>> lemma="ConverterUse.loseReplyPreserves"; }
part binding23:BindingRow { attribute :>> actionName="sfun_converter_use_closure.queryReply"; attribute :>> lemma="ConverterUse.queryReplyPreserves"; }
part binding24:BindingRow { attribute :>> actionName="sfun_converter_use_closure.dropCaptured"; attribute :>> lemma="ConverterUse.dropCapturedPreserves"; }
part binding25:BindingRow { attribute :>> actionName="sfun_converter_use_closure.beginDestructor"; attribute :>> lemma="ConverterUse.beginDestructorPreserves"; }
part binding26:BindingRow { attribute :>> actionName="sfun_converter_use_closure.destructorReturned"; attribute :>> lemma="ConverterUse.destructorReturnedPreserves"; }
part binding27:BindingRow { attribute :>> actionName="sfun_converter_use_closure.destructorUnknown"; attribute :>> lemma="ConverterUse.destructorUnknownPreserves"; }
part binding28:BindingRow { attribute :>> actionName="sfun_converter_use_closure.beginGc"; attribute :>> lemma="ConverterUse.beginGcPreserves"; }
part binding29:BindingRow { attribute :>> actionName="sfun_converter_use_closure.finishGc"; attribute :>> lemma="ConverterUse.finishGcPreserves"; }
part binding30:BindingRow { attribute :>> actionName="sfun_converter_use_closure.retireRoots"; attribute :>> lemma="ConverterUse.retireRootsPreserves"; }
part binding31:BindingRow { attribute :>> actionName="sfun_converter_use_closure.retireCode"; attribute :>> lemma="ConverterUse.retireCodePreserves"; }
part def RouteRow { attribute component:String; attribute actionName:String; attribute lemma:String; attribute producerAnchor:String; attribute obligationId:String; }
part route0:RouteRow { attribute :>> component="resources"; attribute :>> actionName="sfun_converter_use_closure.reservePrivate"; attribute :>> lemma="ConverterUse.reservePrivatePreserves"; attribute :>> producerAnchor="struct-fail"; attribute :>> obligationId="Converter-failure"; }
part route1:RouteRow { attribute :>> component="resources"; attribute :>> actionName="sfun_converter_use_closure.beginWrap"; attribute :>> lemma="ConverterUse.beginWrapPreserves"; attribute :>> producerAnchor="struct-fail"; attribute :>> obligationId="Converter-failure"; }
part route2:RouteRow { attribute :>> component="resources"; attribute :>> actionName="sfun_converter_use_closure.wrapSuccess"; attribute :>> lemma="ConverterUse.wrapSuccessPreserves"; attribute :>> producerAnchor="struct-fail"; attribute :>> obligationId="Converter-failure"; }
part route3:RouteRow { attribute :>> component="resources"; attribute :>> actionName="sfun_converter_use_closure.wrapFailureReturned"; attribute :>> lemma="ConverterUse.wrapFailureReturnedPreserves"; attribute :>> producerAnchor="struct-fail"; attribute :>> obligationId="Converter-failure"; }
part route4:RouteRow { attribute :>> component="resources"; attribute :>> actionName="sfun_converter_use_closure.wrapFailureUnknown"; attribute :>> lemma="ConverterUse.wrapFailureUnknownPreserves"; attribute :>> producerAnchor="struct-fail"; attribute :>> obligationId="Converter-failure"; }
part route5:RouteRow { attribute :>> component="resources"; attribute :>> actionName="sfun_converter_use_closure.auditPrivateDisposed"; attribute :>> lemma="ConverterUse.auditPrivateDisposedPreserves"; attribute :>> producerAnchor="struct-fail"; attribute :>> obligationId="Converter-failure"; }
part route6:RouteRow { attribute :>> component="control"; attribute :>> actionName="sfun_converter_use_closure.bodyBadResult"; attribute :>> lemma="ConverterUse.bodyBadResultPreserves"; attribute :>> producerAnchor="generator-wrapping"; attribute :>> obligationId="Converter-plan"; }
part route7:RouteRow { attribute :>> component="control"; attribute :>> actionName="sfun_converter_use_closure.bodyGoodResult"; attribute :>> lemma="ConverterUse.bodyGoodResultPreserves"; attribute :>> producerAnchor="generator-wrapping"; attribute :>> obligationId="Converter-plan"; }
part route8:RouteRow { attribute :>> component="control"; attribute :>> actionName="sfun_converter_use_closure.captureArgument"; attribute :>> lemma="ConverterUse.captureArgumentPreserves"; attribute :>> producerAnchor="generator-wrapping"; attribute :>> obligationId="Converter-plan"; }
part route9:RouteRow { attribute :>> component="control"; attribute :>> actionName="sfun_converter_use_closure.dropInputReference"; attribute :>> lemma="ConverterUse.dropInputReferencePreserves"; attribute :>> producerAnchor="release-scmobj"; attribute :>> obligationId="Converter-release"; }
part route10:RouteRow { attribute :>> component="control"; attribute :>> actionName="sfun_converter_use_closure.handlerCall"; attribute :>> lemma="ConverterUse.handlerCallPreserves"; attribute :>> producerAnchor="generator-wrapping"; attribute :>> obligationId="Converter-plan"; }
part route11:RouteRow { attribute :>> component="control"; attribute :>> actionName="sfun_converter_use_closure.handlerBadResult"; attribute :>> lemma="ConverterUse.handlerBadResultPreserves"; attribute :>> producerAnchor="generator-wrapping"; attribute :>> obligationId="Converter-plan"; }
part route12:RouteRow { attribute :>> component="control"; attribute :>> actionName="sfun_converter_use_closure.handlerGoodResult"; attribute :>> lemma="ConverterUse.handlerGoodResultPreserves"; attribute :>> producerAnchor="generator-wrapping"; attribute :>> obligationId="Converter-plan"; }
part route13:RouteRow { attribute :>> component="control"; attribute :>> actionName="sfun_converter_use_closure.finishResult"; attribute :>> lemma="ConverterUse.finishResultPreserves"; attribute :>> producerAnchor="generator-wrapping"; attribute :>> obligationId="Converter-plan"; }
part route14:RouteRow { attribute :>> component="control"; attribute :>> actionName="sfun_converter_use_closure.signFinalUse"; attribute :>> lemma="ConverterUse.signFinalUsePreserves"; attribute :>> producerAnchor="generator-wrapping"; attribute :>> obligationId="Converter-plan"; }
part route15:RouteRow { attribute :>> component="control"; attribute :>> actionName="sfun_converter_use_closure.escapeOwner"; attribute :>> lemma="ConverterUse.escapeOwnerPreserves"; attribute :>> producerAnchor="no-sfun-catcher"; attribute :>> obligationId="Converter-unwind"; }
part route16:RouteRow { attribute :>> component="control"; attribute :>> actionName="sfun_converter_use_closure.drainInputFromGuard"; attribute :>> lemma="ConverterUse.drainInputFromGuardPreserves"; attribute :>> producerAnchor="no-sfun-catcher"; attribute :>> obligationId="Converter-unwind"; }
part route17:RouteRow { attribute :>> component="control"; attribute :>> actionName="sfun_converter_use_closure.ackExitedOwner"; attribute :>> lemma="ConverterUse.ackExitedOwnerPreserves"; attribute :>> producerAnchor="no-sfun-catcher"; attribute :>> obligationId="Converter-unwind"; }
part route18:RouteRow { attribute :>> component="control"; attribute :>> actionName="sfun_converter_use_closure.signEscapedUse"; attribute :>> lemma="ConverterUse.signEscapedUsePreserves"; attribute :>> producerAnchor="no-sfun-catcher"; attribute :>> obligationId="Converter-unwind"; }
part route19:RouteRow { attribute :>> component="control"; attribute :>> actionName="sfun_converter_use_closure.beginMarkerRelease"; attribute :>> lemma="ConverterUse.beginMarkerReleasePreserves"; attribute :>> producerAnchor="release-scmobj"; attribute :>> obligationId="Converter-release"; }
part route20:RouteRow { attribute :>> component="control"; attribute :>> actionName="sfun_converter_use_closure.markerDrop"; attribute :>> lemma="ConverterUse.markerDropPreserves"; attribute :>> producerAnchor="release-scmobj"; attribute :>> obligationId="Converter-release"; }
part route21:RouteRow { attribute :>> component="control"; attribute :>> actionName="sfun_converter_use_closure.commitMarkerRelease"; attribute :>> lemma="ConverterUse.commitMarkerReleasePreserves"; attribute :>> producerAnchor="release-scmobj"; attribute :>> obligationId="Converter-release"; }
part route22:RouteRow { attribute :>> component="control"; attribute :>> actionName="sfun_converter_use_closure.loseReply"; attribute :>> lemma="ConverterUse.loseReplyPreserves"; attribute :>> producerAnchor="release-scmobj"; attribute :>> obligationId="Converter-release"; }
part route23:RouteRow { attribute :>> component="control"; attribute :>> actionName="sfun_converter_use_closure.queryReply"; attribute :>> lemma="ConverterUse.queryReplyPreserves"; attribute :>> producerAnchor="release-scmobj"; attribute :>> obligationId="Converter-release"; }
part route24:RouteRow { attribute :>> component="resources"; attribute :>> actionName="sfun_converter_use_closure.dropCaptured"; attribute :>> lemma="ConverterUse.dropCapturedPreserves"; attribute :>> producerAnchor="still-sweep"; attribute :>> obligationId="Converter-payload"; }
part route25:RouteRow { attribute :>> component="resources"; attribute :>> actionName="sfun_converter_use_closure.beginDestructor"; attribute :>> lemma="ConverterUse.beginDestructorPreserves"; attribute :>> producerAnchor="still-sweep"; attribute :>> obligationId="Converter-payload"; }
part route26:RouteRow { attribute :>> component="resources"; attribute :>> actionName="sfun_converter_use_closure.destructorReturned"; attribute :>> lemma="ConverterUse.destructorReturnedPreserves"; attribute :>> producerAnchor="still-sweep"; attribute :>> obligationId="Converter-payload"; }
part route27:RouteRow { attribute :>> component="resources"; attribute :>> actionName="sfun_converter_use_closure.destructorUnknown"; attribute :>> lemma="ConverterUse.destructorUnknownPreserves"; attribute :>> producerAnchor="still-sweep"; attribute :>> obligationId="Converter-payload"; }
part route28:RouteRow { attribute :>> component="resources"; attribute :>> actionName="sfun_converter_use_closure.beginGc"; attribute :>> lemma="ConverterUse.beginGcPreserves"; attribute :>> producerAnchor="still-sweep"; attribute :>> obligationId="Converter-payload"; }
part route29:RouteRow { attribute :>> component="resources"; attribute :>> actionName="sfun_converter_use_closure.finishGc"; attribute :>> lemma="ConverterUse.finishGcPreserves"; attribute :>> producerAnchor="still-sweep"; attribute :>> obligationId="Converter-payload"; }
part route30:RouteRow { attribute :>> component="resources"; attribute :>> actionName="sfun_converter_use_closure.retireRoots"; attribute :>> lemma="ConverterUse.retireRootsPreserves"; attribute :>> producerAnchor="still-sweep"; attribute :>> obligationId="Converter-payload"; }
part route31:RouteRow { attribute :>> component="resources"; attribute :>> actionName="sfun_converter_use_closure.retireCode"; attribute :>> lemma="ConverterUse.retireCodePreserves"; attribute :>> producerAnchor="still-sweep"; attribute :>> obligationId="Converter-payload"; }
part def ProofRow { attribute key:String; attribute lemma:String; }
part proof0:ProofRow { attribute :>> key="inputDropKeepsPayload"; attribute :>> lemma="ConverterUse.inputDropKeepsPayload"; }
part proof1:ProofRow { attribute :>> key="closureDischargesNativeUse"; attribute :>> lemma="ConverterUse.closureDischargesNativeUse"; }
part proof2:ProofRow { attribute :>> key="unknownPrivateHasCustodian"; attribute :>> lemma="ConverterUse.unknownPrivateHasCustodian"; }
part proof3:ProofRow { attribute :>> key="unknownEscapeNoClosure"; attribute :>> lemma="ConverterUse.unknownEscapeNoClosure"; }
part proof4:ProofRow { attribute :>> key="privateAndWrappedExclusive"; attribute :>> lemma="ConverterUse.privateAndWrappedExclusive"; }
part proof5:ProofRow { attribute :>> key="captureRetainsPayload"; attribute :>> lemma="ConverterUse.captureRetainsPayload"; }
part proof6:ProofRow { attribute :>> key="unknownDestructorKeepsCode"; attribute :>> lemma="ConverterUse.unknownDestructorKeepsCode"; }
part proof7:ProofRow { attribute :>> key="markerEffectGap"; attribute :>> lemma="ConverterUse.markerEffectGap"; }
part proof8:ProofRow { attribute :>> key="noRepeatedMarkerDrop"; attribute :>> lemma="ConverterUse.noRepeatedMarkerDrop"; }
part proof9:ProofRow { attribute :>> key="codeRetirementCut"; attribute :>> lemma="ConverterUse.codeRetirementCut"; }
part proof10:ProofRow { attribute :>> key="initialSafe"; attribute :>> lemma="ConverterUse.initialSafe"; }
part proof11:ProofRow { attribute :>> key="stepPreserves"; attribute :>> lemma="ConverterUse.stepPreserves"; }
part proof12:ProofRow { attribute :>> key="reachableSafe"; attribute :>> lemma="ConverterUse.reachableSafe"; }
part proof13:ProofRow { attribute :>> key="argumentDropIsNotDestruction"; attribute :>> lemma="ConverterUse.argumentDropIsNotDestruction"; }
part proof14:ProofRow { attribute :>> key="closureDoesNotDestroyPayload"; attribute :>> lemma="ConverterUse.closureDoesNotDestroyPayload"; }
part proof15:ProofRow { attribute :>> key="queryDoesNotRepeatDrop"; attribute :>> lemma="ConverterUse.queryDoesNotRepeatDrop"; }
part def CompositionRow { attribute key:String; attribute fromAction:String; attribute toAction:String; attribute lemma:String; attribute fromComponent:String; attribute toComponent:String; attribute sharedConstraint:String; }
part composition0:CompositionRow { attribute :>> key="copy-to-wrapper"; attribute :>> fromAction="sfun_converter_use_closure.wrapSuccess"; attribute :>> toAction="sfun_converter_use_closure.dropInputReference"; attribute :>> lemma="ConverterUse.privateAndWrappedExclusive"; attribute :>> fromComponent="resources"; attribute :>> toComponent="control"; attribute :>> sharedConstraint="Copy ownership moves to wrapper; native hold is separate"; }
part composition1:CompositionRow { attribute :>> key="input-to-retry"; attribute :>> fromAction="sfun_converter_use_closure.dropInputReference"; attribute :>> toAction="sfun_converter_use_closure.handlerCall"; attribute :>> lemma="ConverterUse.argumentDropIsNotDestruction"; attribute :>> fromComponent="control"; attribute :>> toComponent="control"; attribute :>> sharedConstraint="Input native reference released before result retry; foreign payload remains"; }
part composition2:CompositionRow { attribute :>> key="owner-to-payload"; attribute :>> fromAction="sfun_converter_use_closure.signFinalUse"; attribute :>> toAction="sfun_converter_use_closure.beginDestructor"; attribute :>> lemma="ConverterUse.closureDoesNotDestroyPayload"; attribute :>> fromComponent="control"; attribute :>> toComponent="resources"; attribute :>> sharedConstraint="Owner closure does not wait for escaped Scheme foreign object destruction"; }
part composition3:CompositionRow { attribute :>> key="unknown-to-unwind"; attribute :>> fromAction="sfun_converter_use_closure.wrapFailureUnknown"; attribute :>> toAction="sfun_converter_use_closure.signEscapedUse"; attribute :>> lemma="ConverterUse.unknownPrivateHasCustodian"; attribute :>> fromComponent="resources"; attribute :>> toComponent="control"; attribute :>> sharedConstraint="Unknown private destructor requires disposition plus native exit before closure"; }
part composition4:CompositionRow { attribute :>> key="capture-to-code"; attribute :>> fromAction="sfun_converter_use_closure.captureArgument"; attribute :>> toAction="sfun_converter_use_closure.retireCode"; attribute :>> lemma="ConverterUse.captureRetainsPayload"; attribute :>> fromComponent="control"; attribute :>> toComponent="resources"; attribute :>> sharedConstraint="Continuation/argument reachability retains native destructor code"; }
part composition5:CompositionRow { attribute :>> key="marker-to-retirement"; attribute :>> fromAction="sfun_converter_use_closure.commitMarkerRelease"; attribute :>> toAction="sfun_converter_use_closure.retireCode"; attribute :>> lemma="ConverterUse.codeRetirementCut"; attribute :>> fromComponent="control"; attribute :>> toComponent="resources"; attribute :>> sharedConstraint="Marker settlement cannot independently unload foreign destructor code"; }
part def LeafRow { attribute key:String; attribute component:String; attribute actionName:String; attribute lemma:String; attribute producerAnchor:String; attribute qualification:String; attribute boundary:String; }
part leaf0:LeafRow { attribute :>> key="input-not-destructor"; attribute :>> component="control"; attribute :>> actionName="sfun_converter_use_closure.dropInputReference"; attribute :>> lemma="ConverterUse.argumentDropIsNotDestruction"; attribute :>> producerAnchor="release-scmobj"; attribute :>> qualification="Classify actual converter END use as still native-hold decrement"; attribute :>> boundary="Do not call native payload destructor merely because argument native reference was dropped"; }
part leaf1:LeafRow { attribute :>> key="final-use"; attribute :>> component="control"; attribute :>> actionName="sfun_converter_use_closure.signFinalUse"; attribute :>> lemma="ConverterUse.closureDischargesNativeUse"; attribute :>> producerAnchor="generator-last-result"; attribute :>> qualification="All admitted converter and native-input uses drained before parent closure"; attribute :>> boundary="Unknown custom callback/native escaped alias cannot receive closure from cleanup boolean"; }
part leaf2:LeafRow { attribute :>> key="private-failure"; attribute :>> component="resources"; attribute :>> actionName="sfun_converter_use_closure.wrapFailureReturned"; attribute :>> lemma="ConverterUse.privateAndWrappedExclusive"; attribute :>> producerAnchor="struct-fail"; attribute :>> qualification="Reliable external private-disposition record, not legacy wrapper status"; attribute :>> boundary="STRUCT/UNION/TYPE failure ignores release_fn return; return alone cannot certify disposal"; }
part leaf3:LeafRow { attribute :>> key="no-abandon"; attribute :>> component="control"; attribute :>> actionName="sfun_converter_use_closure.markerDrop"; attribute :>> lemma="ConverterUse.markerEffectGap"; attribute :>> producerAnchor="still-dec"; attribute :>> qualification="Exclude collector/count writers and non-local exit through decrement and receipt"; attribute :>> boundary="Source-only leaf purity is not effective native qualification"; }
part def ContractRow { attribute fromNode:String; attribute toNode:String; attribute custody:String; }
part contract0:ContractRow { attribute :>> fromNode="ConverterUsePlan"; attribute :>> toNode="Stable_Private_Copy"; attribute :>> custody="resolve direction and actual cleanup effects; pin plan and code"; }
part contract1:ContractRow { attribute :>> fromNode="Stable_Private_Copy"; attribute :>> toNode="Successful_Foreign_Wrapper"; attribute :>> custody="publish tags, pointer and release function; hand off private copy"; }
part contract2:ContractRow { attribute :>> fromNode="Stable_Private_Copy"; attribute :>> toNode="Wrapper_Allocation_Failure"; attribute :>> custody="synchronous release_fn can run before conversion returns"; }
part contract3:ContractRow { attribute :>> fromNode="Wrapper_Allocation_Failure"; attribute :>> toNode="Unknown_Private_Custody"; attribute :>> custody="unknown"; }
part contract4:ContractRow { attribute :>> fromNode="Wrapper_Allocation_Failure"; attribute :>> toNode="Verified_Private_Disposition"; attribute :>> custody="disposed"; }
part contract5:ContractRow { attribute :>> fromNode="Successful_Foreign_Wrapper"; attribute :>> toNode="Body_and_First_Result"; attribute :>> custody="input hold"; }
part contract6:ContractRow { attribute :>> fromNode="Body_and_First_Result"; attribute :>> toNode="Input_Reference_Drop"; attribute :>> custody="END conversion scopes before SFUN_ERROR"; }
part contract7:ContractRow { attribute :>> fromNode="Input_Reference_Drop"; attribute :>> toNode="Error_Handler_Result_Retries"; attribute :>> custody="no repeated input conversion; same live marker"; }
part contract8:ContractRow { attribute :>> fromNode="Error_Handler_Result_Retries"; attribute :>> toNode="Final_Native_Use"; attribute :>> custody="terminal result; admitted native/cleanup users drained"; }
part contract9:ContractRow { attribute :>> fromNode="Final_Native_Use"; attribute :>> toNode="OwnerUseClosureReceipt"; attribute :>> custody="sign exact parent owner/final epoch; payload lifetime stays separate"; }
part contract10:ContractRow { attribute :>> fromNode="OwnerUseClosureReceipt"; attribute :>> toNode="Marker_Settlement"; attribute :>> custody="NoAbandon GC/count exclusion; physical effect precedes receipt"; }
part contract11:ContractRow { attribute :>> fromNode="Successful_Foreign_Wrapper"; attribute :>> toNode="Scheme_Capture_and_Payload"; attribute :>> custody="Scheme roots"; }
part contract12:ContractRow { attribute :>> fromNode="Marker_Settlement"; attribute :>> toNode="Payload_Retirement_Join"; attribute :>> custody="native owner done is only one fact"; }
part contract13:ContractRow { attribute :>> fromNode="Scheme_Capture_and_Payload"; attribute :>> toNode="Payload_Retirement_Join"; attribute :>> custody="last Scheme/capture use closes independently"; }
part contract14:ContractRow { attribute :>> fromNode="Payload_Retirement_Join"; attribute :>> toNode="Foreign_Destructor_Task"; attribute :>> custody="pin code; current GC callback rules need qualification"; }
part contract15:ContractRow { attribute :>> fromNode="Foreign_Destructor_Task"; attribute :>> toNode="Unknown_Destructor_Custody"; attribute :>> custody="cleared fields do not prove callback completion"; }
part contract16:ContractRow { attribute :>> fromNode="Foreign_Destructor_Task"; attribute :>> toNode="Descriptor_Grace"; attribute :>> custody="only reliable callback completion plus global owners permit image retirement"; }
part source33:SourceRow { attribute :>> key="parent-actual-guard"; attribute :>> path="dev/refactoring/modern-c/models/lean/SfunOwnerAst.lean"; attribute :>> needle="def signLocalClosureGuard"; attribute :>> obligation="actual typed parent guard, source hash pinned to parent receipt"; }
part proof16:ProofRow { attribute :>> key="normal-cut-ready"; attribute :>> lemma="ConverterOwnerBridge.normalCutInputs"; }
part proof17:ProofRow { attribute :>> key="normal-cut-parent-guard"; attribute :>> lemma="ConverterOwnerBridge.actualParentGuard"; }
part proof18:ProofRow { attribute :>> key="normal-cut-owner-identity"; attribute :>> lemma="ConverterOwnerBridge.parentClosesSameUse"; }
part composition6:CompositionRow { attribute :>> key="actual-parent-normal-cut"; attribute :>> fromAction="sfun_converter_use_closure.finishResult"; attribute :>> toAction="sfun_converter_use_closure.signFinalUse"; attribute :>> lemma="ConverterOwnerBridge.actualParentGuard"; attribute :>> fromComponent="control"; attribute :>> toComponent="control"; attribute :>> sharedConstraint="Adapter satisfies the actual parent signLocalClosure guard; normal cut only, no full transition or code-retirement simulation"; }
part def InventoryRow { attribute key:String; attribute direction:String; attribute endEffect:String; attribute count:String; attribute actionName:String; attribute lemma:String; attribute sourceAnchor:String; }
part inventory0:InventoryRow { attribute :>> key="input-native-drop"; attribute :>> direction="C-to-Scheme"; attribute :>> endEffect="native-reference-drop"; attribute :>> count="43"; attribute :>> actionName="sfun_converter_use_closure.dropInputReference"; attribute :>> lemma="ConverterUse.argumentDropIsNotDestruction"; attribute :>> sourceAnchor="arg-int-end"; }
part inventory1:InventoryRow { attribute :>> key="input-close-only"; attribute :>> direction="C-to-Scheme"; attribute :>> endEffect="close-only"; attribute :>> count="15"; attribute :>> actionName="sfun_converter_use_closure.finishResult"; attribute :>> lemma="ConverterUse.closureDischargesNativeUse"; attribute :>> sourceAnchor="arg-char-end"; }
part inventory2:InventoryRow { attribute :>> key="result-empty-end"; attribute :>> direction="Scheme-to-C"; attribute :>> endEffect="empty-end"; attribute :>> count="58"; attribute :>> actionName="sfun_converter_use_closure.finishResult"; attribute :>> lemma="ConverterUse.closureDischargesNativeUse"; attribute :>> sourceAnchor="result-struct-end"; }
part source34:SourceRow { attribute :>> key="size-end-no-drop"; attribute :>> path="vendor/gambit/include/_gambit/foreign_conversion.h.in"; attribute :>> needle="#define ___END_SFUN_SIZE_T_TO_SCMOBJ(c,s,i)}"; attribute :>> obligation="close-only END is not proof of nonallocating conversion"; }
part source35:SourceRow { attribute :>> key="size-delegates-u64"; attribute :>> path="vendor/gambit/lib/c_intf.c"; attribute :>> needle="return ___U64_to_SCMOBJ (___ps, ___U64_from_ULONGLONG (___CAST(___ULONGLONG,x)), obj, arg_num);"; attribute :>> obligation="size_t conversion delegates to potentially boxed integer converter"; }
part source36:SourceRow { attribute :>> key="signed-size-delegates-s64"; attribute :>> path="vendor/gambit/lib/c_intf.c"; attribute :>> needle="return ___S64_to_SCMOBJ (___ps, ___S64_from_LONGLONG (___CAST(___LONGLONG,x)), obj, arg_num);"; attribute :>> obligation="ssize_t and ptrdiff_t use the same potentially allocating converter"; }
part source37:SourceRow { attribute :>> key="boxed-integer-allocation"; attribute :>> path="vendor/gambit/lib/c_intf.c"; attribute :>> needle="r = ___alloc_scmobj (___ps, ___sBIGNUM, n<<3);"; attribute :>> obligation="out-of-fixnum branch allocates a Scheme object"; }
part source38:SourceRow { attribute :>> key="converter-release-contract"; attribute :>> path="vendor/gambit/lib/c_intf.c"; attribute :>> needle="call to '___release_scmobj' when the caller no longer needs a"; attribute :>> obligation="local documented caller obligation for non-null processor still conversions"; }
part profile3:ProfileRow { attribute :>> key="size-family-hold-balance-gap"; attribute :>> repeatable="out-of-fixnum values may allocate native-held bignums"; attribute :>> actionName="sfun_converter_use_closure.dropInputReference"; attribute :>> lemma="ConverterUse.closureDischargesNativeUse"; attribute :>> producerAnchor="size-end-no-drop"; attribute :>> boundary="size_t/ssize_t/ptrdiff_t close-only END cannot automatically discharge boxed native hold; conditional source mismatch, no native leak run"; }
part need7:NeedRow { attribute :>> key="Converter-size-balance"; attribute :>> kind="native"; attribute :>> path="vendor/gambit/include/_gambit/foreign_conversion.h.in"; attribute :>> scope="effective native type range, fixnum width and complete alternate-release audit before claiming size-family hold balance"; attribute :>> owner.componentId="control"; }
part gain7:GainRow { attribute :>> key="boxed-size-hold"; attribute :>> avoided="Candidate removes B unintended native holds for B boxed size-family argument conversions if no alternate release exists"; attribute :>> added="Owned-result status or correct generated drop, GC/writer exclusion and exact boundary validation"; attribute :>> condition="Conditional source accounting only: native type must admit out-of-fixnum values, non-null processor must allocate still objects, and no other owner may be charged for that reference; no measured bytes/time or native leak claim"; }
part source39:SourceRow { attribute :>> key="size-registered-builtin"; attribute :>> path="vendor/gambit/gsc/_parms.scm"; attribute :>> needle="(cons size_t-sym"; attribute :>> obligation="real named size_t builtin maps to SIZE_T_TO_SCMOBJ with cleanup flag false; ssize_t/ptrdiff_t follow"; }
part contract17:ContractRow { attribute :>> fromNode="ConverterUsePlan"; attribute :>> toNode="Builtin_Size_Family"; attribute :>> custody="qualified type and value range"; }
part contract18:ContractRow { attribute :>> fromNode="Builtin_Size_Family"; attribute :>> toNode="Close_Only_END"; attribute :>> custody="current END has no drop"; }
part contract19:ContractRow { attribute :>> fromNode="Builtin_Size_Family"; attribute :>> toNode="Boxed_Still_Result"; attribute :>> custody="64-bit converter may allocate"; }
part contract20:ContractRow { attribute :>> fromNode="Close_Only_END"; attribute :>> toNode="Size_Hold_Balance_Gap"; attribute :>> custody="no drop"; }
part contract21:ContractRow { attribute :>> fromNode="Boxed_Still_Result"; attribute :>> toNode="Size_Hold_Balance_Gap"; attribute :>> custody="held"; }
part contract22:ContractRow { attribute :>> fromNode="Size_Hold_Balance_Gap"; attribute :>> toNode="Native_Admission_Blocker"; attribute :>> custody="target and alternate-release audit open"; }
}
