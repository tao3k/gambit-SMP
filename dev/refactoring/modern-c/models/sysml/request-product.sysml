package GambitRequestProduct {
 private import ScalarValues::*;
 attribute sdkModelAuthority:String="Use the existing official opensysml Python SDK and source-bound process custody. Parse_sources strict/strict_conformance, native Model.find/Symbol.children and Model.eval own field selection and values. SDK auto-start/download disabled. CLI projection remains an independent historical reference, not the Python model parser. The pre-change six-model/61-field SDK comparison passed on pinned servicev0.10.1. Typed field equality does not establish native runtime or whole-product admission.";
 attribute compilerClosurePlan:String="One integrated prerequisite chain: audit original host-layout authority; complete Scheme semantic HostGraph and explicit physical host/unit ownership; prove PointId/FrameSpec/root/tail/multi-shot preservation for affected mixed-host edges; produce same-profile generation/native/link witnesses; then resume the three dependent Gerbil modules and whole consumers. Native job overlap and private SSI publication do not divide a single C host. Do not run another full Make attempt until a source-bound change or independently completed exact product can alter the critical path. Do not substitute a profile variant, a generated C file, a stale object or an exit-zero diagnostic for a complete module.";
 attribute compilerPhaseEvidence:String="Historical1b387add/7308a00f evidence only; no d07f67b4 consumer admission follows. Same-profile source bootstrap508.827736s and scoped native frame/tail/multi-shot controls passed. The native build-spec census declares326 targets. That historical official stdlib consumer naturally exits0 in464.354609s, reusing323 module programs and completing the remaining3. All326 declared source identities match complete module records. Its first subsequent initialization-planning attempt failed because historical native candidates overwrote complete-program hashes; that failure is retained. After separating admissions,326 views are issued and libgerbil reaches original static SCM-to-C generation before its120.019055s timeout. The source unconditionally recompiles each static unit; per-unit completion custody is the next open boundary, not another graph-planning failure. Downstream libgerbil/lang/tools and matched release/build remain separate open gates. The bounded1s GC sample occurred before fresh pending modules completed: it is not a warm/no-change baseline or whole-wall causal attribution.";
 attribute compilerBoundaryAudit:String="The existing GambitModernCCommitAdmission::compilationUnit already owns unbounded-host source refinement. Historical pre-host-unit connection~1 exposes that architectural dependency:12820 labels,205 emitted procedure sections,21867016 C bytes and configured single-host limit0. Source configure.ac explicitly defines0 as unlimited. Do not treat this as a new discovery or silently change the profile. Existing HostGraph/FrameSpec/PointId, cross-host tail transfer, roots and multi-shot obligations govern a structural replacement. Compiler-host modernization is not another scheduler setter or cleanup patch.";
 attribute moduleNativeAcceptance:String="Historical1b387add/7308a00f completes326 stdlib programs,740 static units and the four original Make consumers. Current d07f67b4 has47 scoped native checks and complete interpreted408-case cost samples; its exact runtime has independently relinked and executed Gerbil stage1-bach in139.824s. Current d07/987c59dd stdlib/libgerbil/lang/tools now naturally complete with326 programs,326 views and740 static units; see shared-slot-consumer-custody.json. No historical binary is restamped. Original GSC censoring/common failure and unqualified comparative cold cost remain explicit.";
 attribute moduleNativeMatrix:String="Historical source periods retained below; current d07f67b4 consumer custody is recorded in shared-slot-consumer-custody.json and is not whole-product acceptance.\n| Responsibility | Removed work / ambiguity | Added cost | Qualification |\n|----------------+--------------------------+------------+---------------|\n| Metadata query | Cached identity and graph queries do not import native macro phases | Credential validation and original fallback | Real reader/import negative control passed; full product open |\n| Module native jobs | Global deferred completion cannot publish a module early; safe phase jobs can overlap | Per-module requests, threads under existing five-core quota; peak unmeasured | Actual original gxc overlap and raised-false drain passed |\n| Interface publication | SSI bytes cannot stand in for completed native work | Private interface storage and final rename | Source checked; whole consumer still open |\n| Admission | Repeated byte reads share one preparation snapshot; old native timestamps do not trigger Scheme regeneration | Per-preparation stat/hash records, mutation refusal | Framework controls pass; no matched latency claim |\n| Planning admission | Old native candidate history cannot overwrite complete module hashes | Revalidate whole module witnesses and all source/dependency identities |326 admitted,0 rejected; downstream pending |\n| Static native units |736 of740 compiler invocations avoided in the observed library run; closed units survive failed parents | Per-request identity, native effect qualification, dependency hashing, output claims and immutable receipts |740 closed;4 executed;0 unfinished; library natural exit51.450285s is not a matched speedup |\n| Consumer lifetime | Complete-program lease covers library, lang and tools; original compiled caller resolves the activated entry | Scope restoration, exact source inverse and catalogue/driver binding checks | Actual lang module protocol passes; tools remains blocked |\n| Compiler identity roles | Downstream products cannot spuriously invalidate the unchanged compiler host | Native114-host/34-target classification and full effective-input equality | Original58fe43 producer retained; no old files restored or products relabeled |\n| Same-source AOT service | Repeated driver source activation can use a witnessed native object | One observed18.619132s original build plus7.685908s native protocol smoke; Adapter source is part of its production fingerprint; current contract requalification builds once in16.0774s and runs the real smoke in5.0637s; a second same-identity admission issues no new service producer | Service readiness passes; whole tools still reaches native registration limit |\n| Full release/build | No claimed whole-result saving | Latency / peak unmeasured until consumers finish | OPEN |";
 attribute moduleNativeEvidence:String="evidence/research/retained/modern-c/request-product/initializer-view.json and initializer-view-matrix.json bind actual source, native property/real-SSI controls, graph-view derivations,119-root installed planning, fixed bounds and failed histories. Native initializer projections are separately journal-witnessed and cached by semantic input bytes plus transformation contract. Unknown writers cannot issue a view. Closed prefixes survive failed parents without granting native/module completion. generation-planning.json and generation-planning-matrix.json bind the installed prefix reader/coordinator,192 native cases,102 framework checks and the unchanged producer context. catalog-target-closure.json and catalog-target-closure-matrix.json bind the actual326-target native census, exact complete-program source set, natural stdlib exit, catalogue read/activation controls and corrected historical311 interpretation. Every result retains its executionInputs; current hashes do not restamp older native checks. static-unit-evidence.json and static-unit-matrix.json retain actual per-unit requests, completions, exact reuse, header/source qualification, framework fixes and failed parents. Historical semantic-context/library-order packets retain their original source periods.";
 attribute moduleNativeRefinement:String="Existing incremental_build.qnt owns dependency readiness, task completion and failure custody. Private interface writes and job collection are not publish/reuse. Native job completion precedes interface publication; only a stable complete module witness may enable downstream reuse. The C/GC and frame representation obligations remain in their existing Lean scope, with no duplicate temporal model. Source refinement must justify parameter inheritance, distinct native outputs, stable generated inputs, drain on exceptions and original-quota accounting. A producer-role inverse permits old complete programs only because generation and argv/cwd are unchanged; every actual generated input and dependency remains hashed. Static units use the existing incremental_build.qnt start/finish/publish/reuse separation: original process-status and close precede completion, quiescent identity and header checks precede an immutable receipt, and an authenticated source-effect-qualified transport alone permits reuse. Unknown native writers and failed whole parents remain distinct. Closed generation metadata refines only dependency readiness followed by start in models/build/incremental_build.qnt, never reuse or finish. Actual native joins and stable publication remain the only completion edge. Catalogue-only metadata reads must preserve the original driver binding; actual native writes activate the original source compiler under the existing import mutex. Initialization planning must not re-admit stale native request history over complete-program ownership. Native overlap and raised-false draining are scoped implementation tests, not whole Make or peak-memory proof.";
 attribute moduleNativeOwnership:String="IMPLEMENTED current d07f67b4/987c59dd has326 independently witnessed complete programs and naturally completed official stdlib/libgerbil/lang/tools parents. Historical1b387add/7308a00f retains its own observations. This does not close whole downstream acceptance. Planning requalifies complete module programs only; historical native candidates belong to compiler-stage admission and must not overwrite a current complete module hash. Original gxc queue/quota owns native requests. SSI remains private until native joins and source/dependency checks close. Closed managed generations enable only original dependency waits and native continuation, never public SSI or module completion.";
 attribute requiredAcceptanceParts:String="ownerExitRequirement;productRequirement;releaseRequirement";
 ref part result=GambitModernCOutcomes::execution;
 ref part sourceDelivery=GambitPendingCuts::schedulerDelivery;
 attribute queryAssurance:String="The Python repository_clues and evidence_views.evaluate entries return assurance: native ASCENT inference completion; checked byte identities or partial reference coverage; caller-declared premises whose truth is not established by attestation; and native execution not established by query. Source-bound branch_evidence.progress is a separate terminal-process and contract validator. Incomplete inference raises; missing or changed inputs cannot receive a completed-view assertion. The registered recorded-cases reference validator recomputes terminal consistency from the same hashed bytes and returns scoped case counts; it does not authenticate a declaration or replay a program. Org is navigation only. No confidence score or query-success-to-runtime-admission conversion. The recorded-cases validator additionally recomputes the guarded compiler product inventory, joins the88 admitted tasks to old/new request tuples and verifies10 actual hits/78 changed inputs plus parent failure. It rejects inflated hits, false completion, frontend reuse and unknown parent custody. This is consistency verification, not process authentication.";
 attribute evidenceChain:String="Canonical machine-readable integration is evidence/research/retained/modern-c/request-product/owner-closure-acceptance.json: integration.requirements is selected from requiredAcceptanceParts by native SysML; integration.answers is recomputed by the real ASCENT engine; integration.evidenceIdentities binds repository JSON bytes. Cached ready answers cannot grant admission. Gerbil history records original stage1 failures, official BACH success163.746s, real p1/p2 map/wind/GC success and stdlib timeout573.531s. gerbil-consumer-history.json retains actual compiler/make source and unfinished phase inventory; gerbil-map-consumer.json is independently terminal-validated. compiled-release.json records32 successful compiled/exec cases; compiled-release-matrix.json carries10 quantitative rows. None certifies complete downstream construction. No matched baseline consumer exists, so timeout causality remains unresolved. evidence/scenarios/modern-c/request-product.view.json uses existing evidence_views and repository_clues Python APIs with the shared ASCENT Library. Exact candidate-tree, profile observation and selected working-source hashes are distinct. Historical committed-branch qualification remains separate. Changed reference denies the view; recorded observations never grant runtime admission. The original input bytes reconstruct exactly from the existing committed Bazel fixture plus its existing C23 goal overlay; the unrelated configuration document is not that input. gerbil-compiler-completion.json and its normalized five-row matrix bind native completion and exact-context reuse separately from whole producer success; compilerProducts is independently recomputed by the existing Python Evidence validator used by ASCENT. All original failed histories remain failed.";
 attribute nativeCompletion:String="The existing Make worker owns one complete module program: source request, actual GSC child completions, all emitted SSI/SSXI/static/native phase files, and an unchanged imported-artifact snapshot. Python publishes only after parent reaping and process-group quiescence, through the existing execution journal. A ready credential authorizes importing that same complete interface and phase cohort. Raw frontend files, a bare native output, an unfinished task or an unknown parent cannot authorize reuse. GCC-MD header identities and original invoke argv/cwd remain part of native task completion. The issuer independently requires quiescence and requires every native input to be an owned emitted module output. A failed parent remains failed even when complete child module programs survive.";
 attribute nativeReuseBoundary:String="Historical phase-only continuation admitted88 and reused10:78 generated inputs changed. Repository gerbil-generated-input-causes.json records32 clock,45 lexical-identity and1 native-debug-source mark-order witnesses. Complete managed module programs preserve those identities together; no text normalization. The earlier source adapter imported saved complete interfaces only from a dependency-closed journal-backed cohort. That historical same-context continuation admitted105, consumed58 programs and avoided170 GSC/native tasks, then failed after101.450s at std/struct/lru~1. A separate actual counter observation reached exactly20000 global slots from12196 before loading. No stdlib/downstream completion or full release/build gain follows. This is official Make incremental policy plus frozen producer/owned/dependency inputs, not arbitrary macro/eval/native-I/O clean-build equivalence. Unmanaged initialization and unresolved provider identities prohibit reuse.";
 attribute metadataPlanning:String="The real semantic producer owns rich initialization graphs; a separately witnessed pure Scheme projection preserves actual context/phase identities while contracting initializer-visible wrappers and duplicates; original order-modules consumes compact slot views. No macro phase executes for metadata-only planning. Historical58fe43 observations remain source-bound. The new runtime ABI produces context7308a00f,326 complete module programs and326 derived views; original stdlib/libgerbil/lang/tools now naturally complete. Actual compilation retains lexical/phase activation. A derived view never authorizes native/module completion; arbitrary macro/eval/native-I/O clean-build equivalence remains outside this contract.";
 attribute metadataEvidence:String="[[file:../../../evidence/research/retained/modern-c/request-product/gerbil-make-metadata-consumers.json][Official Make histories and joined module witnesses]], [[file:../../../evidence/research/retained/modern-c/request-product/gerbil-metadata-consumers-matrix.json][Measured work and unmeasured whole-product costs]], and [[file:../../../evidence/research/retained/modern-c/request-product/gerbil-metadata-planning.json][Checked source query contract]] are repository evidence. The actual p1 reader control separates a non-activating identity read from an import that raises BODY-ACTIVATED, checks std/values identity and custom-reader fallback; gerbil-make-reader-contract.json retains the default-processor heap failure and the original stderr collector assertion separately. No whole product follows. Failed parents remain failed. Raw observed Make source and its exact producer projection are retained in adjacent source evidence files.";
 attribute metadataRefinement:String="Source-role projection is explicit: the run freezes the observed full Make bytes; only the exact checked identity/timestamp/closed-generation planning query adapter is removed from the generator fingerprint. Every other byte, tool/provider, argv/cwd and generated input remains bound. The Make library target retains its own full source identity and freshness check; dependent library snapshots still invalidate. Unknown adapter edits refuse projection. This is not arbitrary macro/native-I/O hermeticity or a clean-build equivalence theorem. Existing incremental_build.qnt owns deps-ready reuse, completion custody and fault5 redundant-build histories. Source refinement must show metadata reads do not grant completion, a closed prefix selects the ordinary ready/start path rather than reuse/finish, saved metadata retains the same dependency edges, and readiness is not invalidated by borrowed older timestamps. The historical31 duplicate rebuilds expose an enabledness/refinement defect, not a new Lean schedule obligation. Lean keeps existing spatial/frame obligations; no duplicate model.";
 attribute nativeGlobalCapacity:String="Historical official stdlib continuation failed during completion-table preparation: the old module-id called import/mx, whose saved SSI activated compiled macro phases. The native global count grows12196 to exactly20000. Both baseline3d42 and candidate runtime load the exact same saved object at a deliberately saturated table and return ___IMPL_LIMIT_ERR; this is a matched boundary control, not full baseline Gerbil-history reproduction. Whole-build planning and macro activation are mixed responsibilities. A complete validated module program already supplies dependency metadata: the next replacement must let existing Make consume checked module identity/dependency edges without activating cached macro code. Actual compilation still owns phase/lexical activation. Unknown credentials or dependencies must use the original qualified path, never guessed edges. Do not raise ___GLOBALS_CAPACITY or change the profile. The metadata-consumer replacement is now source-implemented and syntax-checked; its producer/consumer identity refinement, extra-input/output checks and full downstream tests remain required. Existing QNT owns scheduling/custody histories; native source refinement owns actual Make edges and C addressability; no duplicate Lean temporal model.";
 attribute nativeCompletionMatrix:String="Historical pre-storage ABI observations only; current outcomes are in global-storage Evidence.\n\n| Scope | Actual evidence | Added cost / remaining boundary |\n|-------+-----------------+--------------------------------|\n|78 regenerated inputs |32 clocks;45 lexical IDs;1 mark order | Observed mechanisms, not exhaustive token equivalence |\n| Coherent cold module attempt |314 native completions;106 programs;105 eligible |530.989s timeout;5 modules unfinished |\n| Same-context continuation |105 admitted;58 consumed;170 native tasks avoided;0 newly executed |101.450s failed at compiled macro phase load |\n| Failure diagnosis |12196 to exactly20000 global bindings |72.366s separate native diagnostic; no heap/capacity increase |\n| Saved macro control | Cold3GSC; two later consumers each0GSC and result42 | Focused control only |\n| Framework |45 tests pass; negative controls reject inflated counts and partial/unknown completion | Not native/full product acceptance |\n| Retained storage |315 source snapshots19362273bytes;105 module records3611588bytes | File bytes only, not RSS or peak |\n| Whole consumers | stdlib failed; libgerbil/lang/tools not complete | Whole release/build and4/4 remain blocked |\n";
 attribute catalogue:String=GambitPendingCuts::schedulerDelivery.audit;
 attribute scope:String="One complete fourth Modern C runtime replacement on vendor modern-c, based on3d42cc5b. Canonical candidate d07f67b4 has current native service/wait/FIFO/continuation controls and a complete326-program/740-unit Gerbil consumer chain. Source attribution retains common numeric debt; matched-release scope remains open. Historical8f/1b/0ec results retain their own identities. No repair-line progress or fragmented commit.";
 attribute priorityWork:String="Scheme priority-update owns STRUCTURE-tagged ticket fields, R+7 private F64 words and ordinary GC-traced graph vectors. Conversion/allocation precede leases. Full unique thread/queue acquisition validates identities and capacity. Solve all keys privately, publish each once, reposition actual BTQ/TOQ, release, clear borrowed roots and retire the plan. Generated direct-call witness scanning rejects boxing, checks, polling and unknown Scheme jumps; it is not a general C proof.";
 attribute propagationCustody:String="The public Scheme base/boost payload remains IEEE, including NaN. Every managed effective-key producer maps NaN to ordered bottom -Infinity before publication. Discovery follows one owner edge per thread, yielding a prefix and at most one cycle. Frozen external queue keys supply constants; planned waiters are excluded to prevent stale self-support. Compute prefix joins then the single cycle join privately, commit each node once. No after-publication owner retry, allocation, polling or exception cut. Retired plans cannot reacquire former graph roots.";
 attribute needClosure:String="3/3; final source/commit five-gate admission pending";
 attribute status:String="FUNCTIONAL_AND_DECLARED_COST_POPULATIONS_CLOSED; architecture3/4 pending whole REV admission; independent SMP1/12; matched cold build is a separate follow-up with no acceleration claim.";
 attribute ownership:String="One existing intrusive request vector stores immutable target/thunk/completion separately from state/result; it allocates no companion service record. Both high-level interrupt and restored-thread entry use one dispatcher and one service claim. The completion mutex retains wait/target-death semantics; it supplies no mutable routing identity.";
 attribute publication:String="One shared ordered-word interface covers ticket ownership, global publication and collective stamps. Ticket reservation is not ownership: the successful polling load acquires and unlock releases. Collective sender-private payload precedes release stamp; every fast receive acquires then copies payload before reset. A reverse tree message, not the local EMPTY flag alone, closes payload reuse within a fixed admitted population. Resource construction/destruction and population change remain separate source-refinement obligations.";
 attribute continuation:String="Scheduler THREAD_RESTORE still installs the logical suffix before service; that macro does not itself execute/copy its frames. The service resume closure reparks without returning through the break handler into the old mutex retry. Arbitrary user captures retain that full suffix. Native p1/p2 checks restore it3 times after the original target ends, with GC, balanced dynamic-wind, persistent parameter update and fresh current-thread registration; no one-shot restriction.";
 attribute fifo:String="Publish a single mailbox identity under the thread lock, allocate detached message cell before acquiring mutation permit, link initialized cell under that permit, synchronize every selective cursor read/write and release before timeout conversion. Rooted cell and request fields remain covered by ordinary generated Scheme frame maps.";
 attribute cQueue:String="C producer/consumer preserves intrusive vector slot0. get-next removes source head/tail and clears claimed node next under the same processor lock before returning. The thread-queue pop already clears next. A rerouted node must own no suffix of its previous queue; no side observer or validation check substitutes for this transfer.";
 attribute costs:String="Each actually contended mutex/join/sleep wait introduces one ordinary continuation header and one self-resume closure. The removed prototype scope vector is not part of this candidate. Internal header.denv is #f like existing Thread.cont: it is a private GC-traced frame root, never a public graftable continuation. User captures retain their full denv and dynamic-wind. Other captured frame values may still retain old parameter graphs. C THREAD_PARK allocates and copies zero payload words; the function-value fallback copies a header and binds it to the current Thread denv before graft. Exact allocated bytes, retained reachability and peak RSS require measurement.";
 attribute waitControlGap:String="Source replacement covers all original wait classes without imposing one semantic rule: mutex/join/sleep preserve durable owner/end/deadline predicates and re-register the same caller suffix. CV and I/O explicitly return interrupted-wait action #t, as the original void-normalization contract already did; that is no signal or readiness credit. I/O retains its post-wake interrupt check and caller read retry. Yield and reschedule retain THREAD_SAVE because they save actual running program state. Final kind-specific native evidence and full composition remain admission obligations.";
 attribute saveCostBoundary:String="Source correction: ___THREAD_SAVE itself stores return/frame links into the already-created Thread.cont; macro-make-thread-cont allocates that header at thread initialization. ___THREAD_RESTORE consumes the frame link, also without allocating a new continuation object. They must not be counted as fresh heap captures. Actual frame copying occurs in the _kernel.scm break handler when overflow undo is unavailable or the caller frame is heap-resident, and GC continuation-roots.inc materializes/marks saved frame chains. The unresolved service/wait refinement must identify these actual copies and roots; blindly eliminating a macro invocation or adding a retained snapshot does not prove lower work or memory.";
 attribute waitRefinement:String="Allocation occurs after initial lock release and before queue-registration locks. The hidden capture header drops denv, retaining its GC-repaired caller frame. THREAD_PARK first invalidates overflow undo, sets FP to the context break, writes the same frame to break.Next and Thread.cont, and sets R0 to the break handler; no safepoint intervenes. The callback receives the current live Thread, never the terminated original physical target. Registration acquires the original resource/Thread/processor lock order and rechecks the durable predicate before enqueue. Real completion consumes physical Thread.cont through THREAD_RESTORE; it does not consume a retained user continuation. Absolute timeout objects are not recomputed after service or late reentry.";
 attribute formalDuty:String="Reuse existing wait lifecycle, sync_message_acquire, sync_atomic_round_publication, sync_slot_retained_resources and gc_sync_membership models. Existing retained-resource/membership checks add2 positive and7 expected violating bounded simulations using32 samples/60 steps/seed173. Source masks and native libc failure counts refine construction, not arbitrary C memory or queue policy. Native-reader callsite coverage is not a permit proof. No new duplicate Lean schedules.";
 attribute unresolved:String="Current d07f67b4/987c59dd naturally completes stdlib/libgerbil/lang/tools with326 complete programs,326 views and740 static units. Original408-file GSC remains312PASS/1FAIL/95UNRESOLVED; baseline331/1/76. The entire95-case follow-up is94PASS/1UNRESOLVED in each role; all19 differential cases pass. Fourteen were not started in the original timed-out cohorts, five were interrupted. The identical fxmul assertion and_num90s censor remain explicit baseline debt, never passed tests. Aggregate timing/header effects are not universally isolated. Full interpreted ABBA and compiled request costs retain regressions; whole cold Gerbil/build comparison is unmeasured and its frozen commit-gate scope awaits resolution. Historical failures stay failed. No new scheduler, CFFI, generational GC, profile, executor, heap or watchdog change is admitted.";
 attribute nativeEvidence:String="Existing35 positive native executions,6 compilations,2 old controls and1728 owner-ring actions remain exact8f7/e63 observations. New original entry GSI40816.819609s and remaining Make109.332105s pass. Old/new compiler root controls27.101632s/27.122851s pass under120s each; original Make reuses two completed variants and builds the missing third in1.113637s. Prior120s failure is not reproduced, cause unresolved. Current full GSC counters334 PASS/1 FAIL/73 UNRESOLVED refine group failure without claiming missing coverage. See product-baseline.json and root-build-control.json.";
 attribute measuredCost:String="Historical8e cohort only, not current87: same8-column native module1b0b5e5f, predecessor0921f6d9 versus runtime3a541c7d, ABBA p1, two runs/role with identical per-role arrays:16 forced GC requests/32 non-tail caller. First observed fresh source-stack frames27 to25; warm rounds4 to2; summed frame events87 to55. Actual copied words76872 to76968 (+96 across16 rounds, +6/round=48 bytes at64bit); source words+64; objects+4/round. Planned/issued copy sections remain1 each round. Observation vectors are retained equally in both roles. Not allocation, unique graph size, peak RSS or overall throughput; mature heap frames still undergo full-GC traversal.";
 attribute producerEvidence:String="Runtime e63f7d8e completed source bootstrap266.202844s, clean2.020066s, dummy0.089693s and stock core32.144213s in original600s envelope with two phase1-4 passes. Test-only8f7fd987 child reuses all canonical generated/native identities: zero source copies, zero generation/core execution. Historical7a9 source bootstrap timeout571.294s retained; never promoted to a completed producer. Same stable workspace and unchanged Bazel/configure/Make profile.";
 attribute valueMatrix:String="| Responsibility | Removed work or ambiguity | Added cost | Evidence boundary |\n|----------------+---------------------------+------------+-------------------|\n| Owner propagation | No NaN equality convergence or stale self-supported cycle; at most R solved-key publications | Complete graph acquisition and bounded graph/tree walks | Source proof plus native PBT and same-case control required |\n| Key representation | Raw public NaN no longer enters comparator key domain | Producer in-place NaN branch; no reader boxing | All managed producer audit and emitted closure witness scan |\n| Scratch | No iterative owner-effect object or persistent VM pending table | R+7 F64 words; 8(R+5) payload bytes beyond old2-word scratch at64bit | Structural count, not measured peak |\n| Historical pre-host-unit build | Test-only child avoids Scheme generation and C rebuild | Exact earlier-period canonical/artifact checks | Earlier runtime bootstrap266.203s/core32.144s; not the current host-unit producer |\n| Closed generation planning | No coordinator source import for an issued prefix; original worker still owns completion | One typed metadata read, dependency waits and all remaining native work | Installed3-payload/192-case native control; official stdlib complete, downstream open |\n| Initializer view | Planner reads198209 bytes instead of173583452 rich input bytes on119 roots | Immutable projections plus retained original graphs and witnesses |161 ordered entries;18042 global cells unchanged; not peak or disk reclamation |\n| Whole runtime | No guessed throughput, latency or peak improvement | Whole product and release evaluation still required | Architecture3/4; independent SMP1/12 |\n";
 attribute waitMembershipGap:String="Existing WaitControl registrations is a cardinality abstraction. It does not prove native BTQ container/tree consistency or composed scheduler-dequeue versus request-withdraw/wake ownership. Crash observations provide a violated remove precondition, not a reconstructed legal interleaving. Derive the producer history before adding temporal transitions; retain existing Lean frame/spatial duties without duplicate schedules.";
 attribute physicalMembershipContract:String="Direct thread-start-on now acquires the same Thread start authority as thread-start plus the destination processor lease, rejecting duplicate starts. Migration holds the Thread lease from THREAD_SAVE through destination insertion and source current-thread withdrawal, never holds two processor locks, then dispatches with the acquired source processor. The fixed10000000-iteration wait is retired. The active-SMP native-reader inventory still finds effective-priority BTQ/TOQ reposition writers without an established complete queue/key-change lease; do not declare all writers closed.";
 attribute nextRefinement:String="Do not treat pre-existing fxmul or common cold compiler costs as owner regression. Preserve successful composed407/1 property coverage separately from failed original budget contracts. Qualify the actual Gerbil consumer and matched whole release/build population through existing owned workspaces; never create another source copy or relabel local GSI observations as whole release. No fragmented REV.";
 attribute commitGates:String="| Gate | Current source-period evidence | Decision |\n|------+-------------------------------+----------|\n| Tests |d07:41 frozen cases plus6 supplementary checks; interpreted408;326 programs/326 views/740 units; all four Gerbil consumers naturally exit; matched95 cases give94PASS/1 common censor in each role | Functional source review closed with explicit common fxmul/num debt; original aggregate cohorts are not passed |\n| Learning | Owned waiter/service/FIFO replacement preserves multi-shot control; VM-owned stable global cells remove fixed-array registration denial | Atomic lookup, extra wait headers/closures and metadata/native-check costs stay visible; no universal speedup |\n| Process | Whole fourth delivery; catalogue item5 of13; architecture3/4; independent SMP1/12 | No fragmented commit or repair credit; Declared runtime costs closed with explicit regressions; exact commit admission pending |\n| Models | Strict native OpenSysML324-field binding and real ASCENT; existing QNT/Lean owners retained | Bounded source/selection descriptor is rebuilt through SDK, not cached prose |\n| Questions | Actual source/case/consumer provenance is bound; cold comparison remains unmeasured in the separate build item | User-authorized cold-build follow-up; current costs retained, no cold-build speedup claim |";
 attribute diagram:String="direction: right\nowner_plan: Full owner graph before key publication\nfrozen_union: Unique thread and queue leases\npriority_solve: Private constants / prefix join / cycle least closure\npriority_commit: At most R key publications\nretire_plan: Clear borrowed roots before work unlock\nowner_plan -> frozen_union -> priority_solve -> priority_commit -> retire_plan\n\ncaller: Logical caller / full multi-shot wind and denv\nroot: Private frame-only root / denv false\nphysical: Thread.cont + break.Next\nservice: Fresh request service activation\npark: THREAD_PARK / no payload copy\nregister: Current Thread / original lock order / durable recheck\nready: Actual owner / join end / absolute deadline\ntransient: CV or I-O interruption abort\npost: I-O postcheck / caller predicate or read retry\ncaller -> root: one capture before registration locks\nroot -> physical: same GC-repaired frame\nphysical -> service: install suffix without executing caller\nservice -> park: durable wait resumes\nroot -> park\npark -> register\nregister -> physical: still pending\nregister -> ready: completed\nready -> caller: consuming physical restore\nservice -> transient: existing CV and I-O semantics\ntransient -> post\npost -> caller\nuser: Retained full user continuation\nservice -> user: call/cc\nuser -> park: late multi-shot / current live Thread\nbaseline_control: Same C and four-way fxmul failure / no new arithmetic regression\nmeasurement: matched compiled p1/p2 body latency and native peak\ngap: OPEN downstream Gerbil / whole cold release admission\nbaseline_control -> gap: does not clear unexecuted cases\nmeasurement -> gap: no whole speedup admission\ngap -> register: historical SIGSEGV retained / current positives scoped { style.stroke-dash: 4 }\ngc: Existing FrameSpec + forwarding + break handler\nroot -> gc\nphysical -> gc\nuser -> gc\nword: Shared ordered word / ticket acquire and unlock release\nmessage: GC payload / release stamp / acquire copy / reset\nreverse: Reverse tree message / consumption before reuse\nresources: VM-owned pair / per-slot construction bits\nword -> register: queue ownership visibility\nword -> message: same atomic interface\nmessage -> gc: ordered operation payload\nmessage -> reverse\nreverse -> message: next fixed-tree payload\nresources -> reverse: retained until closed VM and sender drain { style.stroke-dash: 4 }\nslot: VM sync_constructed / partial native acquisition\nreuse: Reset message state / retain mutex and CV\ndrain: Closed VM + joined carriers / dispose acquired bits\nslot -> resources: once per physical slot\nresources -> reuse: retirement retains native handles\nreuse -> message: reverse-tree cut precedes payload reuse\nresources -> drain: no child destruction\npriority: Frozen owner graph / key change and queue lease\npriority -> register: whole graph source candidate / cyclic admission open { style.stroke-dash: 4 }\nrecord: Scheme priority-update STRUCTURE / ticket + scratch + roots\nrecord -> priority: correct tagged-object ABI\nrecord -> gc: ordinary roots / allocation before lease\nownerDebt: Historical cyclic GC counterexample\nmodelDebt: Existing QNT custody / least closure / finite key laws\nownerDebt -> priority_solve: excludes iterative convergence\nmodelDebt -> ownerDebt: temporal duty / not a native witness\ncaseLedger: Python source and terminal validators\ncaseLedger -> priority: real p1 and p2 checks\ncaseLedger -> ownerDebt: scoped passes do not close this duty\nadmission: ASCENT required-acceptance veto\nownerDebt -> admission: blocks whole result\ncaseLedger -> admission: source-bound facts\nevidence: Registered Python Evidence view / checked references\nidentity: Candidate tree + runtime artifacts + profile observation\nworking: Changed working sources / unqualified\nevidence -> identity: ASCENT shared Library\nevidence -> priority: source and scoped native facts / no whole admission\nworking -> evidence: stale reference rejects query\n\nfrontend: Unadmitted frontend / macro capability closure open\ncompilerTask: Existing gxc invoke / physical output claim\ncompletion: Successful native return / output + MD reads\nquiescence: Parent reaped / group quiescent\ncompletionJournal: Existing Evidence journal / header + runId\nreuseTask: Same argv cwd source provider headers output\nfrontend -> compilerTask\ncompilerTask -> completion\ncompletion -> quiescence\nquiescence -> completionJournal\ncompletionJournal -> reuseTask: immutable witness before derived cache\nreuseTask -> compilerTask: changed identity executes\n\nmodule_program: \"Complete module program\"\nmodule_program -> native_completion: \"Actual child return and all metadata writers\"\nmodule_program -> dependency_frontier: \"Exact imported cohort, closed under dependencies\"\ndependency_frontier -> ready_interface: \"Journal + stable bytes + quiescent parent\"\nready_interface -> downstream: \"Actual macro consumer imports same lexical cohort\"\n\nglobal_addressability: \"Native global addressability: 12196 -> 20000\"\nready_interface -> global_addressability: \"Compiled phase loading\"\nglobal_addressability -> downstream: \"Historical failure at unchanged capacity\"\n\nhistorical_identity -> global_addressability: \"Historical eager SSI identity query\" { style.stroke-dash: 4 }\nmodule_program -> metadata_graph: \"Admitted identity and dependency metadata\"\nmake_identity -> reader_identity: \"No admitted program\"\nreader_identity: Header reader / no body expansion\nreader_identity -> metadata_graph: \"Ordinary Scheme identity only\"\nmetadata_graph -> frontend: \"Needs generation: original macro discovery\"\nmetadata_graph -> downstream: \"Existing Make completion edges, without phase activation\"\n\nmetadata_query: \"Checked identity / dependency metadata\"\nmacro_activation: \"Actual compilation owns phase activation\"\nnative_module: \"Module-owned requests / original gxc quota\"\nprivate_ssi: \"Private SSI until all native jobs join\"\nmodule_witness: \"Complete outputs / stable dependencies / quiescent parent\"\nmetadata_query -> macro_activation: \"only when compilation needs it\"\nmacro_activation -> native_module\nnative_module -> private_ssi: \"drain success\"\nprivate_ssi -> module_witness\nmodule_witness -> metadata_query: \"next incremental build\"\n\ncompiler_unit: \"Physical unit plan: source and scoped native pass; whole consumers OPEN\"\ncompiler_profile: \"Original profile: unlimited single host\"\ncompiler_variant: \"Historical multiple-host flag diagnostic: no producer admission\"\ncompiler_unit -> native_module: \"source-owned plan; whole consumers still required\"\ncompiler_profile -> compiler_unit\ncompiler_variant -> compiler_unit: \"counterfactual, not acceptance\"\n";
 attribute writerCoverage:String="All managed effective-key stores, including thread creation, use one in-place F64 normalization producer. Reads remain raw non-NaN ordered keys; no boxing reader wrapper. Public setters and existing boost/unboost/inherit macros share full owner-plan acquisition. Private raw/FFI/serialization field mutation is outside this adapter and grants no arbitrary-writer admission. Existing automatic insertion/unlock inheritance hooks remain disabled; this solves the owner closure reached by the existing key-update triggers.";
 attribute retainedSyncLifecycle:String="sync_constructed is a VM control array indexed by the existing processor bound, not a new PSTATE field or identity table. Bit0 acquires mutex, bit1 acquires condvar; a failed native constructor never publishes a member. Setup owns interrupt failure unwind. Processor cleanup destroys neither resource; reset occurs after old-set rendezvous and retired receiver join, with uncertain launches refusing reuse. Old signal tails may touch the retained pair but cannot overwrite the new payload after the reverse-tree cut. Closed VM/member entry and joined known carriers precede disposal; POSIX destroy success clears each bit, refusal retains control for retry. Unpublished unexpected teardown failure retains the constructor control and must not authorize caller free or blind setup retry.";
 attribute closureProof:String="Let k(x)=bottom for NaN and x otherwise. Ordered extended real keys modulo signed zero form a max-semilattice. With frozen graph leases, c_i=k(boosted_i) join maximum external waiter key. Every planned waiter is an internal edge, not a constant. Along prefix e_i=c_i join e_(i-1). The cycle value M joins all cycle constants and incoming prefix. These assignments satisfy every owner equation; any fixed point dominates each constant and incoming value, hence dominates M. At most R publications follow private solve. Structural traversal terminates under existing valid finite owner/BTQ invariants; not a wall-clock latency bound.";
 attribute gcBoundary:String="The mutation lease is deliberately nonpolling through partial red-black edits. GC waits for a finite, source-bounded operation, then existing safepoints resume participation; this is not mid-edit preemption or wait-freedom. All retries, allocation and classification precede shared writes. In-place F64 producer normalization avoids the boxing/checks observed in rejected return-value and let-temporary prototypes. Emission witness scan is source-bound and not a complete C verifier.";
 attribute failureCustody:String="Before publication a refused lease or exception leaves the old shared keys intact and releases borrowed roots. After the first shared key store no supported Scheme interruption/exception is admitted until fixed-count completion and release. A retired workspace cannot replay stale keys. Arbitrary OS worker death or corrupt/private field mutation inside the lease is outside this proof; no unknown physical write is relabeled safe.";
 attribute productAttribution:String="Current paired95-case follow-up preserves the same source bytes, SDK roles and300/90s bounds:94 pass and only_num remains censored in both roles. Original19 differential cases include14 unstarted and5 interrupted at parent deadlines; all now pass in each role. Original baseline and candidate fxmul failure signatures are independently identical. The public baseline role projection corrects a workbench-producer label using actual baseline SDK artifacts/argv. Prior0ec and currentd07 share GSI/GSC bytes and all26 RTS archive member bytes; archive metadata differs, and target-header equivalence or whole timing causality is not inferred. No numeric fix or compiler optimization is added here.";
 attribute releaseMeasurement:String="Current d07f67b4 retains full408-case interpreted ABBA, original e52-fixture8-build/16-execution data in shared-slot-cost.json, and a separately qualified argument-only fixture98971f5c in argument-only-inputs.json and argument-only-cost.json. The fresh two ABBA cycles have8 builds and16 natural executions: p1 median0.006810665s baseline versus0.009161115s candidate (+34.51%); p2 median0.018803120s versus0.024389982s (+29.71%). All4096 requests,8192 multi-shot resumes,4096 identity messages and16 explicit GC operations remain. Per-execution latency distributions and native peak/RSS are retained; these regressions must be dispositioned, never selected away. Whole matched cold build and aggregate peak remain unmeasured. The mixed SDK static archive is not baseline static-link evidence; the actual dynamic path has no archive operand.";
 attribute compiledCoverage:String="Historical1b77-case deficit retains its original period. Current d07f67b4 full original408 GSC:312PASS/1FAIL/95UNRESOLVED, versus same-profile baseline331/1/76. There are19 baseline-pass/current-unresolved cases. Earlier0ec has identical GSI/GSC executable bytes and364/1/43; executable identity does not equate all header-dependent compiled modules or explain timing variation. All original77 cases passed in that earlier source period, but the final19 remain open. No subset or started filename replaces the failed whole300/90-second cohort. See shared-slot-coverage.json.";
 part def Adapter { ref part need:GambitModernCOutcomes::Need; attribute path:String; attribute contract:String; attribute status:String; }
 attribute closureMembers:String="ownerFlow;consumerChain;budgetCause;releasePopulation;revisionAdmission";
 part def DeliveryBoundary {
  ref part result:GambitModernCOutcomes::Result;
  attribute replacement:String;
  attribute caseEvidence:String;
  attribute caseEvidenceSha256:String;
  attribute exclusions:String;
  attribute extensionRule:String;
  attribute failureRule:String;
 }
 part boundary:DeliveryBoundary {
  ref part :>> result=GambitModernCOutcomes::execution;
  attribute :>> replacement="Replace repeated waiter capture and ambiguous request/service/FIFO publication with explicit owned control flow. Include only actual compiler/product prerequisites needed to execute the declared consumers. Preserve multi-shot continuation, dynamic-wind, roots and scheduling policy.";
  attribute :>> caseEvidence="evidence/research/retained/modern-c/request-product/shared-slot-native-cases.json";
  attribute :>> caseEvidenceSha256="d51ceece70d84835d96175f62260273d5aa0cf2c1ca96ed0ec66098e8304d7c3";
  attribute :>> exclusions="No whole scheduler redesign, complete CFFI, generational GC, frontend optimization programme, new profile/executor, whole matched cold-build comparison, or independent SMP12-family admission. Cold cost stays unmeasured in the separate build workstream; no cold acceleration claim. Supporting build/model/CI work grants no architecture increment.";
  attribute :>> extensionRule="The requiredAcceptanceParts and pinned nonhistorical cases define the exact admission dependency set. New or removed blockers require a reviewed SysML contract change with causal source/test evidence and refreshed source-bound audit; a report, failed related test or new ASCENT fact cannot silently extend it. Existing reviewed-report/model digests must then invalidate. No boundary change can turn a prior failed or censored run into a pass.";
  attribute :>> failureRule="Retain failures and limits. Baseline-common failure requires matching inputs, artifacts and an independently checked failure signature; current-only or uncertain effects remain unresolved. A dependency can block a required consumer without becoming an unrelated runtime redesign. Historical case identities here retain8f7fd987 and do not qualify1b387add or the dirty checkout.";
 }
 attribute progressAxes:String="3/4 counts locally qualified complete architecture results; item5 of13 is a responsibility address, not5/13 completion;1/12 counts independent branch SMP families. Closure obligations below are not a new progress denominator. Supporting commits and four Gerbil Make stages advance none of these counters by themselves.";
 attribute closureDelay:String="Delivery4 mixed runtime ownership, necessary compiler/ABI consumer prerequisites and an unmeasured whole cold-build comparison. Current326/326/740 consumers and all19 differential functional cases are closed; original aggregate censoring and common failures remain baseline debt. User explicitly assigns cold-build comparison to the later build workstream. Current composed costs retain p1/p2 regressions; bounded owner-graph convergence, unique queue/write ownership and reproducible overhead disposition justify the responsibility replacement, not universal throughput superiority. The remaining step is exact source/commit audit, not another scheduler or frontend project.";
 part def ClosureObligation { ref part component:Adapter; attribute id:String; attribute status:String; attribute scope:String; attribute evidence:String; attribute qntDuty:String; attribute pbtDuty:String; attribute exitCondition:String; attribute exclusion:String; }
 part ownerFlow:ClosureObligation {
  ref part :>> component=propagationExit;
  attribute :>> id="OWNED-CONTROL";
  attribute :>> status="SCOPED_QUALIFIED";
  attribute :>> scope="Request/service/wait/FIFO and priority ownership; preserve multi-shot continuation and real GC roots.";
  attribute :>> evidence="evidence/research/retained/modern-c/request-product/shared-slot-native-cases.json";
  attribute :>> qntDuty="Existing priority_propagation.qnt::initClosure/admissible and interrupt_request_lifecycle.qnt delivery/late-return histories; no compiler timing theorem.";
  attribute :>> pbtDuty="Existing mutex-suspension.scm domain histories, seed173, real owner rings and same-signature deletion-one-minimal shrink. Current native six-case p1/p2 rerun passes; no new failure means shrink was not triggered. Seed controls actions, not every OS interleaving; historical shrink calibration retains its own source period.";
  attribute :>> exitCondition="Current d07f67b4 passes all41 frozen cases and6 supplementary frame/replay controls. Original historical failures retain old source identities. The final native packet is shared-slot-native-cases.json; no new positive failure means current shrinking is NOT_TRIGGERED.";
  attribute :>> exclusion="Keep managed writer/borrow and no-poll commit premises; no one-shot restriction, arbitrary raw writer or whole-SMP credit.";
 }
 part consumerChain:ClosureObligation {
  ref part :>> component=product;
  attribute :>> id="CURRENT-CONSUMERS";
  attribute :>> status="CLOSED_NATIVE";
  attribute :>> scope="Current d07f67b4/987c59dd completes326 programs,326 views and740 static units. Official stdlib/libgerbil/lang/tools naturally exit in15.974612/46.084959/8.684437/94.919886s in the closing incremental attempt. Historical1b/7308 remains a distinct source period; no cold-build speedup follows.";
  attribute :>> evidence="evidence/research/retained/modern-c/request-product/shared-slot-consumer-custody.json";
  attribute :>> qntDuty="Existing incremental_build.qnt owns request/finish/publish/reuse provenance, not wall-time performance.";
  attribute :>> pbtDuty="Existing compiler-product failure/stale-input negative controls and module recovery tests; never substitute frontend files for completion.";
  attribute :>> exitCondition="326 complete programs,740 static units, natural stdlib/libgerbil/lang/tools exits and official GSI408/408.";
  attribute :>> exclusion="Retain failed parents; current successful incremental consumers are not a cold baseline or proof for all GSC files.";
 }
 part budgetCause:ClosureObligation {
  ref part :>> component=product;
  attribute :>> id="COVERAGE-CAUSE";
  attribute :>> status="CLOSED_MATCHED_CASE_REVIEW";
  attribute :>> scope="All95 originally unresolved candidate cases were attempted in both correctly bound SDK roles under300/90s:94 pass and only_num remains censored in each. All19 differential cases pass in both roles. Their original cohort had14 not started and5 interrupted at parent deadlines. This closes the case-specific functional gap; original cohort censoring and phase/timing uncertainty remain explicit cost evidence.";
  attribute :>> evidence="evidence/research/retained/modern-c/request-product/shared-slot-coverage.json";
  attribute :>> qntDuty="No new QNT timing machine. Phase/cwd/tool/source attribution is an empirical obligation.";
  attribute :>> pbtDuty="No random timing property. Reuse original case bytes; separate functional assertion checks from native phase measurements and shrinking.";
  attribute :>> exitCondition="Current326/740 consumers complete. Original408-file cohorts remain312PASS/1FAIL/95UNRESOLVED candidate and331/1/76 baseline; they are not relabeled. Fresh matched95-case follow-up yields94PASS/1UNRESOLVED in both, including19/19 differential positives. Independently checked SDK artifacts and identical fxmul source/assertion signatures establish common failure debt;_num is common90s censoring, never a passed test. Compiler-phase latency and whole-build cost are separate, without universal causal claims.";
  attribute :>> exclusion="Rejected full-inline and first-probe-inline experiments remain rejected. Production uses one actual lookup body in the header and runtime ABI adapter, with no value/address caching or new layout. Native ordered-word targets share the body; legacy generated backends keep the old service. Aggregate wall times cannot establish compiler macro or optimizer causality.";
 }
 part releasePopulation:ClosureObligation {
  ref part :>> component=release;
  attribute :>> id="MATCHED-COST";
  attribute :>> status="CLOSED_DECLARED_POPULATION";
  attribute :>> scope="Declared REV cost population: full408 interpreted ABBA and fixed4096-request compiled8-build/16-execution ABBA; exact inputs, source/ABI, all overheads retained. Whole matched cold Gerbil/build belongs to a separate follow-up per explicit user scope decision; no cold acceleration claim.";
  attribute :>> evidence="evidence/research/retained/modern-c/request-product/argument-only-cost.json";
  attribute :>> qntDuty="No QNT or Lean model predicts measured throughput/RSS. Existing spatial laws do not prove performance.";
  attribute :>> pbtDuty="The4096-request cost workload is fixed functional/measurement data, not random PBT; existing replay/shrink owns semantic counterexamples.";
  attribute :>> exitCondition="Full408 interpreted and current argument-only8-build/16-execution populations are measured on d07. All samples, native process RSS/footprint and observed regressions are retained. Owner propagation now terminates on finite frozen graphs, including cyclic/NaN cases; scratch/leases/lookups are explicit costs. This is correctness and bounded-work benefit with measured overhead, not a speedup gate. Whole cold build and aggregate peak remain unmeasured outside this REV.";
  attribute :>> exclusion="Preserve p2 scheduling variation, requested native bytes versus RSS, all samples and regressions. No guessed speedup.";
 }
 part revisionAdmission:ClosureObligation {
  ref part :>> component=product;
  attribute :>> id="REV-ADMISSION";
  attribute :>> status="OPEN_FIVE_GATES";
  attribute :>> scope="One complete fourth delivery, exact code/test/model evidence and audited submission tree.";
  attribute :>> evidence="evidence/research/retained/modern-c/request-product/owner-closure-acceptance.json";
  attribute :>> qntDuty="ASCENT evaluates existing five gates and source-bound evidence; QNT owns runtime histories only; Lean retains existing spatial/frame obligations.";
  attribute :>> pbtDuty="Reuse existing evidence/source tamper controls; no second test framework or ready flag authored by the caller.";
  attribute :>> exitCondition="Close the remaining named whole-product and matched-release predicates; qualify final source projection and whitelisted commit tree before commit/push.";
  attribute :>> exclusion="Do not merge unrelated staged startup/header prototypes, move repair-line results, change limits, or count supporting commits as architecture outcomes.";
 }
 attribute closureEdges:String="ownerToAdmission;consumerToAdmission;budgetToAdmission;releaseToAdmission";
 part def ClosureDependency { ref part predecessor:ClosureObligation; ref part successor:ClosureObligation; attribute condition:String; }
 part ownerToAdmission:ClosureDependency { ref part :>> predecessor=ownerFlow; ref part :>> successor=revisionAdmission; attribute :>> condition="Managed semantic/source and native duties remain qualified on the final source."; }
 part consumerToAdmission:ClosureDependency { ref part :>> predecessor=consumerChain; ref part :>> successor=revisionAdmission; attribute :>> condition="Actual current-ABI natural consumer exits; failed parents retain their status."; }
 part budgetToAdmission:ClosureDependency { ref part :>> predecessor=budgetCause; ref part :>> successor=revisionAdmission; attribute :>> condition="Attribute77 unmatched completions before declaring the deficit harmless."; }
 part releaseToAdmission:ClosureDependency { ref part :>> predecessor=releasePopulation; ref part :>> successor=revisionAdmission; attribute :>> condition="Declared matched cost population and explicit overhead disposition, not an inferred universal speedup."; }
 part def GlobalRole { attribute role:String; attribute source:String; attribute contract:String; }
 part def GlobalIdentity :> GlobalRole { attribute lifetime:String; }
 part def VmGlobalCells :> GlobalRole { ref part identities:GlobalIdentity; attribute allocationPolicy:String; }
 part def FrozenGlobalCells :> GlobalRole { ref part cells:VmGlobalCells; attribute qualification:String; }
 part def GlobalOwnershipEdge { ref part producer:GlobalRole; ref part consumer:GlobalRole; attribute contract:String; }
 part globalIdentity:GlobalIdentity {
  attribute :>> role="globalIdentity";
  attribute :>> source="vendor/gambit/lib/_mem/global-bindings.inc:global_append/global_room/make_global_var";
  attribute :>> contract="Shared monotonic identity in the existing int domain. Identity publication does not allocate a dense slot in every live VM. The20000 backing-array admission rule retires, without raising heap/profile capacity options.";
  attribute :>> lifetime="GSTATE permanent arena; shared immutable code templates remain. Unpublished permanent metadata stays arena-owned until global cleanup; no per-attempt refund claim.";
 }
 part vmGlobals:VmGlobalCells {
  ref part :>> identities=GambitRequestProduct::globalIdentity;
  attribute :>> role="vmGlobals";
  attribute :>> source="vendor/gambit/lib/_mem/global-storage.inc;global-bindings.inc;memory-lifecycle.inc";
  attribute :>> contract="One VM-owned store. One page holds WORD_WIDTH ordinary and primitive cells plus one primitive-presence word. Page/cell addresses remain stable. A half-full append-only directory doubles geometrically; old directories remain VM-owned until the existing cleanup permit. Reads allocate nothing; binding prepares cells before generated writes.";
  attribute :>> allocationPolicy="Native malloc under the existing registry gate, no Scheme allocation/GC/callback. Failed page/directory preparation preserves the old directory and published cells. VM setup currently materializes the captured entire shared-registry prefix, not a minimal module-demand inventory: setup remains O(G) and no asymptotic startup saving is claimed. Later unrelated-VM registrations allocate no cells in this VM. Generated/admitted writes require prepared VM cells; raw cross-VM identity-only writers are not silently admitted. Native requested-storage measurements are separate from RSS and whole peak.";
 }
 part frozenGlobals:FrozenGlobalCells {
  ref part :>> cells=GambitRequestProduct::vmGlobals;
  attribute :>> role="frozenGlobals";
  attribute :>> source="vendor/gambit/lib/root.h;_mem/root-tasks.inc:root_globals_begin/root_globals_source/root_round_publish;_mem/root-origins.inc:mark_global_variables";
  attribute :>> contract="After writer closure, capture this VM's page head/count once. Partition dense page ordinals, never shared identity count. Both standalone and whole-round publishers initialize each shard cursor. RootTask owns ordinary cells and active primitive overrides in its exact page range. Scan metadata is not a Scheme root. No page/directory is reclaimed until VM cleanup admits all readers and tasks drained.";
  attribute :>> qualification="First self-host seed fault at page offset16 retained; whole-round publisher omitted its cursor and is corrected. Current from-scratch532.533884s passes both full phase sequences. Cold stock120 remains failed; no whole tools/release or4/4 admission follows.";
  attribute spatialRefinement:String="For word width W and identity i: pageKey=floor(i/W), offset=i mod W. Each published key has exactly one stable page. Concrete root cells are Ordinary(page,offset) for every0<=offset<W and Primitive(page,offset) when the frozen presence bit is set. Field arrays are disjoint C subobjects; aliases of Scheme values do not alias root-cell addresses. Floor page partitions cover each physical page once, including empty shards. Reuse existing Lean CompleteCensus/TaskCoverage laws only after these native premises hold; no new temporal theorem.";
  attribute writerCut:String="All own-VM RC domains reach FROZEN at the admitted collective before the global-gate snapshot; same-VM page preparation requires OPEN ownership and cannot overlap that cut. Unrelated VM registration may extend shared identities but does not append these pages. Acquire directory publication exposes fully initialized page payload; old directories and all pages outlive readers through existing VM cleanup permission.";
  attribute qualificationBoundary:String="The snapshot PBT oracle tracks a logical registry transaction stamp separately from physical page geometry. The C observer must independently match snapshot count/head to actual VM storage and source descriptors to that snapshot. Real moving-root tests establish address repair; native registration over20000 does not itself prove failure-injection, every writer, or whole SMP.";
  attribute nextBoundary:String="Future ModuleSpec/HostGraph work, excluded from this delivery: a statically bound GVM global may resolve its stable VM cell address once at a proven dominating host point and reload the mutable payload at each use. Do not mark the generic missing-binding lookup pure, cache the unbound sentinel, snapshot global values into continuations, or hoist an unbound-value error. FrameSpec reentry must reconstruct the correct VM/module scope for multi-shot restoration and tail dispatch; native pointer locals are not Scheme frame roots. Dynamic reflective globals retain checked lookup. Positive condition: eliminated hot lookups exceed binding/reentry/spill costs; counterexamples are cold branches, large host reference sets and frequent context switches. This is an IR address-invariance obligation reusable by generated C and a future MLIR lowering, not a new executor, namespace or implemented optimization.";
 }
 part globalRead:GlobalRole {
  attribute :>> role="globalRead";
  attribute :>> source="vendor/gambit/include/gambit.h.in:___global_page/___global_cell_address/___GLOCELL_IN_VM;vendor/gambit/lib/_mem/global-storage.inc:___global_cell";
  attribute :>> contract="Runtime and native ordered-word generated modules share one outlined address resolver. The exported service remains an ABI adapter; legacy/emulated generated targets retain that service. Preserve acquire loads, collision traversal, stable VM cell lifetime and fresh mutable payload loads. No address/value cache, purity annotation, allocation, poll, callback or layout change. Existing GC/cleanup ownership and QNT/Lean premises are unchanged. Native timing variation and lookup overhead remain empirical costs, not proven gains.";
 }
 part cellsToReads:GlobalOwnershipEdge {
  ref part :>> producer=vmGlobals; ref part :>> consumer=globalRead;
  attribute :>> contract="An acquired immutable directory denotes initialized stable pages through the VM cleanup permit; a read never prepares missing storage or retains a borrowed cell past VM lifetime.";
 }
 part identityToCells:GlobalOwnershipEdge {
  ref part :>> producer=globalIdentity; ref part :>> consumer=vmGlobals;
  attribute :>> contract="Binding transaction maps stable identity to VM storage before symbol/module publication; allocator failure leaves identity unpublished or retains existing binding responsibility.";
 }
 part cellsToRoots:GlobalOwnershipEdge {
  ref part :>> producer=vmGlobals; ref part :>> consumer=frozenGlobals;
  attribute :>> contract="Existing RC writer closure and global_gate publish one immutable page inventory; main-round and standalone adapters must refine the same cursor/range contract.";
 }
 part globalStorage:Adapter {
  ref part :>> need=GambitModernCOutcomes::executionNeed0;
  attribute members:String="globalIdentity;vmGlobals;frozenGlobals;globalRead";
  attribute links:String="identityToCells;cellsToRoots;cellsToReads";
  attribute :>> path="vendor/gambit/lib/_mem/global-storage.inc;global-bindings.inc;root-tasks.inc;root-origins.inc;memory-lifecycle.inc;vendor/gambit/include/gambit.h.in;vendor/gambit/tests/smp/gc/global-storage.scm";
  attribute :>> contract="Complete identity/storage/scan ownership replacement. Scheme names, tail/continuation representation and VM-local primitive override semantics remain. A native lookup and directory retention cost must be measured; no invisible allocation in a read or generated store.";
  attribute :>> status="IMPLEMENTED; source1b387add self-host and explicit native phases pass.21000 roots, snapshot and seven-family native replay/shrink, p1/p2 shard relocation, primitive VM lifecycle and116 framework checks pass. Official stage1-bach independently constructs and runs the new ABI Gerbil; whole cold attempts remain failed. Current stdlib/libgerbil/lang/tools naturally complete with326 programs and740 static units; full comparative release and original final-source checks remain open. No whole-SMP credit.";
 }
 attribute globalStorageMatrix:String="Source periods are distinct: the326-program/740-unit consumer completion below belongs to historical1b387add/7308a00f. Current d07f67b4/987c59dd consumers complete326 programs and740 static units; shared-slot-cost.json retains current measured regressions.\n| Responsibility | Retired work / observed benefit | Added cost / unresolved boundary |\n| Identity | Fixed20000 backing-array registration denial retired; native fixture27216 total identities | Identity still bounded by int representation and allocation failure |\n| VM storage | Physical426 pages in the growth fixture; current three-cycle VM control requests106368 native bytes versus historical fixed322504 | This is requested storage, not RSS or whole peak; more separate native allocations and retained directories |\n| Roots | Native21000 roots, actual snapshot PBT/shrink and p1/p2 shard relocation pass | Rounded page holes plus primitive slots; allocation-failure controls pending |\n| Self-host | Both generation passes532.53s, generated C unchanged | Cold stock120 still failed; explicit native phases and warm Make are separate |\n| Gerbil | New ABI stage0 and official stage1-bach complete in same workspace | Whole stage1 attempts fail; current ABI stdlib/libgerbil/lang/tools all naturally complete with326 programs and740 static units; whole comparative release/build remains open |\n| Lookup | Stable cells and read/store without allocation | Acquire loads, dispatch and worst-case O(P) probing; ABBA p1 body21.34ms to23.70ms,2 samples each, same Scheme bytes; no whole speedup claim |";
 part globalStorageEvidence:EvidenceUse {
  ref part :>> component=globalStorage;
  attribute :>> observation="global-storage-native;global-storage-consumers-complete;global-storage-budget-gap";
  attribute :>> boundary="Current runtime tree and separately hashed pending tests; retained initial main-round cursor crash, corrected self-host pass, cold stock failures, p1/p2 moving roots and new-ABI Gerbil attempts. No support result grants WHOLE-PRODUCT or MATCHED-RELEASE.";
 }
 part request:Adapter { ref part :>> need=GambitModernCOutcomes::executionNeed0; attribute :>> path="vendor/gambit/lib/_thread#.scm;vendor/gambit/lib/_thread.scm"; attribute :>> contract="immutable request identity; both dispatch consumers; one service claim; guarded result; actual completion wait and target-owned abandonment"; attribute :>> status="Current managed source is unchanged between8f and1b; current native interpreted/compiled request controls pass. Historical physical-BTQ ownership gaps are retained in old source periods; this adapter alone grants no whole delivery."; }
 part mailbox:Adapter { ref part :>> need=GambitModernCOutcomes::executionNeed0; attribute :>> path="vendor/gambit/lib/_fifo#.scm;vendor/gambit/lib/_thread.scm"; attribute :>> contract="one mailbox install; detached rooted cell; same mutation permit for link/remove/cursor; allocation outside low-level commit"; attribute :>> status="Current interpreted/compiled p1/p2 publication, permit-root and ordered-handoff controls pass. Selected managed writers are qualified; arbitrary private mutation remains outside scope."; }
 part queue:Adapter { ref part :>> need=GambitModernCOutcomes::executionNeed0; attribute :>> path="vendor/gambit/lib/setup.c::___get_next_high_level_interrupt_pstate;models/gambit/interrupt_request_lifecycle.qnt::deliveryPop"; attribute :>> contract="Under the processor lock: advance head, repair tail and detach next. Scheme thread-pop already detaches next. Refines existing deliveryPop next1=0; do not assume the model tail-retry guard exists for every raw native caller."; attribute :>> status="native pass p1/p2; old embedded runtime fails the identical queue-control module"; }
 part lateReturn:Adapter { ref part :>> need=GambitModernCOutcomes::executionNeed0; attribute :>> path="vendor/gambit/lib/_thread.scm::##thread-intr-service!;vendor/gambit/lib/_thread#.scm::macro-mutex-unlock-with-acquired-lock!;models/gambit/interrupt_request_lifecycle.qnt::initLateReturn"; attribute :>> contract="Target termination precedes late continuation restoration and GC. A subsequent mutex owner retains ownership, no late result publishes. Existing QNT extends only this bounded temporal history; initLateResultWithoutOwner and initLateUnlockWithoutOwner preserve negative controls. Guard/release is one actual lock lease; model staging assumes the lease, not a memory-order or arbitrary-frame proof."; attribute :>> status="current native semantic control accepted; existing temporal model mutations retained; no Lean schedule duplication"; }
 part waitControl:Adapter { ref part :>> need=GambitModernCOutcomes::executionNeed0; attribute :>> path="vendor/gambit/include/gambit.h.in::___THREAD_SAVE;___THREAD_RESTORE;vendor/gambit/lib/_thread.scm::##thread-resume-execution!;##mutex-lock-out-of-line!"; attribute :>> contract="Mutex adapter reuses a typed caller suffix through gsc/_prims.scm lift2213, _t-c-2.scm THREAD_PARK, gambit.h.in root publication and _thread.scm mutex-wait/register/acquire. Existing continuation GC/header/FrameSpec consumers repair aliases. Join/sleep share this frame-root protocol; CV/I-O retain abort semantics. Model composition remains required; no macro-count or one-shot proof."; attribute :>> status="Current p1/p2 mutex/join/sleep/CV/I-O continuation controls pass, including multi-shot frame roots. No macro-count allocation saving or whole product credit is inferred."; }
 part product:Adapter { ref part :>> need=GambitModernCOutcomes::executionNeed1; attribute :>> path="vendor/gambit/tests;src/gambit_smp/gerbil_build/;src/gambit_smp/gerbil_compile_products.ss"; attribute :>> contract="final source bootstrap and complete original/native/Gerbil consumers, actual natural exit and case inventory"; attribute :>> status="Historical1b/7308 completes consumers. Current d07f67b4 interpreted408 and47 scoped native checks pass; current326-program/740-unit consumers all naturally exit. Original GSC retains312PASS/1FAIL/95UNRESOLVED against baseline331/1/76; the complete matched95-file follow-up has94PASS/1UNRESOLVED in both roles and all19 differential positives. Common fxmul failure and_num censoring remain debt; whole release-cost scope stays open."; }
 part release:Adapter { ref part :>> need=GambitModernCOutcomes::executionNeed2; attribute :>> path="evidence/research/retained/modern-c"; attribute :>> contract="matched whole workload throughput/latency/peak/build; no inherited support CI or repair acceptance"; attribute :>> status="Interpreted and compiled p1/p2 matched populations retained; small workload cost and RSS increases explicit; full downstream/cold release open"; }
 part syncSlot:Adapter {
  ref part :>> need=GambitModernCOutcomes::executionNeed0;
  attribute :>> path="vendor/gambit/lib/lifecycle.h;vendor/gambit/lib/setup.c;vendor/gambit/lib/_setup/vm-lifecycle.inc";
  attribute :>> contract="VM-owned acquired bits; no per-incarnation reconstruction; reverse-tree reset cut; no child destruction; closed/joined VM disposal; retain refused destruction";
  attribute :>> status="MANAGED_SOURCE_NATIVE_QUALIFIED; POSIX profile only; raw/private external writes and corrupted OS contracts excluded";
 }
 part queuePriority:Adapter {
  ref part :>> need=GambitModernCOutcomes::executionNeed0;
  attribute :>> path="vendor/gambit/lib/_thread.scm::##thread-priority-try!;##thread-priority-update!";
  attribute :>> contract="Comparator-key update and BTQ/TOQ reposition use one complete ownership transaction; public raw values preserved, NaN scheduling order is explicitly bottom";
  attribute :>> status="IMPLEMENTED_SOURCE_ADAPTER; source-bound cases and emission ledger decide scoped qualification; whole product/benefit admission remains open; original diagnostic nonreturn is not a unique-cause proof";
 }
 part propagationExit:Adapter {
  ref part :>> need=GambitModernCOutcomes::executionNeed0;
  attribute :>> path="vendor/gambit/lib/_thread.scm::##thread-priority-plan;##thread-priority-try!;##thread-priority-apply!;##thread-priority-release!";
  attribute :>> contract="Complete owner graph storage precedes publication. All unique thread and queue leases and exact source identities must validate before the first key store; no exception/poll/allocation is allowed until the complete owner effect releases. Failed graph acquisition publishes no key. Cyclic traversal must terminate without blocking VM GC.";
  attribute :>> status="SCOPED_NATIVE_AND_SOURCE_REFINEMENT_CLOSED; historical3e9 cyclic GC rejection retained. Current exact p1/p2 ring histories, source least-closure argument, emitted witness scan and same-case GC/setter natural completion qualify the managed adapter. Whole-product and matched-release admission remain open.";
 }
 part def AcceptanceUse {
  ref part component:Adapter;
  attribute familyId:String;
  attribute reason:String;
 }
 part ownerExitRequirement:AcceptanceUse {
  ref part :>> component=propagationExit;
  attribute :>> familyId="PRIORITY-PROPAGATION-EXIT";
  attribute :>> reason="Require source functional-graph least-solution argument, all managed key producers, emitted no-GC closure and actual cyclic GC/PBT/retirement evidence before scoped closure";
 }
 part productRequirement:AcceptanceUse {
  ref part :>> component=product;
  attribute :>> familyId="WHOLE-PRODUCT";
  attribute :>> reason="Current d07f67b4 has all four natural original Gerbil consumer exits with326 programs/326 views/740 static units and full408 interpreted positives. Both correctly bound SDK roles pass94 of the same95 original unresolved GSC files; all19 differential cases pass. Original aggregate failures/censoring remain unchanged: common fxmul source/signature and_num90s censor are retained baseline debt under the frozen attribution rule, not passed tests. This is a source-refinement closure of the functional consumer/case obligation, not complete aggregate timing attribution, cold performance or4/4 release admission.";
 }
 part releaseRequirement:AcceptanceUse {
  ref part :>> component=release;
  attribute :>> familyId="MATCHED-RELEASE";
  attribute :>> reason="Current d07f67b4 argument-only native workload98971f5c passes all8 builds/16 executions with exact role identities and retained4096-value latency distributions; observed p1/p2 body regressions34.51%/29.71% remain explicit. Historical fixture costs and explicit-placement baseline failure remain their own populations. Overhead disposition: accept bounded finite owner solving, unique queue/write ownership and completed consumers with measured regressions explicitly retained; no runtime speedup promised. Whole matched cold build is user-assigned to the later build item, stays unmeasured and grants no acceleration claim.";
 }
 part def EvidenceUse {
  ref part component:Adapter;
  attribute evidenceView:String="evidence/scenarios/modern-c/request-product.view.json";
  attribute observation:String;
  attribute boundary:String;
 }
 part priorityEvidence:EvidenceUse {
  ref part :>> component=queuePriority;
  attribute :>> observation="priority-open;working-open;priority-source-native";
  attribute :>> boundary="Baseline/current five-second diagnostic does not identify a unique cause. New working priority transaction has no native qualification. No whole delivery or scheduling-policy credit.";
 }
 part resourceEvidence:EvidenceUse {
  ref part :>> component=syncSlot;
  attribute :>> observation="producer-scoped;native-scoped;whole-open";
  attribute :>> boundary="Retained candidate artifacts and scoped checks are observations, not current working-tree admission or fourth-result completion. Existing temporal models discharge separate bounded histories.";
 }
 part propagationEvidence:EvidenceUse {
  ref part :>> component=propagationExit;
  attribute :>> observation="propagation-exit-open;owner-closure-native;owner-cycle-rejection";
  attribute :>> boundary="Source-scoped least-closure native and same-case control records must qualify separately from historical failures. QNT owns temporal custody; source proof owns general functional graphs; Lean retains existing frame/root spatial obligations.";
 }
 part productEvidence:EvidenceUse {
  ref part :>> component=product;
  attribute :>> observation="product-baseline-delta;product-fxmul-attribution;root-build-reproduction;numeric-phase-comparison;compiled-composed-properties;gerbil-whole-consumer;gerbil-map-consumer;bach-executable;gerbil-native-completion";
  attribute :>> boundary="Source-relative assertion attribution and composed property coverage remain distinct from failed cold-budget contracts and missing whole Gerbil acceptance";
 }
 part releaseEvidence:EvidenceUse {
  ref part :>> component=release;
  attribute :>> observation="release-default-matched;compiled-release-population;compiled-global-storage-population;release-p2-incomparable";
  attribute :>> boundary="Default-placement valid p1/p2 samples and explicit-placement failed baseline have distinct workload identities; no full release/build or byte-unit admission";
 }
 part def TemporalUse {
  ref part component:Adapter;
  attribute source:String;
  attribute obligation:String;
  attribute nativeBoundary:String;
  attribute leanBoundary:String default = "Existing spatial/frame obligations; no duplicate temporal proof";
 }
 part syncSlotHistory:TemporalUse {
  ref part :>> component=syncSlot;
  attribute :>> source="models/gambit/sync_slot_retained_resources.qnt";
  attribute :>> obligation="initFixed safe; repeated initialization, child destruction and undrained VM destruction mutants violate safe";
  attribute :>> nativeBoundary="retained-resource-native.json and ordered-word-source-refinement.json: actual libc attempts, acquired bits, receiver join, sender-tail lifetime and final VM owner";
 }
 part globalStorageHistory:TemporalUse {
  ref part :>> component=globalStorage;
  attribute :>> source="dev/refactoring/modern-c/models/quint/runtime_roles.qnt::root_dispatch";
  attribute :>> obligation="Reuse beginWrite/endWrite/freezeOrigin/publish/claim/enter/finish/seal/drain for VM page-domain shards. Directory/native allocation is preparation before endWrite; failed preparation publishes no new logical binding. Unknown result retains VM page custody. Do not add a duplicate temporal machine.";
  attribute :>> nativeBoundary="Source refinement must establish append-only directory publication, one physical page per key, no use after cleanup, exact dense page partition, both real publisher cursors, and moving ordinary/primitive roots. New global-storage.scm crosses the historical registration boundary; not exhaustive allocation-fault or C11-order validation.";
  attribute :>> leanBoundary="Existing RuntimeRoles CompleteCensus, TaskCoverage, AdapterFaithful, completeRootVisit, distinctOriginsNoDuplicateCell and currentAddressCovered only. Supply native distinct page/cell, range coverage and lifetime premises; Lean does not prove scheduling or malloc success.";
 }
 part syncPopulationHistory:TemporalUse {
  ref part :>> component=syncSlot;
  attribute :>> source="models/gambit/gc_sync_membership.qnt";
  attribute :>> obligation="Use actual admitted population for parked roots and next round; initFixed safe, old/early-scan/target-population/early-resume mutants violate safe";
  attribute :>> nativeBoundary="current-official.json and retained-resource-native.json: actual resize, GC, partial creation, unknown join and healthy VM evidence; model is not C memory-order proof";
 }
 part queuePriorityHistory:TemporalUse {
  ref part :>> component=queuePriority;
  attribute :>> source="models/gambit/btq_operations.qnt";
  attribute :>> obligation="Tree topology/balance assumes exclusive queue/key mutation; the source adapter must validate the full affected lock set and no-GC closure; scoped native cases do not discharge arbitrary raw writes or whole-product obligations";
  attribute :>> nativeBoundary="physical-writer-inventory.json and priority-writer-boundary.json remain unclosed; no inferred causal trace or new Lean schedule";
 }
 part ownerPropagationHistory:TemporalUse {
  ref part :>> component=propagationExit;
  attribute :>> source="dev/refactoring/modern-c/models/quint/priority_propagation.qnt";
  attribute :>> obligation="initSplit retains lost-debt counterexample; initCyclic retains nonterminating commit/GC counterexample. initClosure separates solve then root/owner publications and checks least cycle closure plus finite-domain join laws. Weak-fair completion is a defined temporal obligation, not established by bounded simulation. No duplicate tree topology or Lean layout proof.";
  attribute :>> nativeBoundary="The C adapter must preserve complete graph leases, canonical non-NaN producers, private constants excluding internal waiters, finite prefix/cycle loops and once-only publication. Two-node QNT/finite key domain is an abstraction, not arbitrary-R proof or C memory-order proof. Native replay/shrink, emitted closure and source argument supply independent evidence.";
 }
 part nativeCompletionHistory:TemporalUse {
  ref part :>> component=product;
  attribute :>> source="models/build/incremental_build.qnt";
  attribute :>> obligation="Existing start/finish/publish/reuse stages: a complete module program maps to the existing producer unit; its generated phases remain owned outputs, never standalone frontend completion. Successful guarded invoke maps to task finish; parent quiescence, stable provider and header snapshots plus journal registration map to publish. Invalidation or unknown process result cannot publish. These mappings are refinement obligations, not a claim that integer signatures model arbitrary macro/eval or dynamic-loader behavior.";
  attribute :>> nativeBoundary="Actual GSC completion, GCC-MD paths relative to native output directory (_gsclib.scm gambuild output-dir), same-context cold/warm replay and complete downstream consumers are required. Journal replay must find the original completed witness. General macro/native-I/O closure stays unqualified. Complete managed module programs must satisfy dependency closure and immutable completion witnesses; no duplicate QNT scheduler or Lean temporal proof.";
 }

 // Observational boundaries, not a claim that the current compiler publishes
 // independently reusable intermediate-stage results.
 part def CompilerPhaseBoundary {
  ref part runtimeConsumer:Adapter;
  attribute stage:String;
  attribute phaseStatus:String;
  attribute sourceAnchor:String;
  attribute requiredWitness:String;
  attribute assuranceBoundary:String;
 }
 part def CompilerPhaseTransfer {
  ref part producer:CompilerPhaseBoundary;
  ref part consumer:CompilerPhaseBoundary;
  attribute condition:String;
  attribute proofOwner:String;
 }
 part def PhysicalUnitContract {
  ref part semanticProducer:CompilerPhaseBoundary;
  ref part nativeConsumer:CompilerPhaseBoundary;
  attribute producer:String;
  attribute consumer:String;
  attribute semanticOwner:String;
  attribute hostOwner:String;
  attribute preserved:String;
  attribute foreignBoundary:String;
  attribute retirement:String;
  attribute qualification:String;
  attribute costBoundary:String;
 }
 part compilerAudit {
  ref part delivery=GambitPendingCuts::schedulerDelivery;
  ref part buildSupport=GambitPendingCuts::buildDelivery;
  attribute phaseMembers:String="managedEmission;generation;semanticGraph;initializerProjection;cFrontend;nativeConstruction;settlement;libraryOrder";
  attribute transferMembers:String="emissionToGeneration;generationToFrontend;nativeToSettlement;settlementToLibraryOrder;generationToSemanticGraph;semanticGraphToSettlement;settlementToInitializerProjection;initializerProjectionToLibrary";
  attribute allNativeResultsVerified:Boolean=false;
  attribute parentQuiescent:Boolean=true;
  attribute mayPublish:Boolean=allNativeResultsVerified and parentQuiescent;
  attribute compilerUnitAuthority:String="GambitModernCCommitAdmission::compilationUnit";
  attribute boundary:String="Current source-owned physical-unit policy completes all326 stdlib modules under the unchanged profile. Whole library/downstream and matched release remain open. Runtime request ownership is distinct from compiler placement. No alternate profile, new executor or duplicate QNT/Lean model.";
  part physicalUnit:PhysicalUnitContract {
   ref part :>> semanticProducer=GambitRequestProduct::compilerAudit::generation;
   ref part :>> nativeConsumer=GambitRequestProduct::compilerAudit::nativeConstruction;
   attribute :>> producer="gsc/_t-c-1.scm:targ-dump completes procedure scanning before targ-plan-compilation-unit; targ-heap-dump and targ-dump-prc consume that read-only plan";
   attribute :>> consumer="include/gambit.h.in:HOST_LAYOUT_PROCEDURES selects the existing multiple-host calling protocol before module code; configured profile and compiler optimization flags are unchanged";
   attribute :>> semanticOwner="Scheme owns procedure order, control-point allocation, FrameSpec, root materialization, checks and continuation semantics. This C-target plan is not the complete backend-neutral HostGraph extraction";
   attribute :>> hostOwner="A GVM procedure in a unit without module-level C interfaces owns one physical C host; the module retains one translation unit for shared constants, bindings and initialization. Inline c-code still uses its existing local primitive contract; this classification does not prove absence of C or side effects. A large procedure and whole-unit preprocessing remain unbounded";
   attribute :>> preserved="The plan retains the exact procedure-list identity and label count; emission rejects added control points. FrameSpec contents and descriptors are emitted by existing consumers. Tail/GC/multi-shot behavior still requires native admission, not an equality assertion";
   attribute :>> foreignBoundary="Any embedded C declarations, procedures, initializers or objects retain configured hosts until qualified. Legacy bootstrap C without a declaration also retains its configured host layout; no synthetic threshold or command-line override";
   attribute :>> retirement="For eligible units only, configured unlimited single-host aggregation loses physical placement authority. Existing label/return/frame macros, module setup, foreign hosts and portable runtime remain; no claimed universal C-emitter retirement";
   attribute :>> qualification="Source tree40d098f7972e62c591a2d716876cdb1b44e6ca59: full from-scratch508.827736s and stock core28.840812s passed in the same workspace under the unchanged600s outer limit. Forty native checks passed:2387 FrameSpec checks,306 frame cases,290 layout fixtures,15 physical-plan assertions, original mixed-FFI frames and pure-Scheme map/multi-shot/dynamic-wind p1/p2 controls. Complete Gerbil/release acceptance remains pending";
   attribute :>> costBoundary="No measured whole-build speedup yet. Added per-unit plan and procedure-host boundaries may increase call transfers and code size. Compare completed same-profile consumers, runtime work and peak memory; no gain ratio from a censored baseline";
  }
  part initializerHostPartition {
   ref part producer=GambitRequestProduct::compilerAudit::physicalUnit;
   attribute logicalIdentity:String="Retain one original INTRO and the same contiguous logical label order and offsets. setup.c:___subprocedure_parent_intro walks back to INTRO and ___subprocedure_id derives the logical index from that offset. Preserve return FrameSpec and OFD order.";
   attribute placement:String="Map each admitted PointId to one physical host and host-local entry. A host boundary must not introduce a logical INTRO. C setup consumes host-local entries, while the logical label table and frame descriptors remain independently ordered.";
   attribute transfer:String="Local GOTO and fallthrough remain inside a host. A cross-host destination needs an addressable physical entry and the complete live GVM state materialized before dispatch. A C-only destination must remain private or the cut is refused; inserting a logical label would change procedure IDs. Prove this for computed goto and portable switch, including unknown destinations. Refuse a cut through C temporaries or a partial frame.";
   attribute setup:String="setup_module_fixup currently refreshes the goto table on host change and advances a cursor through label order. Consecutive physical fragments can share a logical INTRO, but a returning host run, a mismatched table count, or a wrong switch base must be rejected by the emission contract.";
   attribute counterexample:String="mvp-gsc-tail-creator-negative.json: both arms reject the non-tail exception, but Scheme source outline changes the creator from _test# to a synthetic procedure. It does not qualify as an identity-preserving host split.";
   attribute cutCensus:String="mvp-gsc-host-cut-census.json: every balanced contiguous split in four candidate initializers crosses explicit GOTOs to private labels. Each zero-crossing cut leaves only the last 127 or 129 emitted bytes. Plan placement over the control-flow graph before C text emission; emitted label order is not a partition algorithm.";
   attribute blockPlacement:String="mvp-gsc-private-block-co-placement.json gives a necessary grouping for the selected private edges and conservative private fallthrough. The largest component ranges from 10.48% to 72.41% of the emitted initializer body. Use this to select the first real CFG plan. Value-entry fallthrough, macro edges, liveness and register writeback remain open.";
   attribute cfgPlacementEvidence:String="mvp-gsc-cfg-placement-constraints.json groups direct GOTOs and conservative fallthrough on real emitted initializer bodies. Large cases have many components even before admitting poll/check transfers. Place components as units and preserve their original internal order; verify C local liveness and implicit macro edges before emission.";
   attribute cfgNativeControl:String="mvp-gsc-cfg-placement-native.json: native four-host placement of conservative emitted CFG components passed original f64vector and concatenate assertions. Host-local GOTOs and textual fallthrough stay together, logical label descriptors stay ordered. Diagnostic C transformation only; producer-driven placement and suite costs remain open.";
   attribute cfgGeneratedControl:String="mvp-gsc-generated-cfg-heavy.json: GSC places structured instruction components into four hosts before emitting C. Unmodified emitted files passed original f64vector and concatenate assertions in both arms. Native compilation fell 35.8% and 23.8% in these single pairs. Scope/hidden-edge admission, total generation cost and population acceptance remain open.";
   attribute singleEmission:String="mvp-gsc-single-layout-heavy.json: compiler-local request selects one layout before planning and C emission. Indexed descriptor is emitted by the producer, with no GCC option delta. Original assertions pass for both matched arms; full cohort and supported-edge admission remain open.";
   attribute hostEntryMap:String="A noncontiguous physical host can recur in the logical label sequence. Replace the setup cursor assumption for admitted split units with a checked logical PointId to physical host and local entry map. Use that local selector for switch dispatch too. Keep frame descriptors and logical label offsets on the original traversal.";
   attribute plannerIndex:String="The private plan indexes placements by procedure identity and assigns entries to selected hosts in one ordered traversal. Host choice, instruction order, local slot numbering and refusal semantics remain fixed. Bounded placement parity is compiler-local evidence; regenerated artifacts and exact-source native acceptance are still required.";
   attribute scopedNativeEvidence:String="mvp-gsc-indexed-cross-host-execution.json witnesses real execution of moved fxorc2 return 212. A delegating pair binding selects the original slow branch. mvp-gsc-indexed-multishot.json adds two post-GC restorations at the moved return with a checked live vector. mvp-gsc-indexed-creator.json compares creator procedure and subprocedure ID at capture and after each GC in both arms. Diagnostic relink and hand-adjusted C only; producer placement remains open.";
   attribute emittedEntries:String="mvp-gsc-indexed-generated-native.json: a relinked GSC emitted all 326 slots of the original fxorc2 fixture with no C rewrite. Legacy and indexed variants ran on the relinked setup. The old setup refused the indexed descriptor. Automatic physical partitioning and whole-cohort admission remain open.";
   attribute automaticReturnControl:String="mvp-gsc-auto-return-host.json: actual GSC emits an isolated return block selected from structured register moves and POLL. Native creator ID and two post-GC restores pass. The default profile and unsupported cuts retain old placement; the rule alone is not expected to close the suite throughput gap.";
   attribute nativeRequired:String="Repeat the creator control, original ca_dr assertions, live root and multi-shot resumes across a physical cut, and the full 408-case GSC under the original deadline. Candidate compiler and runtime products must share the same source identity.";
   attribute admitted:Boolean=false;
  }
  part managedEmission:CompilerPhaseBoundary {
   ref part :>> runtimeConsumer=product;
   attribute :>> stage="Closed Gerbil emission bundle before native task drain";
   attribute :>> phaseStatus="Explicit-argument real-GSC lifecycle controls pass. Actual stdlib histories expose repeated coordinator activation before four generation resumes; the coordinator now has a planning-only prefix path. The installed reader/coordinator passes3 actual issued payloads and192 native cases with ordered dependency waits and forbidden import/completion callbacks. Complete downstream replay remains required";
   attribute :>> sourceAnchor="gerbil_compile_products.ss:compile-product-generation-close/restore/module; gerbil_build/module_generations.py:retain_generations/prepare_generations; make_source.py:_generation_make_source; generation_planning.py:check_generation_planning";
   attribute :>> requiredWitness="Actual closed managed emitter, exact source/dependencies/cwd/native requests/generated outputs, private SSI, successful witness verification and physically quiescent producer before continuation issuance";
   attribute :>> assuranceBoundary="A continuation resumes only this managed module program. It grants neither module completion nor public SSI; arbitrary macro/eval effects and unobserved old files cannot acquire this credential. No new environment variable, configuration layer or executor";
  }
  part generation:CompilerPhaseBoundary {
   ref part :>> runtimeConsumer=product;
   attribute :>> stage="GSC Scheme-to-C generation";
   attribute :>> phaseStatus="C retained; no successful reusable generation-stage receipt";
   attribute :>> sourceAnchor="gsc/_t-c-1.scm:targ-dump-module; existing gxc native request invokes GSC on the closed Scheme output";
   attribute :>> requiredWitness="Stable actual inputs, compiler/options/dependencies and completed producer-owned generation, not file existence";
   attribute :>> assuranceBoundary="Generation duration and clean baseline output equivalence remain unqualified. Retained C can support a diagnostic only.";
  }
  part semanticGraph:CompilerPhaseBoundary {
   ref part :>> runtimeConsumer=product;
   attribute :>> stage="Semantic context graph capture";
   attribute :>> phaseStatus="Actual generated .init outputs observed; codec256 and three real source/SSI comparisons pass. Cold new cohort and its continuation remain failed parents; individually witnessed complete programs retain graph custody.";
   attribute :>> sourceAnchor="compile-product-initialization-graph after compile-meta-code, under the original driver mutex; semantic-context-graph uses local slots reserved before child traversal";
   attribute :>> requiredWitness="The exact source context and phase/template edges; output bytes registered in the same module state and bound to source/dependency identities. A captured graph alone is not module/native completion.";
   attribute :>> assuranceBoundary="Graph capture is separate from executable macro activation by initialization planning. Current issuer conservatively requires full module/native completion to expose a ready graph. Closed generation may retain a private graph without publishing SSI or granting completion. No repeated QNT/Lean model.";
  }
  part generationToSemanticGraph:CompilerPhaseTransfer {
   ref part :>> producer=generation;
   ref part :>> consumer=semanticGraph;
   attribute :>> condition="After actual meta-code generation, capture getter-visible context identity, prelude/import/export/set edges and signed phases without changing emitted code";
   attribute :>> proofOwner="Source codec representation relation and native finite/real-source cases; not a new temporal Lean proof";
  }
  part semanticGraphToSettlement:CompilerPhaseTransfer {
   ref part :>> producer=semanticGraph;
   ref part :>> consumer=settlement;
   attribute :>> condition="Registered .init writer and exact bytes remain owned alongside pending SSI/native tasks. Failed generation may retain only a closed generation continuation. Native drain and quiescent completion precede graph-ready issuance";
   attribute :>> proofOwner="Existing incremental_build.qnt generation/native/publication states; module_generations and module_products source adapters plus actual producer receipts. No duplicate schedule proof";
  }
  part initializerProjection:CompilerPhaseBoundary {
   ref part :>> runtimeConsumer=product;
   attribute :>> stage="Pure initializer graph projection and slot view";
   attribute :>> phaseStatus="Native256 projection/alias/phase/GC/cycle controls and three real source/SSI comparisons pass. Installed119-root planning completes161 entries in3.113309s with native global cells18042 unchanged. Raw full-graph/class reconstruction controls time out at30s and remain failed.";
   attribute :>> sourceAnchor="gerbil_initialization_view.ss:initialization-graph-project/view/resolve; initialization_views.py:materialize_views/planning_views; original order-modules algorithm behind explicit getter operations";
   attribute :>> requiredWitness="Immutable complete-program semantic input; source/transformation/output byte identities; closed native projection return or individually observed closed prefix; matching ready transport. Context identity and template arithmetic must be preserved, not guessed from all-phase dependency IDs.";
   attribute :>> assuranceBoundary="A graph view never grants module/native completion. Data bytes are not RSS.119 roots are not full library acceptance. Same600/575/120/30s bounds and existing environment names; no capacity increase, new profile or executor.";
   attribute representationArgument:String="Conditional source argument, not a Lean theorem: non-label wrapper edges contract to the same ordered context targets using the library's original phi/iphi arithmetic. Remove only later duplicate references to the same context slot; distinct equal-ID contexts remain distinct. Reserve projected slots before descending so active cycles keep back edges and cannot acquire premature completion. The final initialization traversal remains the original checked algorithm.";
   attribute publicationArgument:String="Only issuer-validated complete module graphs enter projection. A closed view prefix is retained after known writer/group stop, but the failed parent remains failed. Ready references distinguish initialization-view derivations from original module outputs. A reader with unknown termination retains its immutable view and transport. Existing incremental_build.qnt owns artifact completion/custody histories; no duplicate Lean schedule model.";
  }
  part settlementToInitializerProjection:CompilerPhaseTransfer {
   ref part :>> producer=settlement;
   ref part :>> consumer=initializerProjection;
   attribute :>> condition="Original semantic graph remains bound to a coherent native/interface program; projection may issue only its own data result with input/contract/output identities";
   attribute :>> proofOwner="Actual module witness validation, native metadata producer prefix and Python issuer/refusal controls; existing QNT completion discipline";
  }
  part initializerProjectionToLibrary:CompilerPhaseTransfer {
   ref part :>> producer=initializerProjection;
   ref part :>> consumer=libraryOrder;
   attribute :>> condition="Issue typed initialization-view transport only after closed data derivation; library uses its original traversal with pure slot getters, preserving context identity, phase edges and active cycles";
   attribute :>> proofOwner="Native PBT/replay/shrink and real source/SSI comparisons plus conditional representation argument; not a repeated temporal Lean proof";
  }
  part cFrontend:CompilerPhaseBoundary {
   ref part :>> runtimeConsumer=product;
   attribute :>> stage="C preprocessing and parsing";
   attribute :>> phaseStatus="Original-layout syntax-only control passes8.640044s; preprocessing reports2.93s";
   attribute :>> sourceAnchor="Configured GCC16.2, exact retained connection~1.c, original header/layout, direct argv receipt";
   attribute :>> requiredWitness="Successful frontend-only process with stable C/header/tool identities";
   attribute :>> assuranceBoundary="No native object, optimization/link completion, runtime execution or exact whole-run fraction follows";
  }
  part nativeConstruction:CompilerPhaseBoundary {
   ref part :>> runtimeConsumer=product;
   attribute staticUnitCustody:String="The original libgerbil work group produces370 Scheme-to-C and370 C-to-object units. A typed nine-field request identifies context, role, program, argv, cwd, source, source blob, output and contract. Existing process-status and close establish result custody; immutable completion plus stable source/header identities establish reuse. Batch failure retains independently closed units but cannot issue parent completion. Existing incremental_build.qnt start/finish/publish/reuse owns the temporal distinction; no new Lean temporal obligation is introduced.";
   attribute compilerServiceReadiness:String="The same driver source may become one original gxc-produced native service. Input stability, output alias exclusion, quiescent original producer, immutable journal custody and a real native module/protocol smoke are all required before publishing its ready transport. Source loading remains the bootstrap path. Host-role and downstream-role classification must precede effective input equality; observing target-output changes does not authorize relabeling products. Both gxc and child GSC must use the existing p1 profile because original run.sh replaces GAMBOPT. Readiness and whole downstream admission are separate.";
   attribute :>> stage="Full C-to-module construction, including its frontend";
   attribute :>> phaseStatus="Current d07/987c59dd completes740 static units and all four original Make consumers; historical1b/7308 remains a separate source period. Pure Scheme generation chooses per-procedure physical hosts; embedded-C retains configured layout. Current ca_dr first observed C pair differs only by HOST_LAYOUT declaration. Isolated30s native compilation is censored in both roles; current-header u16vector layout variants both compile and pass. Do not infer all77 coverage losses or a universal host-layout speedup from this control.";
   attribute :>> sourceAnchor="gsc/_gsclib.scm:gambuild; configured gambuild-C; configure.ac:single-host; _gambit/configuration.h.in";
   attribute :>> requiredWitness="Original-profile natural compiler exit, exact object/dependencies and owned output identity";
   attribute :>> assuranceBoundary="Both timeouts are censored. One-second alias-solver observation does not establish whole-run pass percentages or all causes. Baseline clean Gerbil pipeline causality is open. Historical flag-only alternate-host output cannot enter original-profile products. The current producer-owned physical-unit declaration is a source change under the unchanged profile, not that diagnostic override.";
  }
  part settlement:CompilerPhaseBoundary {
   ref part :>> runtimeConsumer=product;
   attribute :>> stage="Module job drain, private SSI publication and whole-module witness";
   attribute :>> phaseStatus="Current d07f67b4/987c59dd ABI326 complete stdlib programs,740 static native units and natural stdlib/libgerbil/lang/tools exits. Prior partial/failed parents retain separate source periods and completion prefixes. Complete cost/coverage attribution remains a different gate.";
   attribute :>> sourceAnchor="gerbil_compile_products.ss:compile-product-drain/publish/module; gerbil_build/compiler_products.py:_stdlib_compile_products";
   attribute :>> requiredWitness="All native results and outputs verified before SSI publication; Python issuer additionally requires quiescent parent";
   attribute :>> assuranceBoundary="A disappeared private SSI can recover matching renamed bytes only into private generation custody; the original worker still joins native jobs before interface publication. Borrowed products must match original admission and immutable issuer witnesses in the same context. Later same-boot birth-bound empty group/session observation closes writer custody without repairing incomplete streams or failed parent outcomes. Settlement never grants whole-stage completion. Existing incremental_build.qnt owns temporal completion; these actual source adapters require refinement and native validation, not a duplicate Lean schedule proof";
  }
  part emissionToGeneration:CompilerPhaseTransfer {
   ref part :>> producer=managedEmission;
   ref part :>> consumer=generation;
   attribute :>> condition="Only source-bound closed generation witnesses may supply planning identity/dependencies before the original worker restores immutable code and private SSI into the same managed program. The coordinator always enqueues this work and never posts module completion for a generation prefix. Original native argv and CPU quota remain. All native work must succeed and source/dependency identities must still match before public SSI publication";
   attribute :>> proofOwner="Existing incremental_build.qnt owns temporal completion and custody; real helper capture/resume/source-guard controls refine the implementation boundary. Existing Lean FrameSpec scope is unchanged; no duplicate schedule proof";
  }
  part libraryOrder:CompilerPhaseBoundary {
   ref part :>> runtimeConsumer=product;
   attribute :>> stage="Library runtime dependency ordering before static compilation";
   attribute :>> phaseStatus="Current d07f67b4/987c59dd consumes326 complete program graphs and326 compact views; original stdlib/libgerbil/lang/tools all naturally exit under unchanged limits. Current incremental stage times15.974612/46.084959/8.684437/94.919886s;740 static units complete,686 reused and54 executed in the closing library attempt. Historical1b/7308 measurements remain distinct. Tools registration pressure is resolved by the real VM-storage/root-index separation, not a raised capacity. Historical119-root/58fe43 planning and20000-limit failures remain documentary controls. This is not a cold matched build or4/4 release admission.";
   attribute :>> sourceAnchor="gerbil_library_order.ss keeps the checked original traversal behind explicit getter operations. gerbil_initialization_view.ss owns the pure projection/slot adapter. initialization_views.py owns derived view custody; library_source.py installs only consumer-owned code, preserving the native producer identity.";
   attribute :>> requiredWitness="Same complete-program input graph and independently closed derived view; exact source/contract/output identities and ready transport. Native256 properties and three real SSI controls precede installed planning. No decoded expander scopes, replayed macro phase, guessed all-phase order or enlarged global table.";
   attribute :>> assuranceBoundary="Scoped119-root planning and one wall observation are not complete library/whole release admission. Global instrumentation has observer effects. Historical failures remain source-period-specific. Native construction continues under the original bounds and exact producer key.";
   attribute completionOwner:String="Each find-deps root owns an eq-keyed completion table over actual context objects. A module/prelude gets a token only after its children return. The original global module-ID fold remains after root completion. Distinct objects sharing an ID are not merged by the completion table.";
   attribute finiteOrderArgument:String="CONDITIONAL SOURCE ARGUMENT, not a Lean-checked theorem: with immutable outgoing context/phase edges and pure getters, each repeated completed object subtree emits only IDs already present in its first postorder trace. Erasing later copies preserves stable-first-ID projection. Induction on the first finite subtree establishes the original final initialization list, including distinct-context aliases. The global visited set is unchanged during each root walk. Exact phase and import-set-template bodies are pinned by the inverse.";
   attribute cycleArgument:String="Completion is black-only, after child return; no in-progress/gray node is skipped. An uncut active cycle cannot create a completion token and cannot return or publish an order. Phase/global exclusion cuts remain original. core-import-module still raises Cyclic expansion for its original path condition, and runtime loader loading/wait/error handling is untouched. This preserves existing cycle behavior; it does not solve cyclic initialization or invent an SCC order.";
   attribute costBoundary:String="For each finite root: one expansion per distinct context object, plus actual wrapper/template edge work. Additional managed hash storage is O(distinct contexts); dependency trace storage loses repeated completed subtrees. Total root/cold-build latency and peak memory are unmeasured. The14.307715s failed libgerbil process is not a performance improvement over its previous censored timeout.";
   attribute properties:String="Actual original/candidate function finite equivalence, graph encode/restore identity and order, phase/prelude/alias/forced-GC properties pass256 cases; ID-keyed mutation shrinks to3 edges. Actual build-config/time-timeout/socket source versus SSI initialization order comparisons pass with20/22/36 modules. Root phase-zero evaluation is not forced, matching compile-module/order-modules. Existing QNT owns completion/custody histories; Lean is not duplicated.";
   attribute rejectedShortcut:String="The existing current-expander-eval hook was tested only in a disposable diagnostic process. Suppressing evaluation with a trapping syntax value reaches QUERY-CALLED-UNQUALIFIED-MACRO during real module expansion. This disproves adopting a blanket no-eval query as an equivalent link graph. Production source retains the normal evaluator. Graph certificates must be produced from real semantic contexts, including alias identity and phase/template edges, rather than invented from all-phase reuse metadata.";
   attribute semanticArtifact:String="Each .init carries module-initialization tag, exact compiler context, module ID and an immutable slot graph. Slots are reserved before descending; shared references and back edges retain identity. The graph has no executable callbacks or invented import edges.";
   attribute issuerBoundary:String="Graph bytes are included in compile-product-output and original module-completed output identities. Native tasks drain and source/dependency checks precede SSI publication; Python additionally requires producer quiescence and immutable module completion witnesses before exposing a ready graph path. Failed or unknown native production cannot authorize graph-based whole completion.";
   attribute readerBoundary:String="The module_product_scope lease spans libgerbil, lang and tools and restores the existing compile-product fields only after the last consumer or failure. It requalifies complete programs, installs immutable slot views without reconstructing expander objects, and keeps the original ordering traversal. The first managed Make metadata read initializes the existing gxc catalogue only if absent; it must never overwrite an activated native driver writer. Every static native unit has an exact context/role/program/argv/cwd/source/output/contract request. The original invoke-process status and close precede immutable completion; native source-effect and header closure checks precede reuse. Unknown writers or failed whole parents cannot authorize completion. An AOT driver may replace repeated source activation only after the same-source original gxc returns, inputs remain unchanged, outputs have no aliases and a real compiled protocol smoke closes native jobs and module publication. A ready object path alone is insufficient. Unmanaged builds retain their original resolver.";
   attribute benefitCondition:String="Planning native global growth becomes independent of loaded library macro definitions: only the fixed driver/codec is executable, while graph contexts are managed data. Capture adds O(V+E) serialization and disk storage per generated module, plus managed restoration memory. Warm planning reuses the same graph/native/interface witness. Whole wall time and peak benefit remain unmeasured until complete native consumers and matched baseline pass.";
  }
  part settlementToLibraryOrder:CompilerPhaseTransfer {
   ref part :>> producer=settlement;
   ref part :>> consumer=libraryOrder;
   attribute :>> condition="Verified complete stdlib modules may supply stable interface identities. Their all-phase reuse dependency list does not authorize a phase-0 ordered link plan or public library completion";
   attribute :>> proofOwner="Existing incremental_build.qnt retains completion and invalidation custody. Library-order semantic refinement requires source and actual consumer evidence; existing FrameSpec Lean laws do not prove module ordering. No duplicate temporal or spatial model";
  }
  part generationToFrontend:CompilerPhaseTransfer {
   ref part :>> producer=generation;
   ref part :>> consumer=cFrontend;
   attribute :>> condition="Stable generated tokens and complete producer input cut; diagnostic retained-file access does not issue reuse";
   attribute :>> proofOwner="Existing incremental_build.qnt owns temporal reuse/custody; actual generator-to-file refinement remains source/native evidence";
  }
  part nativeToSettlement:CompilerPhaseTransfer {
   ref part :>> producer=nativeConstruction;
   ref part :>> consumer=settlement;
   attribute :>> condition="Every owned native request succeeds under the required profile; unknown or timed-out output retains custody and cannot publish";
   attribute :>> proofOwner="Existing incremental_build.qnt and publisher_contract.qnt; existing FrameSpec/RuntimeRoles Lean retain spatial and frame laws. No duplicate schedule proof.";
  }
 }

 attribute stage:String="Whole fourth responsibility replacement; all predecessor, source/native cases and five gates must be admitted before the single progress increment. Cold comparison is an explicitly separate build follow-up, never a speedup claim.";
 attribute sourceCases:String="owned-wait-state;fifo-write-authority;finite-priority-closure;vm-global-slots;consumer-prerequisites";
 attribute requiredCases:String="multi-shot-waits;mailbox-queue;priority-cycles;root-relocation;unknown-join;official-consumers;gerbil-consumers;matched-cost;native-replay-shrink";
 part submission:GambitCommitGates::SubmissionUnit {
  attribute :>> kind="integration";
  attribute :>> result=GambitModernCOutcomes::execution.id;
  attribute :>> progressDelta=1;
  attribute :>> supportPaths="";
 }
 part def Need { ref part gate:GambitCommitGates::Gate; attribute id:String; attribute method:String; attribute artifact:String; attribute scope:String; }
 part tests:Need { ref part :>> gate=GambitCommitGates::tests; attribute :>> id="REQUEST-NATIVE"; attribute :>> method="native"; attribute :>> artifact="evidence/research/retained/modern-c/request-product/submission/receipt.json"; attribute :>> scope="Exact canonical/native/generated source equivalence, all original and Gerbil consumers, real replay and predecessor regressions. Common baseline failures remain explicitly classified, never passed."; }
 part learning:Need { ref part :>> gate=GambitCommitGates::learning; attribute :>> id="REQUEST-LEARNING"; attribute :>> method="source-analysis"; attribute :>> artifact="dev/refactoring/modern-c/delivery-contract.org"; attribute :>> scope="Finite frozen owner solve, distinct waiting/service activations, single queue authority and VM-local mutable global storage; measured time and memory costs remain explicit."; }
 part process:Need { ref part :>> gate=GambitCommitGates::process; attribute :>> id="REQUEST-PROCESS"; attribute :>> method="source-analysis"; attribute :>> artifact="dev/refactoring/modern-c/delivery-contract.org"; attribute :>> scope="One whole fourth integration with12 programme obligations, five source and nine native groups; no independent SMP or cold-build progress."; }
 part models:Need { ref part :>> gate=GambitCommitGates::models; attribute :>> id="REQUEST-MODELS"; attribute :>> method="source-refinement"; attribute :>> artifact="evidence/research/retained/modern-c/request-product/submission/source-review.json"; attribute :>> scope="Native OpenSysML selects the complete unit and obligations; ASCENT checks actual evidence identities. Existing QNT owns histories, Lean only existing spatial laws; neither is duplicated."; }
 part questions:Need { ref part :>> gate=GambitCommitGates::questions; attribute :>> id="REQUEST-QUESTIONS"; attribute :>> method="source-analysis"; attribute :>> artifact="dev/refactoring/modern-c/delivery-contract.org"; attribute :>> scope="What terminates cyclic propagation, who owns every queue mutation and stopped writer, how are multi-shot roots preserved, what is actually faster or slower, and what remains outside this REV?"; }
}
