package GambitModularSmpValidation {
  private import ScalarValues::*;
  part writerAuthorization:SharedContract {
    attribute :>> id="write-authority";
    attribute :>> source="vendor/gambit/lib/write_authority.c";
    attribute :>> anchor="___write_authority_try_handoff";
    attribute :>> invariant="One generation-bound packed word couples admission and live/spent writer roles. Transfer requires closed and drained and installs both owner permits atomically. Shared C controls compile the actual implementation; the Scheme caller fingerprints private headers, memory modules and component sources with exact-path batched hashes";
    attribute :>> open="A permit is not a root, VM-lifetime lease or physical-stop receipt; full generated and foreign writer wiring remains a RootWorkerExit source obligation";
  }
  part writerCoverage:Coverage {
    ref part :>> lane=c3; ref part :>> contract=writerAuthorization;
    attribute :>> scope="Current write-authority C control body, shared GC kernel and actual module linking; no whole writer-closure or shutdown admission";
  }
  ref part orderedWord:GambitOrderedSynchronization::Responsibility=GambitOrderedSynchronization::word;
  ref part stopPublication:GambitOrderedSynchronization::Responsibility=GambitOrderedSynchronization::stop;
  ref part mailboxProtocol:GambitMailboxPublication::Responsibility=GambitMailboxPublication::queue;
  ref part mailboxRootTransfer:GambitMailboxPublication::Responsibility=GambitMailboxPublication::roots;
  attribute sourceLock:String="evidence/research/ordered-sync/initialization/source.lock.json";
  attribute profile:String="evidence/fixtures/gerbil-bazel-build-profile/profile.json";
  attribute runner:String="macos-15";
  attribute hashToolVariable:String="GAMBIT_SMP_SHASUM";
  part def ToolDependency {
    attribute id:String; attribute variable:String; attribute command:String;
  }
  part hashTool:ToolDependency { attribute :>> id="hash"; attribute :>> variable="GAMBIT_SMP_SHASUM"; attribute :>> command="shasum"; }
  part compilerTool:ToolDependency { attribute :>> id="compiler"; attribute :>> variable="GAMBIT_SMP_CC"; attribute :>> command="gcc-16"; }
  part timeoutTool:ToolDependency { attribute :>> id="timeout"; attribute :>> variable="GAMBIT_SMP_TIMEOUT"; attribute :>> command="gtimeout"; }
  part makeTool:ToolDependency { attribute :>> id="make"; attribute :>> variable="GAMBIT_SMP_MAKE"; attribute :>> command="make"; }
  part killTool:ToolDependency { attribute :>> id="kill"; attribute :>> variable="GAMBIT_SMP_KILL"; attribute :>> command="kill"; }
  part developerTool:ToolDependency { attribute :>> id="developer"; attribute :>> variable="GAMBIT_SMP_XCRUN"; attribute :>> command="xcrun"; }
  part cpuTool:ToolDependency { attribute :>> id="cpu"; attribute :>> variable="GAMBIT_SMP_SYSCTL"; attribute :>> command="sysctl"; }
  attribute hashToolContract:String="Caller supplies an existing absolute executable path with the shasum -a 256 -- interface. Freeze it before hashing; record selected path and tool SHA. Missing/invalid input refuses rather than falling back to a fixed system binary; batch validation retains exact paths and all before/after file checks";
  attribute workflow:String="vendor/gambit/.github/workflows/smp.yml";
  attribute ownership:String="Gambit owns independent native CI and fixtures. SMP owns SysML, ASCENT, QNT/Lean links, Org, D2 and evidence; no parent-repository runtime dependency.";
  attribute proofOwnership:String="Existing CS-SCHEDULE QNT owns ordering and permit histories; CS-COHERENCE Lean owns issued-view algebra. Source adapters and native observations do not duplicate either theorem.";
  attribute bootstrapContract:String="One exact-source two-pass bootstrap, original 600-second wall budget; no heap increase, patch import or timeout extension. CI runs modules against its single bootstrapped checkout; local research may use an authenticated existing producer without making a cold-CI claim.";
  attribute failureCustody:String="Unknown or failed origins retain roots and native resources; missing native observations remain open. CI definitions are not remote CI acceptance.";
  part def Lane { attribute id:String; attribute namespace:String; attribute name:String; attribute kind:String; attribute program:String; attribute stdout:String; attribute topology:String; attribute budget:Integer; }
  part callbackExit:Lane { attribute :>> id="gambit.smp.control.callback.nonlocal-exit"; attribute :>> namespace="gambit.smp.control.callback"; attribute :>> name="nonlocal-exit"; attribute :>> kind="scheme"; attribute :>> program="vendor/gambit/tests/sfun-exit.scm"; attribute :>> stdout="CALLBACK-EXIT-PASS direct nested normal gc dynamic-wind\n"; attribute :>> topology="host-managed"; attribute :>> budget=90; }
  part vmLifecycle:Lane { attribute :>> id="gambit.smp.gc.vm-lifecycle.custody"; attribute :>> namespace="gambit.smp.gc.vm-lifecycle"; attribute :>> name="custody"; attribute :>> kind="scheme"; attribute :>> program="vendor/gambit/tests/smp/gc/vm-lifecycle.scm"; attribute :>> stdout="VM-LIFECYCLE-PASS registry owner roots retained-release no-replay healthy-gc\n"; attribute :>> topology="fixture-managed"; attribute :>> budget=90; }
  part vmGlobalReclaim:Lane { attribute :>> id="gambit.smp.gc.vm-lifecycle.global-reclaim"; attribute :>> namespace="gambit.smp.gc.vm-lifecycle"; attribute :>> name="global-reclaim"; attribute :>> kind="scheme-host"; attribute :>> program="vendor/gambit/tests/smp/gc/vm-lifecycle-host.scm"; attribute :>> stdout="VM-GLOBAL-RECLAIM-PASS secondary-ack global-permit duplicate-refusal\n"; attribute :>> topology="fixture-managed"; attribute :>> budget=90; }
  part c3:Lane { attribute :>> id="gambit.smp.gc.root-task.publication-claim-arena"; attribute :>> namespace="gambit.smp.gc.root-task"; attribute :>> name="publication-claim-arena"; attribute :>> kind="kernel"; attribute :>> program="vendor/gambit/tests/gc-root-task.c"; attribute :>> stdout="PUBLICATION-PASS\nCLAIM-RACE-PASS\nCOPY-AUTHORITY-PASS\nARENA-PASS\nARENA-HANDOFF-PASS\nROOT-DOMAIN-RESUME-PASS\nNATIVE-RUN-ABI-PASS\nwrite-authority controls passed\n"; attribute :>> topology=""; attribute :>> budget=180; }
  part c4:Lane { attribute :>> id="gambit.smp.runtime.roles.storage-layout"; attribute :>> namespace="gambit.smp.runtime.roles"; attribute :>> name="storage-layout"; attribute :>> kind="kernel"; attribute :>> program="vendor/gambit/tests/runtime-roles.c"; attribute :>> stdout=""; attribute :>> topology=""; attribute :>> budget=180; }
  part c5:Lane { attribute :>> id="gambit.smp.control.continuation.map-multishot"; attribute :>> namespace="gambit.smp.control.continuation"; attribute :>> name="map-multishot"; attribute :>> kind="scheme"; attribute :>> program="vendor/gambit/tests/frame-continuation.scm"; attribute :>> stdout="FRAME-CONTINUATION-PASS\nHASH-INDEX-OWNER-PASS\n"; attribute :>> topology="fixture-managed"; attribute :>> budget=90; }
  part c6:Lane { attribute :>> id="gambit.smp.gc.frame-roots.single-processor"; attribute :>> namespace="gambit.smp.gc.frame-roots"; attribute :>> name="single-processor"; attribute :>> kind="scheme"; attribute :>> program="vendor/gambit/tests/frame-continuation-roots.scm"; attribute :>> stdout="FRAME-CONTINUATION-ROOTS-PASS\nFORCED-GC-COMPLETE count=11\n"; attribute :>> topology="fixture-managed"; attribute :>> budget=90; }
  part c7:Lane { attribute :>> id="gambit.smp.gc.frame-roots.host-processors"; attribute :>> namespace="gambit.smp.gc.frame-roots"; attribute :>> name="host-processors"; attribute :>> kind="scheme"; attribute :>> program="vendor/gambit/tests/frame-continuation-roots.scm"; attribute :>> stdout="FRAME-CONTINUATION-ROOTS-PASS\nFORCED-GC-COMPLETE count=11\n"; attribute :>> topology="host-managed"; attribute :>> budget=90; }
  part c8:Lane { attribute :>> id="gambit.smp.gc.shared-roots.cyclic-aliases"; attribute :>> namespace="gambit.smp.gc.shared-roots"; attribute :>> name="cyclic-aliases"; attribute :>> kind="scheme"; attribute :>> program="vendor/gambit/tests/smp/gc/shared-roots.scm"; attribute :>> stdout="SHARED-ROOTS-GC-PASS collections=33\n"; attribute :>> topology="host-managed"; attribute :>> budget=90; }
  part c9:Lane { attribute :>> id="gambit.smp.scheduler.mailbox.ordered-shared-values"; attribute :>> namespace="gambit.smp.scheduler.mailbox"; attribute :>> name="ordered-shared-values"; attribute :>> kind="scheme"; attribute :>> program="vendor/gambit/tests/smp/scheduler/mailbox-publication.scm"; attribute :>> stdout="MAILBOX-ROOTS-PASS messages=64\n"; attribute :>> topology="host-managed"; attribute :>> budget=90; }
  part c10:Lane { attribute :>> id="gambit.smp.control.dynamic-wind.multishot-gc"; attribute :>> namespace="gambit.smp.control.dynamic-wind"; attribute :>> name="multishot-gc"; attribute :>> kind="scheme"; attribute :>> program="vendor/gambit/tests/smp/control/dynamic-wind-multishot.scm"; attribute :>> stdout="WIND-RESUME-GC-PASS shots=3\n"; attribute :>> topology="host-managed"; attribute :>> budget=90; }
  part dependencies:Lane { attribute :>> id="gambit.smp.memory.modules.make-invalidation"; attribute :>> namespace="gambit.smp.memory.modules"; attribute :>> name="make-invalidation"; attribute :>> kind="make"; attribute :>> program="vendor/gambit/lib/makefile.in"; attribute :>> stdout="MEMORY-DEPENDENCIES-PASS fragments=25\n"; attribute :>> topology=""; attribute :>> budget=60; }
  part mailboxPermit:Lane { attribute :>> id="gambit.smp.scheduler.mailbox.blocked-cell-roots"; attribute :>> namespace="gambit.smp.scheduler.mailbox"; attribute :>> name="blocked-cell-roots"; attribute :>> kind="scheme"; attribute :>> program="vendor/gambit/tests/smp/scheduler/mailbox-permit-roots.scm"; attribute :>> stdout="MAILBOX-PERMIT-ROOTS-PASS blocked-cell-gc selective-cursor timeout-cleanup\n"; attribute :>> topology="host-managed"; attribute :>> budget=90; }
  part mailboxIdentity:Lane { attribute :>> id="gambit.smp.scheduler.mailbox.concurrent-first-publishers"; attribute :>> namespace="gambit.smp.scheduler.mailbox"; attribute :>> name="concurrent-first-publishers"; attribute :>> kind="scheme"; attribute :>> program="vendor/gambit/tests/smp/scheduler/mailbox-identity.scm"; attribute :>> stdout="MAILBOX-IDENTITY-PASS publishers=8 messages=64 shared-aliases\n"; attribute :>> topology="host-managed"; attribute :>> budget=90; }
  part orderedKernel:Lane { attribute :>> id="gambit.smp.sync.ordered.word-ticket-slot"; attribute :>> namespace="gambit.smp.sync.ordered"; attribute :>> name="word-ticket-slot"; attribute :>> kind="kernel"; attribute :>> program="vendor/gambit/tests/ordered-sync.c"; attribute :>> stdout="ORDERED-SYNC-PASS locks=16384 slots=16384 trylock=2 wrap=1\nORDERED-SYNC-LAYOUT word=64 slot=32 prior-pair=32\n"; attribute :>> topology=""; attribute :>> budget=180; }
  part mailboxStop:Lane { attribute :>> id="gambit.smp.gc.stop.mailbox-epoch-handoff"; attribute :>> namespace="gambit.smp.gc.stop"; attribute :>> name="mailbox-epoch-handoff"; attribute :>> kind="scheme"; attribute :>> program="vendor/gambit/tests/smp/gc/mailbox-epoch-handoff.scm"; attribute :>> stdout="MAILBOX-EPOCH-HANDOFF-PASS workers=4 messages=128\n"; attribute :>> topology="host-managed"; attribute :>> budget=90; }
  part def SharedContract { attribute id:String; attribute source:String; attribute anchor:String; attribute invariant:String; attribute open:String; }
  part sourcePartition:SharedContract { attribute :>> id="source-partition"; attribute :>> source="vendor/gambit/lib/mem.c"; attribute :>> anchor="memory/configuration.inc"; attribute :>> invariant="Original preamble and all payload intervals reconstruct exactly; explicit fragment end markers preserve blank bytes and pass strict patch admission; Make owns the complete include dependency inventory"; attribute :>> open="One translation unit remains; no parallel compilation or reduced macro expansion is established"; }
  part rootAuthority:SharedContract { attribute :>> id="root-authority"; attribute :>> source="vendor/gambit/lib/_mem/root-origins.inc"; attribute :>> anchor="mark_execution_roots"; attribute :>> invariant="Existing collective physically freezes complete origins; epoch and incarnation publish before READY; one owner-bearing CAS grants repair authority; DONE does not alone authorize whole-round resume"; attribute :>> open="Foreign writer admission, unknown-owner stop, reader grace and full carrier retirement remain canonical RootWorkerExit obligations"; }
  part frameRoots:SharedContract { attribute :>> id="frame-roots"; attribute :>> source="vendor/gambit/lib/_mem/continuation-roots.inc"; attribute :>> anchor="mark_captured_continuation_locked"; attribute :>> invariant="Frame descriptors identify ordinary roots separately from structural links; frame access serializes capture/link repair; full multi-shot restoration preserves shared aliases and Scheme dynamic-wind"; attribute :>> open="Existing CS-SCHEDULE QNT and CS-COHERENCE Lean are reused; general C root-map, writer and FFI refinement is not replaced by finite native fixtures"; }
  part arenaReservation:SharedContract { attribute :>> id="arena-reservation"; attribute :>> source="vendor/gambit/lib/_mem/copy-reservations.inc"; attribute :>> anchor="reserve_copy"; attribute :>> invariant="Actual contiguous worker interval is reserved before forwarding; exact unpublished reservation alone may refund; visible forwarding retains initialization and Tail responsibility"; attribute :>> open="Current WorkerArena and W/R source evidence is owned by RootWorkerExit; full physical packing, arbitrary unknown CAS outcomes and whole round-capacity proof remain open"; }
  part sharedScheduler:SharedContract { attribute :>> id="shared-scheduler"; attribute :>> source="vendor/gambit/lib/_thread.scm"; attribute :>> anchor="thread-send"; attribute :>> invariant="GambitMailboxPublication owns source refinement: one mailbox identity, detached rooted node, one permit for FIFO/cursor; scanner uses physical writer stop and unique scan authority without taking the mailbox permit. Original shared values and multi-shot roots remain"; attribute :>> open="Unknown native writers, arbitrary owner death and all original SMP acceptance families remain separate from message/GC controls"; }
  part orderedContract:SharedContract { attribute :>> id="ordered-synchronization"; attribute :>> source="vendor/gambit/include/gambit.h.in"; attribute :>> anchor="___SYNC_SLOT_ACK"; attribute :>> invariant="GambitOrderedSynchronization owns atomic ticket handoff and fixed-slot collective publication: payload-before-READY, copy-before-ACK, acquire before consumption/reuse, and physical GC stop distinct from fences"; attribute :>> open="Finite kernel/native controls do not prove every weak-memory history. Debug history, unqualified platforms and unknown-owner membership remain open"; }
  part def Coverage { ref part lane:Lane; ref part contract:SharedContract; attribute scope:String; }
  part orderedCoverage:Coverage { ref part :>> lane=orderedKernel; ref part :>> contract=orderedContract; attribute :>> scope="Actual ordered ticket and SPSC slot macros, finite races, wrap and fixed native layout"; }
  part stopCoverage:Coverage { ref part :>> lane=mailboxStop; ref part :>> contract=orderedContract; attribute :>> scope="Real built-in mailbox, four blocked senders, whole collective GCs and original shared identities"; }
  part dependencyCoverage:Coverage { ref part :>> lane=dependencies; ref part :>> contract=sourcePartition; attribute :>> scope="Unchanged Make target is up to date; all 25 fragment changes invalidate mem.o without modifying source timestamps"; }
  part h3:Coverage { ref part :>> lane=c3; ref part :>> contract=rootAuthority; attribute :>> scope="Local C protocol with physical stop as an external precondition"; }
  part h4:Coverage { ref part :>> lane=c3; ref part :>> contract=arenaReservation; attribute :>> scope="Exact private grant, bounds and refund; not whole-round packing"; }
  part h5:Coverage { ref part :>> lane=c4; ref part :>> contract=rootAuthority; attribute :>> scope="Representation and alias storage; not live migration"; }
  part h6:Coverage { ref part :>> lane=c5; ref part :>> contract=frameRoots; attribute :>> scope="Real map full multi-shot results and native bridge"; }
  part h7:Coverage { ref part :>> lane=c6; ref part :>> contract=frameRoots; attribute :>> scope="Eighty live roots and eleven completed forced GCs"; }
  part h8:Coverage { ref part :>> lane=c7; ref part :>> contract=frameRoots; attribute :>> scope="Same fixture under host-managed compiler and runtime populations"; }
  part h9:Coverage { ref part :>> lane=c8; ref part :>> contract=sharedScheduler; attribute :>> scope="Shared cyclic aliases across logical workers and completed collections"; }
  part h10:Coverage { ref part :>> lane=c9; ref part :>> contract=sharedScheduler; attribute :>> scope="Mailbox order, value reachability and bounded progress"; }
  part mailboxPermitCoverage:Coverage { ref part :>> lane=mailboxPermit; ref part :>> contract=sharedScheduler; attribute :>> scope="Exact blocked sender root, GC under held mailbox permit, selective cursor and exception cleanup"; }
  part mailboxIdentityCoverage:Coverage { ref part :>> lane=mailboxIdentity; ref part :>> contract=sharedScheduler; attribute :>> scope="Concurrent first publishers,64 messages and original shared alias identity"; }
  part h11:Coverage { ref part :>> lane=c10; ref part :>> contract=frameRoots; attribute :>> scope="Three shots, two restorations, winding order and GC"; }
}
