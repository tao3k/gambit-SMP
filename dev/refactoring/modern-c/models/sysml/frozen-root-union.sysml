package GambitFrozenRootUnion {
  private import ScalarValues::*;
  ref part delivery=GambitModernCOutcomes::roots;
  attribute scope:String="Complete frozen-root integration candidate on043a9341, not a setter leaf and not independent collector or affine-resource retirement admission.";
  attribute stage:String="Qualified managed C-target frozen roots result:15 source obligations and20 native cases close on delivery tree 47ceb50789d14f8e41b910c89a31fd1397896d66. Native ABI/GC/entry consumers passed with unchanged limits. Other platforms, independent workers, affine retirement and full SMP families remain separate.";
  attribute formalDuty:String="Reuse root_store_projection and root_enumeration Quint histories for close/store/borrow and source coverage; runtime_roles owns collective scan/strong/weak/prepare/resume order. Reuse RuntimeOwnership canonicalAliasesShareUpdatedCell, rewriteCoversEveryDeclaredRoot and reloadRestoresValueAgreement only after actual C slot/lifetime premises. Source refinement owns current-processor exclusivity, collective happens-before, epoch arithmetic, native argument reload, compiler/header binding and catcher cleanup. Native tests own execution/replay/shrink. Do not duplicate either formal model or treat LLM review as native proof.";
  attribute sourceCases:String="complete-roster;shared-epoch;six-sources;ordinary-cell;cooperative-store;joined-exit;raw-argument-root;argument-reload;catcher-cleanup;module-binding;shared-writers;logical-physical-cut;primitive-storage-lifetime;image-template-only;borrow-readers";
  attribute requiredCases:String="bootstrap;composed-union;nonzero-rc;moving-bank;moving-globals;multi-shot;native-input-gc;native-escape;native-failure;source-close;shared-primitive-root;vm-primitive-isolation;vm-primitive-rebind;vm-primitive-lifecycle;old-module-refusal;original-gsi;original-make;original-gsc;predecessor-control;serialized-replay";
  attribute sourceKinds:String="VM;symbol/keyword;RC;globals;stack;bank";
  attribute graph:String="complete_view -> roster -> close -> freeze -> scan -> drain -> restore -> resume";
  attribute ownershipDecision:String="User selected VM-local mutable primitive overrides with shared immutable code templates. Existing Scheme names remain. Each owning globals shard scans and rewrites its override slot; presence bits and code templates are nonroots. A module rebind clears only the loading VM override. Other VM overrides survive. VM setup constructs the storage before publication and cleanup frees it after leases drain. Native relocation, cross-VM isolation, rebind and repeated lifecycle cases must pass; the historical observed3/required7 remains a negative witness.";
  attribute cost:String="Coordinator setup owns sizeof(root_round) native bytes, including bounded MAX_PROCESSORS descriptors; each RC domain gains two pointers. Root-bank storage is NARGS+1 native pointers plus one existing RC allocation per raw Scheme input; each generated entry installs a catcher. Ordinary stores gain a noncollecting owner/phase/union check and call, not a per-store mutex. Four extra unconditional GC collective calls versus the selected predecessor. Multiple-VM storage adds CAP Scheme words plus ceil(CAP/WORD_WIDTH) bitmap words per VM; CAP is the existing20000 global capacity, not a new limit. Single-VM uses two fields per registered global. Primitive lookup adds presence and slot loads; primitive publication adds the existing global mutex, not a GC wait. Measure actual sizes and costs; no speedup, RSS or throughput claim.";
  attribute failure:String="Any unfinished source retains the round and joined domains. Epoch exhaustion refuses reuse, never wraps. Allocation failure during setup publishes no RC domain. Native root-bank partial construction releases installed records; unknown/nonlocal control must follow the actual catcher. Shared primitive cells, raw lvalue aliases and unknown native effects require their own source closure and cannot be inferred from ordinary globals.";
  part def Source { attribute id:String; attribute path:String; attribute anchor:String; attribute obligation:String; }
  part union:Source { attribute :>> id="six-sources"; attribute :>> path="lib/_mem/root-tasks.inc"; attribute :>> anchor="___BOOL ___root_round_scan"; attribute :>> obligation="VM and symkey plus each member RC/globals/stack/bank retain their actual source identities and original scan order."; }
  part epoch:Source { attribute :>> id="shared-epoch"; attribute :>> path="lib/_mem/root-tasks.inc"; attribute :>> anchor="___BOOL ___root_round_freeze"; attribute :>> obligation="Every admitted RC source receives the VM union epoch, including newly initialized members; local counters are not the roster authority."; }
  part cut:Source { attribute :>> id="complete-roster"; attribute :>> path="lib/_mem/collection-round.inc"; attribute :>> anchor="___root_round_begin(___ps)"; attribute :>> obligation="Complete saved frame/context views and first collective precede capture; roster lifetime and current-processor uniqueness must be traced to actual callers."; }
  part writers:Source { attribute :>> id="cooperative-store"; attribute :>> path="lib/_mem/global-bindings.inc"; attribute :>> anchor="___BOOL ___try_store_global"; attribute :>> obligation="Only the current exclusive processor writes, with no poll/allocation/callback before final store. Collective ordering supplies scan visibility; the RC name or a count snapshot alone proves nothing."; }
  part shared:Source { attribute :>> id="shared-writers"; attribute :>> path="include/gambit.h.in"; attribute :>> anchor="#define ___GLOBALVARPRIMSET"; attribute :>> obligation="GLOBALVARPRIMSET and PRM retain Scheme names but read/write owning VM override storage. DEF_MOD_PRM alone publishes permanent code through bind_primitive and clears the loading VM override. A shared image field must never hold an owning heap pointer; raw PRMCELL is an rvalue. Canonical override slots are scanned once by their owning global shard. Trace _gsclib, reflection, module setup and raw consumers."; }
  part cell:Source { attribute :>> id="ordinary-cell"; attribute :>> path="include/gambit.h.in"; attribute :>> anchor="#define ___GLOBALVARSET"; attribute :>> obligation="Generated SET_GLO, reflective GLOBALVARSET and DEF_MOD_GLO use store_global on the owning canonical value cell. No alias snapshot becomes an independent scan task."; }
  part reload:Source { attribute :>> id="argument-reload"; attribute :>> path="include/gambit.h.in"; attribute :>> anchor="#define ___SFUN_ARG(i,arg)"; attribute :>> obligation="After marker/conversion GC reload raw Scheme parameters from their RC slots when writing actual Scheme arguments. Keep those slots through logical continuation transfer until physical host exit."; }
  part moduleEntry:Source { attribute :>> id="module-binding"; attribute :>> path="lib/setup.c"; attribute :>> anchor="module->setup_mod (ctx->ps)"; attribute :>> obligation="Generated module setup receives the loading processor explicitly. Old modules must fail runtime size/version admission before an old function table or setup signature is invoked."; }
  part storage:Source { attribute :>> id="primitive-storage-lifetime"; attribute :>> path="lib/_mem/memory-lifecycle.inc"; attribute :>> anchor="___GLOBALS_STORAGE_WORDS"; attribute :>> obligation="VM slot allocation is checked and all values/bits initialize before usable VM publication. setup.c propagates failure and rolls back linked VM/OS state. Leases and borrowers drain before freeing the single block; repeated setup/cleanup must not reuse stale override state."; }
  part image:Source { attribute :>> id="image-template-only"; attribute :>> path="lib/setup.c"; attribute :>> anchor="___HIDDEN void setup_kernel_handlers"; attribute :>> obligation="Raw PRMCELL consumers in setup and _kernel.scm address fixed image labels and must read immutable template code, not a user override with an arbitrary frame shape. setup.c also temporarily reads the prepublication symbol hash from prm. Ordinary Scheme PRM and reflective reads use VM overrides. External private raw writes must fail source admission. CPU fixup operations3/4 previously returned unbounded writable global/primitive addresses; now propagate UNIMPL before code can run. This C-target REV does not claim a redesigned CPU backend root-borrow protocol."; }
  part borrows:Source { attribute :>> id="borrow-readers"; attribute :>> path="lib/_mem/rc-allocation.inc"; attribute :>> anchor="___borrow_rc_root"; attribute :>> obligation="A borrow pins the canonical RC slot, prevents payload rebinding/retirement and remains scanned. Actual startup/on_all_processors and marker callers reload after allocating calls and return the loan at their physical boundary. The current processor is the only executing Scheme owner; a suspended enclosing C frame is not a concurrent cell reader. Borrowing does not admit an arbitrary asynchronous C reader or a foreign-VM Scheme object."; }
  part entryRoots:Source { attribute :>> id="raw-argument-root"; attribute :>> path="gsc/_ptree2.scm"; attribute :>> anchor="(define (root-arguments)"; attribute :>> obligation="Every raw Scheme parameter is registered before the first collecting marker/conversion and reloaded at actual argument transfer."; }
  part entryExit:Source { attribute :>> id="catcher-cleanup"; attribute :>> path="include/gambit.h.in"; attribute :>> anchor="#define ___END_SFUN "; attribute :>> obligation="Volatile entry records and marker survive catcher recovery; normal and continuation-unwind paths release roots before propagating control."; }
  part control:Source { attribute :>> id="logical-physical-cut"; attribute :>> path="lib/setup.c"; attribute :>> anchor="stack_marker != ___ps->context->fp[___FRAME_SPACE(2)-2]"; attribute :>> obligation="Scheme continuation restoration may execute inside a still-live inner C trampoline. Keep entry roots across that interval and its GC. Only an actual return to the enclosing host marker establishes physical unwind and final drain; Scheme logical escape alone is not that receipt."; }
  part retirement:Source { attribute :>> id="joined-exit"; attribute :>> path="lib/_mem/rc-allocation.inc"; attribute :>> anchor="if (d->joined_round != 0) return 0;"; attribute :>> obligation="Local task DONE cannot authorize domain cleanup; the restored collective alone drops joined-round custody."; }
  part def Need { ref part gate:GambitCommitGates::Gate; attribute id:String; attribute method:String; attribute artifact:String; attribute scope:String; }
  part tests:Need { ref part :>> gate=GambitCommitGates::tests; attribute :>> id="FROZEN-ROOT-NATIVE"; attribute :>> method="native"; attribute :>> artifact="evidence/research/retained/modern-c/frozen-root-union/receipt.json"; attribute :>> scope="Exact-source bootstrap, composed six-kind implementation PBT/replay/shrink, nonzero member, real moving GC and multi-shot frames, generated raw input before marker GC, unwind/failure cleanup, unchanged original consumers and independent predecessor/baseline attribution."; }
  part learning:Need { ref part :>> gate=GambitCommitGates::learning; attribute :>> id="FROZEN-ROOT-LEARNING"; attribute :>> method="source-analysis"; attribute :>> artifact="dev/refactoring/modern-c/frozen-root-union.org"; attribute :>> scope="A population owns one epoch and restoration lifetime; source adapters and writer/borrow coverage are different obligations. Preserve precise roots and Gambit multi-shot semantics."; }
  part process:Need { ref part :>> gate=GambitCommitGates::process; attribute :>> id="FROZEN-ROOT-PROCESS"; attribute :>> method="source-analysis"; attribute :>> artifact="dev/refactoring/modern-c/delivery-outcomes.org"; attribute :>> scope="First complete integration result, not dotted leaf progress. Preserve pending prototype custody; independent collector, capacity, retirement, service and twelve-family admission remain separate."; }
  part models:Need { ref part :>> gate=GambitCommitGates::models; attribute :>> id="FROZEN-ROOT-MODELS"; attribute :>> method="source-refinement"; attribute :>> artifact="dev/refactoring/modern-c/frozen-root-union.org"; attribute :>> scope="Native SysML projection drives ASCENT source/native obligations and closure. Distinct existing Quint temporal and Lean conditional laws are referenced, not duplicated."; }
  part questions:Need { ref part :>> gate=GambitCommitGates::questions; attribute :>> id="FROZEN-ROOT-QUESTIONS"; attribute :>> method="source-analysis"; attribute :>> artifact="dev/refactoring/modern-c/frozen-root-union.org"; attribute :>> scope="Who closes every actual writer, who owns every borrowed root through GC, what orders publication, what prevents cleanup after local DONE, and what still falsifies complete closure? Report unmeasured performance and actual extra memory/synchronization."; }
}
