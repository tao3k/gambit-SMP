package GambitThreadCacheTail { private import ScalarValues::*;
part def SourceRow { attribute key:String; attribute path:String; attribute needle:String; attribute limit:String; }
part source0:SourceRow { attribute :>> key="threshold"; attribute :>> path="evidence/research/source-references/tcl/cbf86d62348d6b052e1961b4df995960fb21545f/generic/tclInt.h"; attribute :>> needle="#  define ALLOC_NOBJHIGH 1200"; attribute :>> limit="macro direct put iff existing interp cache count in 1..1199"; }
part source1:SourceRow { attribute :>> key="macro-route"; attribute :>> path="evidence/research/source-references/tcl/cbf86d62348d6b052e1961b4df995960fb21545f/generic/tclInt.h"; attribute :>> needle="(cachePtr->numObjects >= ALLOC_NOBJHIGH)"; attribute :>> limit="empty or >=high diverts to TclThreadFreeObj"; }
part source2:SourceRow { attribute :>> key="fast-store"; attribute :>> path="evidence/research/source-references/tcl/cbf86d62348d6b052e1961b4df995960fb21545f/generic/tclInt.h"; attribute :>> needle="cachePtr->firstObjPtr = objPtr;"; attribute :>> limit="link/head/count source sequence; require owner and no reentry"; }
part source3:SourceRow { attribute :>> key="interp-cache"; attribute :>> path="evidence/research/source-references/tcl/cbf86d62348d6b052e1961b4df995960fb21545f/generic/tclBasic.c"; attribute :>> needle="iPtr->allocCache = (AllocCache *)TclpGetAllocCache();"; attribute :>> limit="interp creation records per-thread cache prefix; loaded ABI/alias qualification open"; }
part source4:SourceRow { attribute :>> key="helper-cache"; attribute :>> path="evidence/research/source-references/tcl/cbf86d62348d6b052e1961b4df995960fb21545f/generic/tclThreadAlloc.c"; attribute :>> needle="GETCACHE(cachePtr);"; attribute :>> limit="helper can enter lazy GetCache; not uniformly nonallocating"; }
part source5:SourceRow { attribute :>> key="helper-push"; attribute :>> path="evidence/research/source-references/tcl/cbf86d62348d6b052e1961b4df995960fb21545f/generic/tclThreadAlloc.c"; attribute :>> needle="cachePtr->lastPtr = objPtr;"; attribute :>> limit="empty path updates tail before count increment"; }
part source6:SourceRow { attribute :>> key="helper-high"; attribute :>> path="evidence/research/source-references/tcl/cbf86d62348d6b052e1961b4df995960fb21545f/generic/tclThreadAlloc.c"; attribute :>> needle="if (cachePtr->numObjects > NOBJHIGH)"; attribute :>> limit="after push; 1200 -> 1201 then flush"; }
part source7:SourceRow { attribute :>> key="batch"; attribute :>> path="evidence/research/source-references/tcl/cbf86d62348d6b052e1961b4df995960fb21545f/generic/tclThreadAlloc.c"; attribute :>> needle="#define NOBJALLOC\t800"; attribute :>> limit="fixed source batch amount; not runtime benchmark"; }
part source8:SourceRow { attribute :>> key="shared-transfer"; attribute :>> path="evidence/research/source-references/tcl/cbf86d62348d6b052e1961b4df995960fb21545f/generic/tclThreadAlloc.c"; attribute :>> needle="Tcl_MutexLock(objLockPtr);"; attribute :>> limit="PutObjs walks keep prefix then locks shared list"; }
part source9:SourceRow { attribute :>> key="cache-init"; attribute :>> path="evidence/research/source-references/tcl/cbf86d62348d6b052e1961b4df995960fb21545f/generic/tclThreadAlloc.c"; attribute :>> needle="cachePtr = TclpSysAlloc(sizeof(Cache), 0);"; attribute :>> limit="lazy initialization can allocate and create mutexes"; }
part source10:SourceRow { attribute :>> key="stats"; attribute :>> path="evidence/research/source-references/tcl/cbf86d62348d6b052e1961b4df995960fb21545f/generic/tclInt.h"; attribute :>> needle="tclObjsFreed++"; attribute :>> limit="selected TCLNR_FREE expansion includes optional statistics after storage put"; }
part source11:SourceRow { attribute :>> key="previous"; attribute :>> path="dev/refactoring/modern-c/models/quint/escrow_critical_tail.qnt"; attribute :>> needle="action beginRestoreCancel="; attribute :>> limit="previous slot/cancel guard; new refinement keeps nested debts separate"; }
part source12:SourceRow { attribute :>> key="cancel-restore"; attribute :>> path="vendor/gambit/lib/setup.c"; attribute :>> needle="pthread_setcancelstate(cancel_state, NULL);"; attribute :>> limit="actual source pattern; no automatic NR completion receipt"; }
part def ObligationRow { attribute key:String; attribute status:String; attribute condition:String; }
part obligation0:ObligationRow { attribute :>> key="branch-safety"; attribute :>> status="conditional-model"; attribute :>> condition="correct native owner, stable cache identity/count and admitted qualified fast tail"; }
part obligation1:ObligationRow { attribute :>> key="threshold-source"; attribute :>> status="source-bound"; attribute :>> condition="1200 macro guard, 800 helper transfer and actual empty/high routes"; }
part obligation2:ObligationRow { attribute :>> key="native-tail"; attribute :>> status="unresolved"; attribute :>> condition="complete selected expansion incl stats/instrumentation and receipt stores excludes abandonment"; }
part obligation3:ObligationRow { attribute :>> key="helper-completion"; attribute :>> status="unresolved"; attribute :>> condition="lazy cache/partial PutObjs/shared lock outcomes need exact native custody; no replay"; }
part obligation4:ObligationRow { attribute :>> key="slot-capacity"; attribute :>> status="unresolved"; attribute :>> condition="capacity covers active/preparing/unknown nested owners or admission refuses before pop"; }
part obligation5:ObligationRow { attribute :>> key="native-affinity"; attribute :>> status="unresolved"; attribute :>> condition="owner/current-thread/cache prefix identity, loaded ABI and C23 alias/layout validity"; }
part obligation6:ObligationRow { attribute :>> key="cancel-landing"; attribute :>> status="unresolved"; attribute :>> condition="stable supervisor before restore; exact parent/child return receipts and independent result debts"; }
part def RouteRow { attribute actionName:String; attribute lemma:String; attribute source:String; attribute obligation:String; }
part route0:RouteRow { attribute :>> actionName="enterChild"; attribute :>> lemma="ThreadCacheTail.enterChildPreserves"; attribute :>> source="previous"; attribute :>> obligation="branch-safety"; }
part route1:RouteRow { attribute :>> actionName="childCleanupKnown"; attribute :>> lemma="ThreadCacheTail.childCleanupKnownPreserves"; attribute :>> source="previous"; attribute :>> obligation="branch-safety"; }
part route2:RouteRow { attribute :>> actionName="beginChildRestore"; attribute :>> lemma="ThreadCacheTail.beginChildRestorePreserves"; attribute :>> source="cancel-restore"; attribute :>> obligation="branch-safety"; }
part route3:RouteRow { attribute :>> actionName="knownChildRestore"; attribute :>> lemma="ThreadCacheTail.knownChildRestorePreserves"; attribute :>> source="cancel-restore"; attribute :>> obligation="branch-safety"; }
part route4:RouteRow { attribute :>> actionName="claimExtra"; attribute :>> lemma="ThreadCacheTail.claimExtraPreserves"; attribute :>> source="previous"; attribute :>> obligation="branch-safety"; }
part route5:RouteRow { attribute :>> actionName="returnExtra"; attribute :>> lemma="ThreadCacheTail.returnExtraPreserves"; attribute :>> source="previous"; attribute :>> obligation="branch-safety"; }
part route6:RouteRow { attribute :>> actionName="denyOwner"; attribute :>> lemma="ThreadCacheTail.denyOwnerPreserves"; attribute :>> source="previous"; attribute :>> obligation="branch-safety"; }
part route7:RouteRow { attribute :>> actionName="sampleEmpty"; attribute :>> lemma="ThreadCacheTail.sampleEmptyPreserves"; attribute :>> source="previous"; attribute :>> obligation="branch-safety"; }
part route8:RouteRow { attribute :>> actionName="sampleLow"; attribute :>> lemma="ThreadCacheTail.sampleLowPreserves"; attribute :>> source="previous"; attribute :>> obligation="branch-safety"; }
part route9:RouteRow { attribute :>> actionName="sampleNear"; attribute :>> lemma="ThreadCacheTail.sampleNearPreserves"; attribute :>> source="previous"; attribute :>> obligation="branch-safety"; }
part route10:RouteRow { attribute :>> actionName="sampleHigh"; attribute :>> lemma="ThreadCacheTail.sampleHighPreserves"; attribute :>> source="previous"; attribute :>> obligation="branch-safety"; }
part route11:RouteRow { attribute :>> actionName="selectFast"; attribute :>> lemma="ThreadCacheTail.selectFastPreserves"; attribute :>> source="fast-store"; attribute :>> obligation="branch-safety"; }
part route12:RouteRow { attribute :>> actionName="selectHelper"; attribute :>> lemma="ThreadCacheTail.selectHelperPreserves"; attribute :>> source="shared-transfer"; attribute :>> obligation="branch-safety"; }
part route13:RouteRow { attribute :>> actionName="attestFastTail"; attribute :>> lemma="ThreadCacheTail.attestFastTailPreserves"; attribute :>> source="fast-store"; attribute :>> obligation="branch-safety"; }
part route14:RouteRow { attribute :>> actionName="writeFastLink"; attribute :>> lemma="ThreadCacheTail.writeFastLinkPreserves"; attribute :>> source="fast-store"; attribute :>> obligation="branch-safety"; }
part route15:RouteRow { attribute :>> actionName="publishFastHead"; attribute :>> lemma="ThreadCacheTail.publishFastHeadPreserves"; attribute :>> source="fast-store"; attribute :>> obligation="branch-safety"; }
part route16:RouteRow { attribute :>> actionName="incrementFastCount"; attribute :>> lemma="ThreadCacheTail.incrementFastCountPreserves"; attribute :>> source="fast-store"; attribute :>> obligation="branch-safety"; }
part route17:RouteRow { attribute :>> actionName="publishFastReceipt"; attribute :>> lemma="ThreadCacheTail.publishFastReceiptPreserves"; attribute :>> source="fast-store"; attribute :>> obligation="branch-safety"; }
part route18:RouteRow { attribute :>> actionName="helperPush"; attribute :>> lemma="ThreadCacheTail.helperPushPreserves"; attribute :>> source="shared-transfer"; attribute :>> obligation="branch-safety"; }
part route19:RouteRow { attribute :>> actionName="helperFlush800"; attribute :>> lemma="ThreadCacheTail.helperFlush800Preserves"; attribute :>> source="shared-transfer"; attribute :>> obligation="branch-safety"; }
part route20:RouteRow { attribute :>> actionName="helperKnownReturn"; attribute :>> lemma="ThreadCacheTail.helperKnownReturnPreserves"; attribute :>> source="shared-transfer"; attribute :>> obligation="branch-safety"; }
part route21:RouteRow { attribute :>> actionName="unknownHelper"; attribute :>> lemma="ThreadCacheTail.unknownHelperPreserves"; attribute :>> source="shared-transfer"; attribute :>> obligation="branch-safety"; }
part route22:RouteRow { attribute :>> actionName="handoffParent"; attribute :>> lemma="ThreadCacheTail.handoffParentPreserves"; attribute :>> source="cancel-restore"; attribute :>> obligation="branch-safety"; }
part route23:RouteRow { attribute :>> actionName="beginParentRestore"; attribute :>> lemma="ThreadCacheTail.beginParentRestorePreserves"; attribute :>> source="cancel-restore"; attribute :>> obligation="branch-safety"; }
part route24:RouteRow { attribute :>> actionName="knownParentRestore"; attribute :>> lemma="ThreadCacheTail.knownParentRestorePreserves"; attribute :>> source="cancel-restore"; attribute :>> obligation="branch-safety"; }
part def GainRow { attribute key:String; attribute saved:String; attribute added:String; attribute condition:String; attribute status:String; }
part gain0:GainRow { attribute :>> key="fast-put"; attribute :>> saved="eligible direct branch has 3 native cache/link stores; no helper shared-lock or batch walk"; attribute :>> added="stable receipt publication adds at least one logical store plus ordering/owner qualification"; attribute :>> condition="nonnull existing cache, same owner, 1<=n<1200, selected no-callout profile"; attribute :>> status="source-bound/conditional"; }
part gain1:GainRow { attribute :>> key="high-helper"; attribute :>> saved="at entry n=1200: push to1201, retain401, transfer800"; attribute :>> added="401 keep-list advances plus shared mutex/splice; full helper completion required"; attribute :>> condition="valid source list/counter representation; normal PutObjs return"; attribute :>> status="source-bound"; }
part gain2:GainRow { attribute :>> key="empty-helper"; attribute :>> saved="n=0 helper sets lastPtr and returns count1 without batch transfer"; attribute :>> added="GETCACHE may initialize TLS/cache/locks; current node/cache duty retained"; attribute :>> condition="same native owner and known cache creation"; attribute :>> status="source-bound"; }
part gain3:GainRow { attribute :>> key="nested-reserve"; attribute :>> saved="parent/child/deferred debt have disjoint slots; no waiting on own ancestry"; attribute :>> added="P*S metadata plus retained unknown restoration; finite P not enough for arbitrary nesting"; attribute :>> condition="known child cleanup and saved-state restore before its slot refund"; attribute :>> status="conditional-model"; }
part gain4:GainRow { attribute :>> key="tail-value"; attribute :>> saved="qualify direct-put normal path rather than mask the entire destructor/helper"; attribute :>> added="helper fallback remains slower/effectful; unknown cache batches may be quarantined"; attribute :>> condition="actual compiled profile and no-abandon tail not yet qualified"; attribute :>> status="design-only"; }
part def IssuerRow { attribute key:String; attribute source:String; attribute signature:String; attribute gap:String; }
part issuer0:IssuerRow { attribute :>> key="cache-owner"; attribute :>> source="interp-cache"; attribute :>> signature="correct Tcl OS-thread/cache identity and stable representation before branch read"; attribute :>> gap="macro does not dynamically validate owner; prefix alias rules open"; }
part issuer1:IssuerRow { attribute :>> key="fast-tail-owner"; attribute :>> source="fast-store"; attribute :>> signature="node not already free; no reentry from count read through receipt publication"; attribute :>> gap="token/descriptor last-use and all selected effects must be qualified"; }
part issuer2:IssuerRow { attribute :>> key="helper-owner"; attribute :>> source="shared-transfer"; attribute :>> signature="known complete local split/shared splice and mutex release"; attribute :>> gap="first pool-head store is not helper completion"; }
part issuer3:IssuerRow { attribute :>> key="slot-supervisor"; attribute :>> source="previous"; attribute :>> signature="parent/child/extra reservation conservation and release only on exact completion"; attribute :>> gap="unknown restore or nested self-wait cannot refund slot"; }
part issuer4:IssuerRow { attribute :>> key="restore-owner"; attribute :>> source="cancel-restore"; attribute :>> signature="saved cancellation state restored after stable ownership handoff"; attribute :>> gap="nested saved DISABLE is not unconditional enable; call may not return"; }
part def ConsumerRow { attribute key:String; attribute source:String; attribute access:String; attribute lifetime:String; attribute limit:String; }
part consumer0:ConsumerRow { attribute :>> key="direct-put"; attribute :>> source="fast-store"; attribute :>> access="node.link <- oldhead; cache.head <- node; cache.count++"; attribute :>> lifetime="owner-exclusive cache across reads and writes"; attribute :>> limit="head publication precedes consistent count; forbid reentry in middle"; }
part consumer1:ConsumerRow { attribute :>> key="empty-put"; attribute :>> source="helper-push"; attribute :>> access="GETCACHE -> push -> lastPtr for empty -> count++"; attribute :>> lifetime="original thread cache and source node"; attribute :>> limit="allocation/initialization may occur before push"; }
part consumer2:ConsumerRow { attribute :>> key="high-put"; attribute :>> source="helper-high"; attribute :>> access="push -> count1201 -> PutObjs(cache,800)"; attribute :>> lifetime="whole helper/cache batch until full return"; attribute :>> limit="node at head may be read again during keep traversal"; }
part consumer3:ConsumerRow { attribute :>> key="shared-batch"; attribute :>> source="shared-transfer"; attribute :>> access="set keep count/local split -> shared mutex -> splice/account -> lastPtr"; attribute :>> lifetime="both cache representations and lock owner"; attribute :>> limit="unknown needs batch/cache custody, not only NodeId"; }
part consumer4:ConsumerRow { attribute :>> key="nested-slot"; attribute :>> source="previous"; attribute :>> access="parent slot retained while child owns another slot"; attribute :>> lifetime="all active and unknown cancellation scopes"; attribute :>> limit="two-slot witness is not arbitrary Scheme nesting bound"; }
part def EdgeRow { attribute fromNode:String; attribute toNode:String; attribute contract:String; }
part edge0:EdgeRow { attribute :>> fromNode="Owner/cache admission"; attribute :>> toNode="Snapshot current count"; attribute :>> contract="after token/callback effects; no stale pre-callback branch proof"; }
part edge1:EdgeRow { attribute :>> fromNode="Count 1..1199"; attribute :>> toNode="Qualified direct put"; attribute :>> contract="3 cache stores then stable receipt under protected tail"; }
part edge2:EdgeRow { attribute :>> fromNode="Count 0 or >=1200"; attribute :>> toNode="TclThreadFreeObj"; attribute :>> contract="GETCACHE + push; may initialize or transfer batch"; }
part edge3:EdgeRow { attribute :>> fromNode="Count becomes1201"; attribute :>> toNode="PutObjs 800"; attribute :>> contract="401 remain; shared transfer and lastPtr complete before receipt"; }
part edge4:EdgeRow { attribute :>> fromNode="Nested child restore pending"; attribute :>> toNode="Child slot retained"; attribute :>> contract="parent cannot finish based on cleanup alone"; }
part edge5:EdgeRow { attribute :>> fromNode="Parent known receipt"; attribute :>> toNode="Stable supervisor"; attribute :>> contract="hand off before restoring saved cancellation state"; }
part edge6:EdgeRow { attribute :>> fromNode="Unknown helper/restore"; attribute :>> toNode="Retained native owner"; attribute :>> contract="no replay, no forced capacity refund"; }
}
