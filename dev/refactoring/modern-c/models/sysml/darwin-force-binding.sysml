package GambitDarwinForceBinding { private import ScalarValues::*;
part def Route { attribute key:String; attribute sourcePath:String; attribute needle:String; attribute obligation:String; }
part route0:Route { attribute :>> key="configured-request"; attribute :>> sourcePath="../ci-source-patch-check/src/gambit/bin/gambuild-C.unix"; attribute :>> needle="-D___TRUST_C_TCO"; attribute :>> obligation="Retained Darwin defaults; actual per-unit overrides and loaded binary identity remain unbound"; }
part route1:Route { attribute :>> key="configured-jumps"; attribute :>> sourcePath="../ci-source-patch-check/src/gambit/include/gambit.h"; attribute :>> needle="#define ___USE_PROPER_TAIL_CALL_EXCLUSIVELY_TO_EXIT_HOST"; attribute :>> obligation="C-mode setjmp plus trusted TCO selects direct host-tail route unless centralized or multi-compiler override"; }
part route2:Route { attribute :>> key="configured-hosts"; attribute :>> sourcePath="../ci-source-patch-check/src/gambit/lib/_kernel.c"; attribute :>> needle="#define ___LBLCOUNT 1461"; attribute :>> obligation="Single-host kernel saves/restores all five GVM registers; distinct module force still crosses hosts"; }
part route3:Route { attribute :>> key="configured-coverage"; attribute :>> sourcePath="../ci-source-patch-check/src/gambit/lib/setup.h"; attribute :>> needle="#define ___COVER(n)"; attribute :>> obligation="Current retained coverage hook is empty; changing it invalidates transfer-window evidence"; }
part route4:Route { attribute :>> key="semantic-force"; attribute :>> sourcePath="vendor/gambit/lib/_kernel.scm"; attribute :>> needle="___ps->temp2 = ___R1;"; attribute :>> obligation="Normal internal return writes result before saved-register restoration; exceptions need independent ownership"; }
part route5:Route { attribute :>> key="exception-owner"; attribute :>> sourcePath="vendor/gambit/lib/setup.c"; attribute :>> needle="___CALL_LABEL_HOST(___ps->pc,___ps);"; attribute :>> obligation="Host call and catcher/trampoline routes cannot release code pin before final actual access"; }
part route6:Route { attribute :>> key="signal-defer"; attribute :>> sourcePath="vendor/gambit/lib/os_setup.c"; attribute :>> needle="___HIDDEN void user_intr"; attribute :>> obligation="Signal requests interrupt through processor zero; full abort-device transitive effects remain unproved"; }
part route7:Route { attribute :>> key="lookup-producer"; attribute :>> sourcePath="/opt/homebrew/Cellar/quint/0.33.0/libexec/lib/node_modules/@informalsystems/quint/dist/src/names/resolver.js"; attribute :>> needle="this.table.set(id, def);"; attribute :>> obligation="Reference occurrence ID maps to declaration; spelling is not binding identity"; }
part route8:Route { attribute :>> key="lookup-consumer"; attribute :>> sourcePath="/opt/homebrew/Cellar/quint/0.33.0/libexec/lib/node_modules/@informalsystems/quint/dist/src/runtime/impl/builder.js"; attribute :>> needle="const def = builder.table.get(expr.id);"; attribute :>> obligation="Evaluation and assignment resolve occurrence IDs; malformed missing lookup must reject"; }
part route9:Route { attribute :>> key="json-input"; attribute :>> sourcePath="evidence/research/reti-ofd-semantics/typed-ir.json"; attribute :>> needle="\"typechecking\""; attribute :>> obligation="Pinned parent JSON typed IR is formal input; not Scheme/C execution"; }
part route10:Route { attribute :>> key="current-scanner"; attribute :>> sourcePath="vendor/gambit/lib/mem.c"; attribute :>> needle="descriptor = ___decode_frame_descriptor (___LABEL_DESCR_GET(actual_ra), 1);"; attribute :>> obligation="Current scanner uses central descriptor decode; old-code and trailing OFD-map storage must stay live through final scan access"; }
part def Contract { attribute key:String; attribute owner:String; attribute actionName:String; attribute invariant:String; attribute gap:String; }
part contract0:Contract { attribute :>> key="darwin-jump-profile"; attribute :>> owner="native/build"; attribute :>> actionName="selectProfile"; attribute :>> invariant="Bind generated header request flags and per-unit source before selecting jump branch"; attribute :>> gap="Compiler predefined macros and actual invocation not captured"; }
part contract1:Contract { attribute :>> key="transfer-window"; attribute :>> owner="semantic/native"; attribute :>> actionName="saveResult restoreCaller consumeForce"; attribute :>> invariant="No collecting or reentrant effect between sole temp2 ownership and declared destination"; attribute :>> gap="Debug hooks device-abort closure and all target representations open"; }
part contract2:Contract { attribute :>> key="exception-custody"; attribute :>> owner="control/foreign"; attribute :>> actionName="throw catch restore"; attribute :>> invariant="Escaping thunk does not deliver normal force result; code roots outlive unwind cleanup"; attribute :>> gap="All FFI catchers and raw native aliases open"; }
part contract3:Contract { attribute :>> key="inherited-child"; attribute :>> owner="collector/roots"; attribute :>> actionName="childReserve publish claim"; attribute :>> invariant="Reserve child before parent release; queued private and active phases retain one debt"; attribute :>> gap="QNT atomic relation is not C11 proof"; }
part contract4:Contract { attribute :>> key="cohort-ledger"; attribute :>> owner="release/native"; attribute :>> actionName="parentLastUse retire"; attribute :>> invariant="Single generation ledger reaches stable zero only after gates close and all actual final uses"; attribute :>> gap="Affine task state and C11 release-sequence implementation open"; }
part contract5:Contract { attribute :>> key="binding-identity"; attribute :>> owner="build/modeling"; attribute :>> actionName="resolve extract"; attribute :>> invariant="Occurrence ID canonical declaration body inferred type and scope agree before Lean projection"; attribute :>> gap="JSON and lookup producer remain trusted; full boolean/action relation open"; }
part def Obligation { attribute key:String; attribute status:String; attribute scope:String; attribute counterexample:String; }
part obligation0:Obligation { attribute :>> key="resolved-reference"; attribute :>> status="conditional-proved"; attribute :>> scope="Lean accepted expression respects declaration-ID resolver under source environment"; attribute :>> counterexample="Same spelling s with declaration 8 cannot target declaration 7"; }
part obligation1:Obligation { attribute :>> key="private-to-reader"; attribute :>> status="bounded-checked"; attribute :>> scope="Private reservation initialized queued claimed completed; inherited grant after close"; attribute :>> counterexample="Dropping parent before reserving child permits zero-gap retirement"; }
part obligation2:Obligation { attribute :>> key="child-arithmetic"; attribute :>> status="conditional-proved"; attribute :>> scope="Reserve-before-drop leaves one debt; unknown and child prevent free"; attribute :>> counterexample="Publishing before initialization preserves an invalid payload"; }
part obligation3:Obligation { attribute :>> key="darwin-native-profile"; attribute :>> status="open"; attribute :>> scope="Retained configuration hashes match earlier ledger; vendor header/kernel/mem drift from parent; loaded binary and overrides unbound"; attribute :>> counterexample="Configure enable-smp does not attest multiple-threaded runtime"; }
part obligation4:Obligation { attribute :>> key="json-extraction"; attribute :>> status="partially-checked"; attribute :>> scope="91 selected references validate on pinned JSON; rejecting controls exercise binding admission"; attribute :>> counterexample="Authenticated JSON-table construction and whole adapter semantics not proved"; }
part obligation5:Obligation { attribute :>> key="c11-refinement"; attribute :>> status="open"; attribute :>> scope="Same ledger RMW release sequence plus affine parent state and queue release/acquire"; attribute :>> counterexample="Related but distinct counters do not inherit synchronization"; }
part obligation6:Obligation { attribute :>> key="complete-source"; attribute :>> status="open"; attribute :>> scope="All readers signals inspectors callbacks and actual exception final uses"; attribute :>> counterexample="Static route witnesses do not establish full alias closure"; }
part def Gain { attribute key:String; attribute avoided:String; attribute added:String; attribute condition:String; }
part gain0:Gain { attribute :>> key="force-hot-path"; attribute :>> avoided="Extra permanent root publication may be avoided for a proved no-safepoint window"; attribute :>> added="Profile-bound generated annotations and validation; otherwise publish and reload a movable root"; attribute :>> condition="Zero measured speedup; conditional transfer theorem does not qualify loaded binary"; }
part gain1:Gain { attribute :>> key="scan-handoff"; attribute :>> avoided="Temporary zero-debt gaps and duplicate enqueue after lost acknowledgement"; attribute :>> added="One child reservation one queue publish one claim one completion plus affine task state"; attribute :>> condition="Same-cohort batch may amortize ledger reservations only while parent covers every child"; }
part gain2:Gain { attribute :>> key="metadata-retention"; attribute :>> avoided="Keeping every old cohort forever when final-use evidence can be signed"; attribute :>> added="Live and unknown code/OFD bytes plus stable directory and task records"; attribute :>> condition="Unknown raw aliases can force unbounded retention; no guaranteed memory saving"; }
part gain3:Gain { attribute :>> key="binding-reuse"; attribute :>> avoided="Name-based accidental cache/certificate reuse across bindings"; attribute :>> added="91 reference witnesses for current input; ID scope type and digest checking"; attribute :>> condition="Input IDs are local; alpha-renamed inputs require new witness not old raw-ID cache keys"; }
part gain4:Gain { attribute :>> key="language-boundary"; attribute :>> avoided="Duplicated semantic machinery in a speculative Zig runtime"; attribute :>> added="Modern C root/lifetime contract plus generator and model checks"; attribute :>> condition="No incremental Zig-specific benefit established by these required contracts"; }
part def Binding { attribute key:String; attribute qntAction:String; attribute leanLemma:String; attribute refinement:String; }
part binding0:Binding { attribute :>> key="reserve-before-drop"; attribute :>> qntAction="childReserve"; attribute :>> leanLemma="reserveBeforeDrop"; attribute :>> refinement="Abstract debt preservation only; concrete task-state CAS protocol OPEN"; }
part binding1:Binding { attribute :>> key="queue-payload"; attribute :>> qntAction="claim"; attribute :>> leanLemma="publishAcquire"; attribute :>> refinement="Initialized bit preservation only; queue C11 synchronization OPEN"; }
part binding2:Binding { attribute :>> key="unknown-custody"; attribute :>> qntAction="lose"; attribute :>> leanLemma="unknownBlocks"; attribute :>> refinement="Unknown blocks reclaim; recovery oracle and final termination OPEN"; }
part history:GambitAssuranceRouting::ModelNeed { ref part :>> owner=GambitBuildAssurance::planner.component; attribute :>> obligationId="DF-H"; attribute :>> kind="interleaving"; attribute :>> subjectPath="dev/refactoring/modern-c/models/quint/darwin_force_binding.qnt"; attribute :>> subjectScope="Private child reservation publish acquire and completion under inherited cohort grant"; attribute :>> premise="Retained Darwin configuration and pinned typed IR; no loaded binary or C11 qualification"; }
part induction:GambitAssuranceRouting::ModelNeed { ref part :>> owner=GambitBuildAssurance::planner.component; attribute :>> obligationId="DF-I"; attribute :>> kind="induction"; attribute :>> subjectPath="dev/refactoring/modern-c/models/lean/DarwinForceBinding.lean"; attribute :>> subjectScope="Declaration-ID resolved extraction meaning and abstract child debt lemmas"; attribute :>> premise="Retained Darwin configuration and pinned typed IR; no loaded binary or C11 qualification"; }
part source:GambitAssuranceRouting::ModelNeed { ref part :>> owner=GambitBuildAssurance::planner.component; attribute :>> obligationId="DF-S"; attribute :>> kind="source-refinement"; attribute :>> subjectPath="dev/refactoring/modern-c/darwin-force-binding-design.org"; attribute :>> subjectScope="Effective force windows complete source reader closure and JSON bridge OPEN"; attribute :>> premise="Retained Darwin configuration and pinned typed IR; no loaded binary or C11 qualification"; }
part platform:GambitAssuranceRouting::ModelNeed { ref part :>> owner=GambitBuildAssurance::planner.component; attribute :>> obligationId="DF-E"; attribute :>> kind="environment-refinement"; attribute :>> subjectPath="dev/refactoring/modern-c/darwin-force-binding-design.org"; attribute :>> subjectScope="C11 ledger and actual Darwin compiler binary loader correspondence OPEN"; attribute :>> premise="Retained Darwin configuration and pinned typed IR; no loaded binary or C11 qualification"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitForceMaintenanceFidelity::source; }

part def ModelFlow { attribute fromNode:String; attribute toNode:String; attribute reason:String; }
part flow0:ModelFlow { attribute :>> fromNode="c0"; attribute :>> toNode="c1"; attribute :>> reason="Profile selects expanded transfer route"; }
part flow1:ModelFlow { attribute :>> fromNode="c0"; attribute :>> toNode="c2"; attribute :>> reason="Profile selects catcher and host-exit route"; }
part flow2:ModelFlow { attribute :>> fromNode="c1"; attribute :>> toNode="o3"; attribute :>> reason="Actual unit identity remains required"; }
part flow3:ModelFlow { attribute :>> fromNode="c2"; attribute :>> toNode="c4"; attribute :>> reason="Exception cleanup retains cohort grant"; }
part flow4:ModelFlow { attribute :>> fromNode="c3"; attribute :>> toNode="c4"; attribute :>> reason="Inherited child debt delays retirement"; }
part flow5:ModelFlow { attribute :>> fromNode="c3"; attribute :>> toNode="o1"; attribute :>> reason="Finite private to queued to reader histories"; }
part flow6:ModelFlow { attribute :>> fromNode="c4"; attribute :>> toNode="o2"; attribute :>> reason="Conditional debt arithmetic"; }
part flow7:ModelFlow { attribute :>> fromNode="c4"; attribute :>> toNode="o5"; attribute :>> reason="Concrete memory-order refinement remains open"; }
part flow8:ModelFlow { attribute :>> fromNode="o5"; attribute :>> toNode="o6"; attribute :>> reason="All actual users must satisfy refinement premises"; }
part flow9:ModelFlow { attribute :>> fromNode="c5"; attribute :>> toNode="o0"; attribute :>> reason="Resolved identity extraction theorem"; }
part flow10:ModelFlow { attribute :>> fromNode="c5"; attribute :>> toNode="o4"; attribute :>> reason="Pinned JSON witness and rejecting controls"; }
part flow11:ModelFlow { attribute :>> fromNode="o0"; attribute :>> toNode="o4"; attribute :>> reason="Resolver construction is still trusted"; }
}
