package GambitEntryAdmission {
 private import ScalarValues::*;
 attribute stage:String="rc-entry-admission";
 attribute baseline:String="4b9ac8430dcc6021327fb33ff04c68a0fb5cdd34";
 attribute scope:String="Complete RC source registration/mutation/borrow and activation-owned SFUN span admission, including marker, freeze, exceptional physical exit and same-ABI consumers. General foreign entry, startup/resize retirement and other queued source work remain separate.";
 attribute formalDuty:String="Existing native_entry_admission.qnt alone owns marker revocation/freeze/physical exit. Existing root_store_projection.qnt owns root lifetime and borrowed identity. No new Lean theorem: unchanged RootSpan arithmetic only. C pointer validity, cooperative owners and locks are conditional source premises.";
 attribute sourceCases:String="registration;activation-store;borrow-scan;physical-exit;abi-and-generation";
 attribute requiredCases:String="baseline-witness;production-pbt;nonzero;exception;existing-consumers;model;cost;source-custody";
 part def Component { attribute source:String; attribute owns:String; attribute contract:String; }
 part source:Component { attribute :>> source="vendor/gambit/lib/_mem/rc-allocation.inc;vendor/gambit/lib/rc.h"; attribute :>> owns="Registration, including duplicate registration, and write/borrow admission share actual current owner/OPEN/not-joined source authority under the existing RC mutex."; attribute :>> contract="Registration cannot bypass source closure via its old same-domain early return. Rejection neither links storage nor changes counts. Caller owns valid RC storage before inspecting its header; no arbitrary pointer validation is claimed."; }
 part activation:Component { attribute :>> source="vendor/gambit/lib/_mem/rc-allocation.inc: store_rc_root / ___sfun_arg;vendor/gambit/lib/_c_intf/sfun-entry.inc"; attribute :>> owns="Only ROOTED or ACTIVE actual SFUN records authorize positive argument indices. A raw store or one outstanding borrow cannot supply that identity. Public generated ABI remains unchanged."; attribute :>> contract="Same current owner, record root bank, finite checked index and exactly one bank borrow precede mutation. Revoked records retain their roots until last C use but never reacquire write permission, including after GC. No extra table/record/permit. Colocation may remove a machine-code call; inspect actual linked code and measure rather than assume inlining."; }
 part exitOwner:Component { attribute :>> source="vendor/gambit/lib/_setup/vm-registry.inc;vendor/gambit/lib/_setup/vm-lifecycle.inc;vendor/gambit/include/_gambit/foreign_conversion.h.in"; attribute :>> owns="Existing generated try/catcher/end owns the bank borrow and lifecycle entry until physical C exit; GC may relocate canonical roots while revoked."; attribute :>> contract="No eager release at marker kill. Nested callback/continuation escape still has its own actual activation. Failed/unknown join does not prove last use. Arbitrary dead-thread takeover and general CFFI are outside."; }
 attribute refinements:String="registrationMap;storeMap;exitMap";
 part def Refinement { attribute actions:String; attribute source:String; attribute guard:String; attribute obligation:String; attribute quint:String; attribute leanDuty:String default="No duplicate lifecycle theorem; existing RootSpan arithmetic unchanged."; }
 part registrationMap:Refinement { attribute :>> actions="publishCarrier;borrowCell;freeze;scan;returnBorrow"; attribute :>> source="___register_rc;___borrow_rc_root;root_writer_open"; attribute :>> guard="Actual owner/source identity plus same RC mutex; cooperative scanner freeze precedes relocation. Duplicate registration receives no closure bypass."; attribute :>> obligation="ENTRY-SOURCE"; attribute :>> quint="dev/refactoring/modern-c/models/quint/root_store_projection.qnt"; }
 part storeMap:Refinement { attribute :>> actions="writeEntryState;populateConverted;revokeMarker;freezeWriters;thawWriters"; attribute :>> source="store_rc_root;___sfun_arg;___store_rc_root"; attribute :>> guard="Prepared versus active maps to actual record kind. Revoked write permission never follows from retained physical storage. No poll/callback/allocation between admission and store."; attribute :>> obligation="ENTRY-ACTIVATION"; attribute :>> quint="dev/refactoring/modern-c/models/quint/native_entry_admission.qnt"; }
 part exitMap:Refinement { attribute :>> actions="revokeMarker;recordOutcome;settleKnown;retireCarrier"; attribute :>> source="___lifecycle_marker_kill;___end_sfun;___lifecycle_marker_abort"; attribute :>> guard="Actual last C use, not logical revocation or unknown join, discharges borrow. Existing scanner updates roots while storage remains registered."; attribute :>> obligation="ENTRY-EXIT"; attribute :>> quint="dev/refactoring/modern-c/models/quint/native_entry_admission.qnt"; }
 part def Obligation { attribute id:String; attribute status:String; attribute premise:String; }
 attribute obligations:String="sourceProof;activationProof;borrowProof;exitProof;abiProof;propertyProof;costProof";
 part sourceProof:Obligation { attribute :>> id="ENTRY-SOURCE"; attribute :>> status="CLOSED"; attribute :>> premise="Registration/write/borrow use one actual source authority; duplicate registration has no early OPEN bypass."; }
 part activationProof:Obligation { attribute :>> id="ENTRY-ACTIVATION"; attribute :>> status="CLOSED"; attribute :>> premise="Raw positive-index writes and revoked SFUN writes refused without mutation; actual retained-scope baseline witness."; }
 part borrowProof:Obligation { attribute :>> id="ENTRY-BORROW"; attribute :>> status="CLOSED"; attribute :>> premise="Borrow pins storage/logical identity, not execution permission or a moving Scheme address; GC and reload remain actual consumers."; }
 part exitProof:Obligation { attribute :>> id="ENTRY-EXIT"; attribute :>> status="CLOSED"; attribute :>> premise="Logical revoke retains bank/entry through GC until actual end; nested exceptions and multi-shot restoration preserved."; }
 part abiProof:Obligation { attribute :>> id="ENTRY-ABI"; attribute :>> status="CLOSED"; attribute :>> premise="Same public generated names/layout, old module/callback consumers; no Scheme generation on C-only transition."; }
 part propertyProof:Obligation { attribute :>> id="ENTRY-PROPERTY"; attribute :>> status="CLOSED"; attribute :>> premise="Real native stateful histories include revocation, replay and shrink; existing QNT tests target disjoint protocol obligations."; }
 part costProof:Obligation { attribute :>> id="ENTRY-COST"; attribute :>> status="CLOSED"; attribute :>> premise="Paired same fixture/roles0/1/8 workloads and linked arm64 code; no stable speedup or total-allocation inference."; }
 part submission:GambitCommitGates::SubmissionUnit { attribute :>> kind="integration"; attribute :>> result="rc-entry-admission"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="ENTRY-TESTS"; attribute :>> method="native"; attribute :>> artifact="evidence/research/retained/modern-c/entry-admission/qualification.json"; attribute :>> scope="Actual baseline witness and full scoped native registration/borrow/SFUN/GC/exception consumers; original broader negatives remain separate."; }
 part learning:Need { ref part :>> gate=GambitCommitGates::learning; attribute :>> id="ENTRY-LEARNING"; attribute :>> method="source-analysis"; attribute :>> artifact="dev/refactoring/modern-c/entry-admission.org"; attribute :>> scope="Physical root custody and logical mutation permission have distinct lifetimes; borrow count is not activation identity."; }
 part process:Need { ref part :>> gate=GambitCommitGates::process; attribute :>> id="ENTRY-PROCESS"; attribute :>> method="source-analysis"; attribute :>> artifact="dev/refactoring/modern-c/entry-admission.org"; attribute :>> scope="One complete source/activation owner; no startup/resize/scheduler or whole-SMP promotion."; }
 part models:Need { ref part :>> gate=GambitCommitGates::models; attribute :>> id="ENTRY-MODELS"; attribute :>> method="native"; attribute :>> artifact="evidence/research/retained/modern-c/entry-admission/qualification.json"; attribute :>> scope="Native SDK and ASCENT seven obligations/three adapters; existing QNT adds revoked-write-after-GC case; no duplicate Lean."; }
 part questions:Need { ref part :>> gate=GambitCommitGates::questions; attribute :>> id="ENTRY-QUESTIONS"; attribute :>> method="source-analysis"; attribute :>> artifact="dev/refactoring/modern-c/entry-admission.org"; attribute :>> scope="Actual writers, aliases, freeze, GC roots, physical exit, source reuse and matched regression accounting addressed conditionally."; }
}
