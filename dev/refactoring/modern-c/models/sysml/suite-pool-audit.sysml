package GambitSuitePoolAudit {
 private import ScalarValues::*;
 attribute scope:String="Complete fixed-pool producer, observation-owner, exclusive lease and test-caller correction. All original limits and assertions remain. No runtime source or independent SMP-family promotion.";
 attribute stage:String="suite-pool-caller-closure";
 attribute formalDuty:String="OpenSysML SDK resolves the actual producer/lease/receipt owners. Existing ASCENT gates bind the exact Git Python source period, complete test consumers and historical CI failure inventory. Existing QNT/Lean runtime duties remain distinct and unchanged.";
 part submission:GambitCommitGates::SubmissionUnit {
  attribute :>> kind="support"; attribute :>> result=""; attribute :>> progressDelta=0;
  attribute :>> supportPaths="dev/refactoring/modern-c/header-build.d2;dev/refactoring/modern-c/header-build.org;dev/refactoring/modern-c/models/sysml/suite-pool-audit.sysml;dev/refactoring/modern-c/models/sysml/suite-pool-custody.sysml;evidence/research/retained/modern-c/header-build/continuation-accounting.json;evidence/research/retained/modern-c/header-build/pool-architecture-inputs.json;evidence/research/retained/modern-c/header-build/pool-caller-validation.json;evidence/research/retained/modern-c/header-build/pool-fixtures-inputs.json;evidence/research/retained/modern-c/header-build/pool-library-inputs.json;evidence/research/retained/modern-c/header-build/pool-source-period.json;evidence/research/retained/modern-c/header-build/pool-validation.json;evidence/research/retained/modern-c/header-build/remote-ci-0017.json;evidence/research/retained/modern-c/header-build/suite-pool-model.json;src/gambit_smp/artifact_storage.py;src/gambit_smp/revision_submission.py;src/gambit_smp/suite_primitives.py;tests/support.py;tests/test_artifact_storage.py;tests/test_native_recipes.py;tests/test_native_suite.py;tests/test_revision_submission.py;tests/test_stress_inventory.py;tests/test_suite_observations.py";
  attribute :>> testModules="tests/test_artifact_storage.py;tests/test_native_recipes.py;tests/test_native_suite.py;tests/test_revision_submission.py;tests/test_stress_inventory.py;tests/test_suite_observations.py";
 }
 part def Need { ref part gate:GambitCommitGates::Gate; attribute id:String; attribute method:String; attribute artifact:String; attribute scope:String; }
 part tests:Need { ref part :>> gate=GambitCommitGates::tests; attribute :>> id="SUITE-POOL-TESTS"; attribute :>> method="native"; attribute :>> artifact="evidence/research/retained/modern-c/header-build/pool-validation.json"; attribute :>> scope="All six whole test modules finish158 tests with zero failure/error/skip and no input changes. Cover real exclusive lease, both receipt layouts, foreign owners, deadline/preparation, payload capture and unknown child refusal; synthetic stubs remain test-only."; }
 part learning:Need { ref part :>> gate=GambitCommitGates::learning; attribute :>> id="SUITE-POOL-LEARNING"; attribute :>> method="source-analysis"; attribute :>> artifact="dev/refactoring/modern-c/header-build.org"; attribute :>> scope="Bind producer and lease consumer in one cut. Directory spelling is not ownership; use the existing task_output authority. Frozen full Python source periods prevent reliance on dirty unselected imports."; }
 part process:Need { ref part :>> gate=GambitCommitGates::process; attribute :>> id="SUITE-POOL-PROCESS"; attribute :>> method="source-analysis"; attribute :>> artifact="dev/refactoring/modern-c/header-build.org"; attribute :>> scope="Correct the observed CI pre-execution barriers without changing Gambit, heap, limits or assertions. KeepSMP4/12; full historical framework failure inventory remains visible and is not waived."; }
 part models:Need { ref part :>> gate=GambitCommitGates::models; attribute :>> id="SUITE-POOL-MODELS"; attribute :>> method="native"; attribute :>> artifact="evidence/research/retained/modern-c/header-build/suite-pool-model.json"; attribute :>> scope="Strict pinned OpenSysML SDK resolves all four model-listed components; existing ASCENT binds this exact support cut and refuses missing/stale gates."; }
 part questions:Need { ref part :>> gate=GambitCommitGates::questions; attribute :>> id="SUITE-POOL-QUESTIONS"; attribute :>> method="source-analysis"; attribute :>> artifact="dev/refactoring/modern-c/header-build.org"; attribute :>> scope="Answer exact owner, observation/lease identity, source period, synthetic-versus-native lifecycle and remaining platform/history boundaries. Never infer global CI success or SMP-family progress."; }
}
