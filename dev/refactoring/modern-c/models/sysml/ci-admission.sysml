package GambitCIAdmission {
 private import ScalarValues::*;
 attribute scope:String="Complete CI input-consumer refinement: recorded source epochs and maintained-runtime caller policy. No new execution layer, refreshed hashes, scheduler or runtime change.";
 attribute stage:String="Support only, progressDelta0. Local architecture3/4 and independent SMP1/12. Fourth integration blocked on fresh remote consumers and hosted macOS attribution.";
 attribute formalDuty:String="Existing incremental_build.qnt owns bounded scheduling; IncrementalBuild.lean owns conditional input algebra. Immutable-object and real interface refinement is source/native evidence, not duplicate QNT or Lean.";
 attribute historicalRule:String="Every old SHA, fact, range and pointer remains unchanged. Read original Git blob; deny absent or wrong objects. Authored generated view must pass the actual existing ASCENT producer binding.";
 attribute reuseRule:String="Existing runtime prepare_import requires explicit in-place policy. All original eight graphs, source locks, modes, workloads, timeoutPolicy and stage limits stay unchanged; no test pass is inferred from preflight admission.";
 attribute remoteRule:String="3a build PASS at330.750313393s closes seed finalization transport only. Framework and eight module failures remain historical failures; next source CI is independent. Hosted macOS baseline/candidate currently queued; historical images differ.";
 attribute producer:String="src/gambit_smp/view_materialize.py#materialize";
 attribute sourceReader:String="src/gambit_smp/source_identity.py#read_source";
 attribute runtimeConsumer:String="src/gambit_smp/runtime_artifact.py#prepare_import";
 attribute closureRule:String="All44 registered views and all3 producer bindings load; cross-view references remain bound to original source epochs. Two transitive dependencies must not acquire a refreshed expected hash.";
 attribute inventoryRule:String="Only prevalidated gambit.suite.expectedSource matching the exact import candidate is read-only. Graph/native_capabilities validates its runtime ancestry; expected_suite_inventory reads file names only. Other operands and aliases retain mutation refusal.";
 attribute makeRule:String="Keep original incomplete Make declaration as an adverse control. Three real callers select existing sealed qualified-upstream-tests.json, including the missing multi-target core-recursive header. No header predicate, target, mode, workload, timeout or review weakened.";
 attribute currentObservation:String="Full54 module cases,44 registered view loads,3 generated bindings,2 original cross-view identities.865 source-core PASS343.545440768s. New remote framework/modules and hosted macOS attribution remain independent gates.";
 attribute diagram:String="direction: right\npast: Original source revision + hash\nview: Recorded view + ranges + facts\nproducer: Existing ASCENT producer + binding\nrecipe: Original eight CI Recipes\npolicy: Existing in-place workspace interface\nchecks: Full module tests + real consumers\nremote: New remote framework and module receipts\nmac: Hosted macOS paired attribution\nfourth: Fourth runtime integration gate\npast -> view: immutable Git identity\nview -> producer: unchanged claims\nrecipe -> policy: explicit declaration only\nproducer -> checks\npolicy -> checks\ndependency: Complete44-view dependency closure\nborrow: Typed inventory read only\nmake: Existing complete Make declaration\ndependency -> checks: original identities and bindings\nborrow -> checks: other aliases rejected\nmake -> checks: incomplete declaration still rejects\nchecks -> remote: local support qualification only\nremote -> fourth: must independently pass\nmac -> fourth: currently queued and unresolved\n";
 part def Need { attribute id:String; ref part gate:GambitCommitGates::Gate; attribute method:String; attribute artifact:String; attribute scope:String; }
 part tests:Need { attribute :>> id="CI-ADMISSION-TESTS"; ref part :>> gate=GambitCommitGates::tests; attribute :>> method="native"; attribute :>> artifact="evidence/research/retained/modern-c/ci-consumer-closure/receipt.json"; attribute :>> scope="Bounded CI input support; no historical outcome rewrite or fourth integration admission"; }
 part learning:Need { attribute :>> id="CI-ADMISSION-LEARNING"; ref part :>> gate=GambitCommitGates::learning; attribute :>> method="source-refinement"; attribute :>> artifact="evidence/research/retained/modern-c/ci-consumer-closure/receipt.json"; attribute :>> scope="Bounded CI input support; no historical outcome rewrite or fourth integration admission"; }
 part process:Need { attribute :>> id="CI-ADMISSION-PROCESS"; ref part :>> gate=GambitCommitGates::process; attribute :>> method="source-refinement"; attribute :>> artifact="evidence/research/retained/modern-c/ci-consumer-closure/receipt.json"; attribute :>> scope="Bounded CI input support; no historical outcome rewrite or fourth integration admission"; }
 part models:Need { attribute :>> id="CI-ADMISSION-MODELS"; ref part :>> gate=GambitCommitGates::models; attribute :>> method="source-refinement"; attribute :>> artifact="evidence/research/retained/modern-c/ci-consumer-closure/receipt.json"; attribute :>> scope="Bounded CI input support; no historical outcome rewrite or fourth integration admission"; }
 part questions:Need { attribute :>> id="CI-ADMISSION-QUESTIONS"; ref part :>> gate=GambitCommitGates::questions; attribute :>> method="source-refinement"; attribute :>> artifact="evidence/research/retained/modern-c/ci-consumer-closure/receipt.json"; attribute :>> scope="Bounded CI input support; no historical outcome rewrite or fourth integration admission"; }
 part submission:GambitCommitGates::SubmissionUnit { attribute :>> kind="support"; attribute :>> result=""; attribute :>> progressDelta=0; attribute :>> supportPaths="src/gambit_smp/runtime_artifact.py;tests/test_runtime_artifact.py;tests/test_upstream_tests.py;tests/test_source_identity.py;evidence/scenarios/concurrent-gc/working-modeling.view.json;evidence/scenarios/concurrent-gc/reasoning-methods.view.json;evidence/scenarios/concurrent-gc/reasoning-methods.view.source.json;evidence/scenarios/concurrent-gc/reasoning-methods.view.binding.json;evidence/research/ci/upstream-check.recipe.json;evidence/research/ci/gc-ffi.recipe.json;evidence/research/ci/compile-execute.recipe.json;dev/refactoring/modern-c/models/sysml/ci-admission.sysml;dev/refactoring/modern-c/ci-admission.org;dev/refactoring/modern-c/branch-checklist.org;dev/refactoring/modern-c/diagrams/ci-admission.d2;dev/refactoring/modern-c/diagrams/ci-admission.svg;evidence/research/retained/modern-c/ci-consumer-closure/receipt.json;evidence/research/retained/modern-c/ci-consumer-closure/remote.json;evidence/research/retained/modern-c/ci-consumer-closure/tests.txt;evidence/research/retained/modern-c/ci-consumer-closure/framework-failure.txt"; attribute :>> testModules="tests/test_source_identity.py;tests/test_runtime_artifact.py;tests/test_upstream_tests.py"; }
}
