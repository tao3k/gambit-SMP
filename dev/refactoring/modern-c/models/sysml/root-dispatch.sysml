package GambitRootDispatch {
  private import ScalarValues::*;
  ref part predecessor=GambitRevisionDelivery::runtimeBinding;
  ref part selected=GambitRevisionDelivery::rootDispatch;
  attribute base:String="vendor/gambit b77ad85cd338adad6ea571395975bdb2166dd147";
  attribute status:String="READY-FOR-SOURCE-REFINEMENT; predecessor CI accepted, no RootTask implementation or native admission. Existing storage/fixture tests do not qualify this successor's seven duties";
  attribute predecessorGate:String="CLOSED for b77ad85c: exact-head run40456227030 succeeds on all five platform jobs and ReportResult; actual MSVC Test compiles/executes frame-contract and continuation/root consumers with all290 fixture declarations retained. MinGW32 keeps its official Test skip. Original bf08f39f run40453535604 failure remains historical evidence. Begin ROOT-SOURCE refinement from the published base, not the dirty prototype; no root-dispatch runtime acceptance transfers from this green CI";
  attribute scope:String="Replace the complete strong-root census, frozen-origin publication, explicit scan-source adapters, generation-checked task claim, completion and source-borrow release. Roots are selected from RootOrigin, never inferred from the collector carrier index";
  attribute publicBoundary:String="Keep public Gambit names, GVM/frame descriptor semantics, multi-shot continuation, configure/Make/CI entries and the committed flat gambit.h.in. Private role types/signatures may change when required. The pending header-module split, generic CFFI redesign and new test framework are excluded";
  attribute identity:String="VM identity plus closed GC epoch, origin kind/slot and partition. Stable bounded records; no unbounded identity table. Reuse needs all task/reader borrows drained and prior claims excluded. Reject epoch exhaustion; a separately read generation followed by state-only CAS is not ABA protection";
  attribute publication:String="Managed root writers stop and root-address view freezes before release-publishing the immutable census. Claim acquires that publication under a generation/lifetime pin. Completion release-publishes rewritten roots; an acquire observer releases source borrows only after existing whole-round strong/weak/copy/cleanup barriers allow it. Actual barrier/lock refinement is mandatory";
  attribute sourceOwnership:String="Context owns Scheme root storage; RC heads remain explicitly borrowed from their actual PSTATE owners in this cut; VM/global root descriptors preserve existing ownership disciplines. Descriptor metadata cannot extend the lifetime of an unpinned source. External/raw writers without a demonstrated freeze contract remain a blocking premise";
  attribute executionBoundary:String="Worker allocation/restore/cleanup policy remains the committed policy. Task eligibility records its required allocation and thread-affinity capabilities. Where only same-carrier capacity is qualified, assignment remains explicitly constrained; arbitrary stealing, independent worker counts and whole-collector W<R require the later worker arena/restoration cut";
  attribute states:String="Collecting -> FrozenPublished -> Ready -> Claimed -> Scanning -> Done -> RoundDrained -> Reusable. Ready claim has one winner. Known rejection before scanner entry retains source custody. A lost completion result is queried by the same key; it is not permission to scan again";
  attribute unknownRule:String="Unknown execution/stop/join keeps the task, source roots and descriptor pinned. A worker may return an unstarted task only with a stop/entry-exclusion proof. After possible scanner entry, do not requeue destructive stack/frame work without a separate progress/recovery proof. Root-task completion alone never permits VM/PSTATE/global cleanup";
  attribute benefit:String="One source-explicit root census covers every admitted context and actual RC head; VM/global work is explicit instead of processor-zero authority. RootTask owns unique root-job permission independently of collector identity, enabling later worker-policy changes without rewriting root meaning. No reduced object scan/copy count or speedup is established by this design";
  attribute addedCost:String="R origin records plus K tasks and bounded borrow/status metadata: O(R+K) space and publication/claim/completion work. Size bytes require actual C sizeof; roots and reachable objects still require their existing scans. No extra heap or timeout is authorized";
  attribute retirement:String="Retire carrier-index-derived root selection and root-range partitioning, leader-only implicit RC coverage, and root scanner reads of the executor's context as its source. Preserve the current copy/weak algorithm and worker allocation owner; task uniqueness does not establish unique object/frame copy";
  attribute stopRule:String="No code REV until all seven needs and five gates close for one exact source tree. Source model links, existing tests or the current storage REV cannot discharge missing claim protocol, source coverage, writer freeze or native evidence";

  part def Route { attribute id:String; attribute path:String; attribute symbol:String; attribute duty:String; }
  part contexts:Route { attribute :>> id="context-roots"; attribute :>> path="lib/_mem/capacity-resize.inc;lib/_mem/root-origins.inc"; attribute :>> symbol="mark_registers;mark_saved;mark_type_cache;mark_processor_scmobj"; attribute :>> duty="Read the frozen origin's bank; keep executor allocation/diagnostic ownership explicit"; }
  part stacks:Route { attribute :>> id="continuation-roots"; attribute :>> path="lib/_mem/continuation-roots.inc"; attribute :>> symbol="mark_continuation;mark_frame;mark_captured_continuation"; attribute :>> duty="Origin supplies fp/stack_break and frame address view; retain existing frame-root cursor, multi-shot shared reachability and forwarding protocol"; }
  part globals:Route { attribute :>> id="vm-global-roots"; attribute :>> path="lib/_mem/root-origins.inc;lib/_mem/collection-round.inc"; attribute :>> symbol="mark_vm_scmobj;mark_global_variables;mark_symkey_tables;garbage_collect_mark_strong_phase"; attribute :>> duty="Explicit VM/global root tasks and partition descriptors; preserve global/VM ownership and include empty/single-origin cases"; }
  part rc:Route { attribute :>> id="rc-roots"; attribute :>> path="lib/_mem/configuration.inc;lib/_mem/rc-allocation.inc;lib/_mem/rc-roots.inc;lib/_mem/collection-round.inc"; attribute :>> symbol="rc_head;___alloc_rc;mark_rc;garbage_collect_mark_strong_phase"; attribute :>> duty="Close actual registration/write/scan/cleanup callers for every admitted RC owner; source shows per-PSTATE heads and leader-selected scan, but nonzero caller reachability still requires qualification"; }
  part lifecycle:Route { attribute :>> id="root-task-lifetime"; attribute :>> path="include/gambit.h.in;lib/_mem/collection-round.inc;lib/_mem/memory-lifecycle.inc;lib/_mem/capacity-resize.inc;lib/setup.c"; attribute :>> symbol="GC entry/exit;setup/resize membership;root census publication/claim/finish adapters to be introduced"; attribute :>> duty="Freeze a stable source roster, guard record reuse and writer reentry; do not infer writer stop from a logical flag or whole-round completion from root-task count"; }

  part def Need { ref part gate:GambitCommitGates::Gate; attribute id:String; attribute method:String; attribute artifact:String; attribute scope:String; }
  part source:Need { ref part :>> gate=GambitCommitGates::tests; attribute :>> id="ROOT-SOURCE"; attribute :>> method="source-refinement"; attribute :>> artifact="vendor/gambit/lib/_mem/collection-round.inc"; attribute :>> scope="Actual reader/writer/registration/cleanup census and explicit origin vs executor arguments, including nonzero RC producers; generation/pin, memory-order and failure custody refinement. OPEN"; }
  part protocol:Need { ref part :>> gate=GambitCommitGates::tests; attribute :>> id="ROOT-PROTOCOL"; attribute :>> method="bounded-protocol"; attribute :>> artifact="dev/refactoring/modern-c/models/quint/runtime_roles.qnt"; attribute :>> scope="Extend this existing model with task readiness/owner, claims, duplicate/lost completion, stale epoch, close/claim/reentry and stopped-vs-unknown worker schedules. Existing scanned-set model lacks those states; no new result claimed. OPEN"; }
  part coverage:Need { ref part :>> gate=GambitCommitGates::models; attribute :>> id="ROOT-COVERAGE"; attribute :>> method="universal-coverage"; attribute :>> artifact="dev/refactoring/modern-c/models/lean/RuntimeRoles.lean"; attribute :>> scope="Refine logical root cells/origin families and partitions to actual C/FrameSpec consumers for arbitrary census size. Existing Covered only proves scanned subset of frozen, not completeness. Do not duplicate QNT interleavings. OPEN"; }
  part native:Need { ref part :>> gate=GambitCommitGates::tests; attribute :>> id="ROOT-NATIVE"; attribute :>> method="native"; attribute :>> artifact="vendor/gambit/tests/runtime-roles.c"; attribute :>> scope="Reuse existing test targets and same Bazel/cache: exact full bootstrap <=600s, original check/disposition, nonzero-origin and RC moving-root updates, real map multi-shot/GC, stale/duplicate claim and unknown-stop refusal. W<R dispatcher-only observations are not whole-GC acceptance. OPEN"; }
  part learning:Need { ref part :>> gate=GambitCommitGates::learning; attribute :>> id="ROOT-AUDIT"; attribute :>> method="source-analysis"; attribute :>> artifact="dev/refactoring/modern-c/root-dispatch.org"; attribute :>> scope="Per-path necessary retirement and measured root coverage, duplicate-job prevention and actual metadata/atomic/peak costs; no invented speedup or inherited SMP credit. OPEN for implementation"; }
  part processNeed:Need { ref part :>> gate=GambitCommitGates::process; attribute :>> id="ROOT-PROCESS"; attribute :>> method="source-analysis"; attribute :>> artifact="dev/refactoring/modern-c/models/sysml/root-dispatch.sysml"; attribute :>> scope="Complete root-dispatch responsibility after published b77ad85c; worker arena/restoration, entry lifetime and VM cleanup remain dependency-bound cuts. OPEN for implementation"; }
  part questions:Need { ref part :>> gate=GambitCommitGates::questions; attribute :>> id="ROOT-QUESTIONS"; attribute :>> method="source-analysis"; attribute :>> artifact="dev/refactoring/modern-c/root-dispatch.org"; attribute :>> scope="Actual producer closure, frozen global ownership, root aliases vs object forwarding, affinity/capacity, bounded reuse, unknown worker effects and Gambit multi-shot amplification answered before code commit. OPEN"; }
}
