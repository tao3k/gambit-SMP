package GambitPersistentCarrierCoverage { private import ScalarValues::*;
part def Owner { attribute componentId:String; }
part registryOwner:Owner { attribute :>> componentId="registry"; }
part rootsOwner:Owner { attribute :>> componentId="roots"; }
part writerOwner:Owner { attribute :>> componentId="writer"; }
part guardOwner:Owner { attribute :>> componentId="guard"; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-init"; attribute :>> path="vendor/gambit/lib/memory/rc-allocation.inc"; attribute :>> needle="h->data = ___FAL;"; attribute :>> obligation="Native allocation initializes data before registration; not a source lease"; }
part source4:SourceRow { attribute :>> key="rc-register"; attribute :>> path="vendor/gambit/lib/memory/rc-allocation.inc"; attribute :>> needle="tail->next = h;"; attribute :>> obligation="Plain list insertion requires owner and collector exclusion"; }
part source5:SourceRow { attribute :>> key="rc-free"; attribute :>> path="vendor/gambit/lib/memory/rc-allocation.inc"; attribute :>> needle="if (--h->refcount == 0)"; attribute :>> obligation="Nonatomic decrement and unlink are not safe arbitrary-thread admission"; }
part source6:SourceRow { attribute :>> key="rc-retain"; attribute :>> path="vendor/gambit/lib/memory/rc-allocation.inc"; attribute :>> needle="h->refcount++;"; attribute :>> obligation="Dereferences existing header; cannot safely retain already-freed raw client_data"; }
part source7:SourceRow { attribute :>> key="rc-read"; attribute :>> path="vendor/gambit/lib/memory/rc-allocation.inc"; attribute :>> needle="return h->data;"; attribute :>> obligation="Raw native copy is not a registered update slot"; }
part source8:SourceRow { attribute :>> key="rc-write"; attribute :>> path="vendor/gambit/lib/memory/rc-allocation.inc"; attribute :>> needle="h->data = val;"; attribute :>> obligation="All semantic writers must join freeze/generation protocol or deny admission"; }
part source9:SourceRow { attribute :>> key="rc-cleanup"; attribute :>> path="vendor/gambit/lib/memory/rc-allocation.inc"; attribute :>> needle="___HIDDEN void cleanup_rc"; attribute :>> obligation="Bulk cleanup frees chain independent of per-entry leases"; }
part source10:SourceRow { attribute :>> key="rc-scan"; attribute :>> path="vendor/gambit/lib/memory/rc-roots.inc"; attribute :>> needle="mark_array (work, &h->data, 1);"; attribute :>> obligation="Actual GC slot update; target private carrier is not implicitly scanned"; }
part source11:SourceRow { attribute :>> key="retire-refuse"; attribute :>> path="vendor/gambit/lib/memory/capacity-resize.inc"; attribute :>> needle="return 0; /* no freeze receipt for external RC/native borrowers */"; attribute :>> obligation="Current processor retirement refuses nonempty RC rather than manufacturing a lease"; }
part source12:SourceRow { attribute :>> key="pstate-cleanup"; attribute :>> path="vendor/gambit/lib/memory/memory-lifecycle.inc"; attribute :>> needle="free_still_objs (___ps);"; attribute :>> obligation="cleanup_mem_pstate frees still storage before cleanup_rc; not an active-lease release helper"; }
part source13:SourceRow { attribute :>> key="vm-cleanup"; attribute :>> path="vendor/gambit/lib/memory/memory-lifecycle.inc"; attribute :>> needle="___cleanup_mem_pstate (___PSTATE_FROM_PROCESSOR_ID(0,___vms));"; attribute :>> obligation="VM cleanup still has other-processors TODO; global retirement qualification cannot be inferred"; }
part source14:SourceRow { attribute :>> key="pstate-wrapper"; attribute :>> path="vendor/gambit/lib/setup.c"; attribute :>> needle="___cleanup_mem_pstate (___ps);"; attribute :>> obligation="PSTATE cleanup wrapper reaches destructive memory cleanup before OS cleanup"; }
part source15:SourceRow { attribute :>> key="setter-export"; attribute :>> path="vendor/gambit/lib/setup.c"; attribute :>> needle="= ___set_data_rc;"; attribute :>> obligation="Public GSTATE function pointer permits indirect/out-of-tree callers; lexical sites do not close writer authority"; }
part source16:SourceRow { attribute :>> key="register-export"; attribute :>> path="vendor/gambit/lib/setup.c"; attribute :>> needle="= ___register_rc;"; attribute :>> obligation="Public registration ABI is not a stable VM SourceOwner registry"; }
part source17:SourceRow { attribute :>> key="context-owner"; attribute :>> path="vendor/gambit/lib/memory/configuration.inc"; attribute :>> needle="#define rc_head                 ___CONTEXT_MEM(rc_head_)"; attribute :>> obligation="RC chain belongs to context; not independent VM owner identity"; }
part source18:SourceRow { attribute :>> key="closure-writer"; attribute :>> path="vendor/gambit/lib/os_dyn.c"; attribute :>> needle="___set_data_rc (c_closure, proc);"; attribute :>> obligation="Concrete semantic payload installer, architecture conditional"; }
part source19:SourceRow { attribute :>> key="closure-release"; attribute :>> path="vendor/gambit/lib/os_dyn.c"; attribute :>> needle="___release_rc (c_closure);"; attribute :>> obligation="Indirect function release reaches native RC retirement"; }
part source20:SourceRow { attribute :>> key="release-function"; attribute :>> path="vendor/gambit/lib/c_intf.c"; attribute :>> needle="if (___is_a_c_closure (x))"; attribute :>> obligation="Function retain/release wrappers reach RC API conditionally"; }
part source21:SourceRow { attribute :>> key="release-string"; attribute :>> path="vendor/gambit/lib/c_intf.c"; attribute :>> needle="___EXP_FUNC(void,___release_string)"; attribute :>> obligation="RC API also owns native buffers; root-bearing sources must be classified separately"; }
part source22:SourceRow { attribute :>> key="tls-release"; attribute :>> path="vendor/gambit/lib/os_io.c"; attribute :>> needle="___SCMOBJ ___release_rc_tls_context"; attribute :>> obligation="Native destructor has SSL/string effects; not all RC users are Scheme root sources"; }
part source23:SourceRow { attribute :>> key="epoch-limit"; attribute :>> path="vendor/gambit/lib/memory/heap-sections.inc"; attribute :>> needle="if (___vms->gc_round.epoch >= ___MAX_FIX)"; attribute :>> obligation="Existing round identity refuses exhaustion; no unchecked wrapping receipt"; }
part source24:SourceRow { attribute :>> key="epoch-new"; attribute :>> path="vendor/gambit/lib/memory/heap-sections.inc"; attribute :>> needle="___vms->gc_round.epoch++;"; attribute :>> obligation="Round number created at setup, distinct from semantic payload generation"; }
part source25:SourceRow { attribute :>> key="origin-publish"; attribute :>> path="vendor/gambit/lib/memory/heap-sections.inc"; attribute :>> needle="!___gc_root_task_publish(&___vms->gc_root_tasks[i],"; attribute :>> obligation="Publish follows frozen origin; not generic new-source enrollment"; }
part source26:SourceRow { attribute :>> key="origin-claim"; attribute :>> path="vendor/gambit/lib/memory/collection-round.inc"; attribute :>> needle="if (___gc_root_task_claim(task,___vms->gc_round.epoch,owner))"; attribute :>> obligation="Actual claim checks current round and worker owner"; }
part source27:SourceRow { attribute :>> key="origin-finish"; attribute :>> path="vendor/gambit/lib/memory/collection-round.inc"; attribute :>> needle="if (!___gc_root_task_finish(task,___vms->gc_round.epoch,owner))"; attribute :>> obligation="Task finish has exact owner and epoch boundary"; }
part source28:SourceRow { attribute :>> key="origin-thaw"; attribute :>> path="vendor/gambit/lib/memory/collection-round.inc"; attribute :>> needle="if (!___gc_origin_thaw(&___vms->gc_root_tasks[id],___vms->gc_round.epoch))"; attribute :>> obligation="Resume requires completed origin; not a payload-version receipt"; }
part source29:SourceRow { attribute :>> key="view-drain"; attribute :>> path="vendor/gambit/lib/memory/collection-round.inc"; attribute :>> needle="BARRIER(); /* no worker may retain a stopped root view past this cut */"; attribute :>> obligation="Root view grace cut precedes ordinary execution"; }
part source30:SourceRow { attribute :>> key="growth-cleanup"; attribute :>> path="vendor/gambit/lib/setup.c"; attribute :>> needle="___cleanup_pstate (___PSTATE_FROM_PROCESSOR_ID(i,vms));"; attribute :>> obligation="Known failed growth joins before destructive cleanup; unknown join retains"; }
part source31:SourceRow { attribute :>> key="shrink-cleanup"; attribute :>> path="vendor/gambit/lib/setup.c"; attribute :>> needle="___transfer_retired_still (ps, ___ps);"; attribute :>> obligation="Shrink known join transfers still before cleanup; does not qualify arbitrary native roots"; }
part source32:SourceRow { attribute :>> key="vm-root-retained"; attribute :>> path="vendor/gambit/lib/setup.c"; attribute :>> needle="return; /* do not erase retained source roots through repeated setup */"; attribute :>> obligation="Whole VM cleanup checks resize source requests; generic SourceRegistry not covered"; }
part source33:SourceRow { attribute :>> key="register-abi"; attribute :>> path="vendor/gambit/include/gambit.h"; attribute :>> needle="void *(*___register_rc)"; attribute :>> obligation="Inspected exported return type differs from void implementation spelling; effective header/profile correspondence open"; }
part source34:SourceRow { attribute :>> key="vm-request-slots"; attribute :>> path="vendor/gambit/lib/memory/root-origins.inc"; attribute :>> needle="&___vms->resize_requests[i].thunk"; attribute :>> obligation="All VM request slots scanned independently of participant membership; precedent not generic registry"; }
part source35:SourceRow { attribute :>> key="context-rc-roots"; attribute :>> path="vendor/gambit/lib/memory/root-origins.inc"; attribute :>> needle="mark_rc (work, context);"; attribute :>> obligation="RC roots reached through frozen execution origin"; }
part source36:SourceRow { attribute :>> key="context-startup"; attribute :>> path="vendor/gambit/lib/memory/root-origins.inc"; attribute :>> needle="&context->startup_thunk"; attribute :>> obligation="Startup root remains a stable update slot"; }
part source37:SourceRow { attribute :>> key="root-hook"; attribute :>> path="vendor/gambit/lib/memory/root-origins.inc"; attribute :>> needle="___GC_ROOT_CONTROL(work);"; attribute :>> obligation="Default hook has no storage or code; not proof of generic carrier coverage"; }
part def IdentityRow { attribute key:String; attribute structure:String; attribute rule:String; attribute caveat:String; }
part identity0:IdentityRow { attribute :>> key="owner"; attribute :>> structure="VM SourceSlotId + owner generation"; attribute :>> rule="Register complete immutable descriptor and root before exposing source lookup"; attribute :>> caveat="Current context RC list is not such a descriptor"; }
part identity1:IdentityRow { attribute :>> key="writer"; attribute :>> structure="SourceId + WriteOperationId + candidate root"; attribute :>> rule="Accepted writer survives close; keyed completion cannot target next operation"; attribute :>> caveat="Unbounded abstract IDs do not prove finite native overflow"; }
part identity2:IdentityRow { attribute :>> key="payload"; attribute :>> structure="Semantic payload generation"; attribute :>> rule="Frozen for source pins; old target carries independent prior generation"; attribute :>> caveat="GC relocation does not increment this semantic generation"; }
part identity3:IdentityRow { attribute :>> key="round"; attribute :>> structure="CollectorRoundId + root descriptor generation + scan owner"; attribute :>> rule="Refresh round receipt after GC; do not equate with payload generation"; attribute :>> caveat="Task completion is not by itself source admission"; }
part identity4:IdentityRow { attribute :>> key="target"; attribute :>> structure="CarrierId + bound payload generation"; attribute :>> rule="Old carrier remains rooted if new source payload is installed"; attribute :>> caveat="Backing storage and module/context grace still require owners"; }
part def IssuerRow { attribute key:String; attribute proposedIssuer:String; attribute actualSource:String; attribute status:String; attribute responsibility:String; }
part issuer0:IssuerRow { attribute :>> key="registration"; attribute :>> proposedIssuer="VM SourceRegistry owner"; attribute :>> actualSource="setup_rc/register_rc set context list links; exported through GSTATE"; attribute :>> status="No complete stable SourceOwner registration identified"; attribute :>> responsibility="Reserve descriptor, root and generation then publish lookup"; }
part issuer1:IssuerRow { attribute :>> key="writer"; attribute :>> proposedIssuer="Managed payload setter owner"; attribute :>> actualSource="Only direct semantic setter sites found in Tcl and C closure; public setter escapes"; attribute :>> status="All indirect/out-of-tree writers unclosed"; attribute :>> responsibility="Root candidate; serialize source pins; retain accepted/unknown write on close"; }
part issuer2:IssuerRow { attribute :>> key="round"; attribute :>> proposedIssuer="Collector root-origin publisher and final grace owner"; attribute :>> actualSource="epoch increment, origin publish, claim, finish and thaw found"; attribute :>> status="Partial real round signers; carrier/source registration gap remains"; attribute :>> responsibility="Bind descriptor/epoch; renew after round transition"; }
part issuer3:IssuerRow { attribute :>> key="pin"; attribute :>> proposedIssuer="Stable source adapter and per-source admission owner"; attribute :>> actualSource="Current raw data/refcount APIs do not validate stable owner identity"; attribute :>> status="Native pin issuer absent"; attribute :>> responsibility="Check published source, generation and writer state without allocation"; }
part issuer4:IssuerRow { attribute :>> key="reservation"; attribute :>> proposedIssuer="Stable host guard commit owner"; attribute :>> actualSource="Prior rooted helper and guard designs only"; attribute :>> status="Exact native lookup and outcomes unimplemented"; attribute :>> responsibility="Unknown record retains source pin and target"; }
part issuer5:IssuerRow { attribute :>> key="cleanup"; attribute :>> proposedIssuer="Registry close plus storage/scanner owners"; attribute :>> actualSource="Known resize failure/shrink cleanup and retained-source checks found"; attribute :>> status="Whole SourceRegistry closed manifest not implemented"; attribute :>> responsibility="Drain accepted writes/pins, root scans and storage; then bulk cleanup"; }
part def ClaimRow { attribute key:String; attribute mechanism:String; attribute condition:String; attribute result:String; attribute gap:String; }
part claim0:ClaimRow { attribute :>> key="census"; attribute :>> mechanism="Enumerate active and closing descriptors every round"; attribute :>> condition="Authoritative registry complete; membership frozen before claim"; attribute :>> result="No retained root omitted by processor shrink"; attribute :>> gap="Native registration/alias closure open"; }
part claim1:ClaimRow { attribute :>> key="revocation"; attribute :>> mechanism="Close borrowing without removing scan membership"; attribute :>> condition="Drain current scans, payload users and receipt readers"; attribute :>> result="Closing carrier remains rooted across later rounds"; attribute :>> gap="Reclamation implementation and unknown-result resolver open"; }
part claim2:ClaimRow { attribute :>> key="old-payload"; attribute :>> mechanism="Carrier binds source semantic generation at initialization"; attribute :>> condition="Source pin covers initialization; collector updates exact slot"; attribute :>> result="Later setter changes source only"; attribute :>> gap="Still arena and foreign destructor ownership separate"; }
part claim3:ClaimRow { attribute :>> key="unknown"; attribute :>> mechanism="Committed registration with lost reply retains source pin"; attribute :>> condition="Query same identity and generation; never infer failure from timeout"; attribute :>> result="No root gap before exact result"; attribute :>> gap="Resolver liveness not proved"; }
part claim4:ClaimRow { attribute :>> key="cleanup"; attribute :>> mechanism="Separate root receipt from storage receipt"; attribute :>> condition="Known target registration plus backing owner; no active source pin"; attribute :>> result="Source header can retire without invalidating target binding"; attribute :>> gap="Actual cleanup caller integration unimplemented"; }
part claim5:ClaimRow { attribute :>> key="arbitrary-registry"; attribute :>> mechanism="List filter completeness and revoke preservation"; attribute :>> condition="Native roots correspond bijectively to authoritative descriptor registry"; attribute :>> result="Arbitrary finite list census lemma"; attribute :>> gap="Not arbitrary native trace or unbounded concurrent product proof"; }
part def MemoryRow { attribute key:String; attribute publication:String; attribute observation:String; attribute obligation:String; attribute overhead:String; }
part memory0:MemoryRow { attribute :>> key="register"; attribute :>> publication="Initialize private slot and descriptor then release publish"; attribute :>> observation="Acquire frozen census before dereference"; attribute :>> obligation="No GC gap: source pin until target membership known"; attribute :>> overhead="Descriptor, root slot and generation"; }
part memory1:MemoryRow { attribute :>> key="scan"; attribute :>> publication="Freeze membership and root mutation under collector protocol"; attribute :>> observation="Claim exact descriptor generation and round"; attribute :>> obligation="mark_array writes moving slot; release completion only after last use"; attribute :>> overhead="Per-round update plus task claim"; }
part memory2:MemoryRow { attribute :>> key="close"; attribute :>> publication="Atomic admission transition active to closing"; attribute :>> observation="Acquire validation prevents accepted late borrow"; attribute :>> obligation="Accepted before close drains; closing remains in census"; attribute :>> overhead="Lifecycle state and counters"; }
part memory3:MemoryRow { attribute :>> key="retire"; attribute :>> publication="Registry unlink only after scans, users and observers drain"; attribute :>> observation="Acquire all last-use decrements and completed round cut"; attribute :>> obligation="No count-to-zero check separate from close; prevent ABA reuse"; attribute :>> overhead="Grace period and identity tombstone"; }
part memory4:MemoryRow { attribute :>> key="payload"; attribute :>> publication="Setter serialized with source pins and GC freeze"; attribute :>> observation="Consumer reloads registered slot after GC"; attribute :>> obligation="Atomic metadata does not make arbitrary SCMOBJ mutation safe"; attribute :>> overhead="Rooted candidate and source write authority"; }
part memory5:MemoryRow { attribute :>> key="unknown"; attribute :>> publication="Keep descriptor and backing owner in durable live registry"; attribute :>> observation="Exact keyed resolver observes commit or safe abort"; attribute :>> obligation="Timeout is not evidence of nonpublication"; attribute :>> overhead="Retained memory may be unbounded without resolution"; }
part def GainRow { attribute key:String; attribute avoided:String; attribute added:String; attribute condition:String; }
part gain0:GainRow { attribute :>> key="processor-retirement"; attribute :>> avoided="No need to keep an entire processor alive solely for carrier roots"; attribute :>> added="Independent VM carrier descriptors and census"; attribute :>> condition="Only after backing storage and all nonroot dependencies transferred"; }
part gain1:GainRow { attribute :>> key="repeated-handoff"; attribute :>> avoided="One persistent registration rather than per-GC deregister/reregister"; attribute :>> added="One scan per live slot per round remains"; attribute :>> condition="Lifetime spans multiple rounds; native fidelity required"; }
part gain2:GainRow { attribute :>> key="classified-scan"; attribute :>> avoided="N_RC minus N_payload slot visits per round"; attribute :>> added="Classification and descriptor indexing"; attribute :>> condition="All unknown/native ABI users retain conservative fallback; duplicates deduplicated"; }
part gain3:GainRow { attribute :>> key="revocation"; attribute :>> avoided="No global shutdown guess or repeated rediscovery of alias ownership"; attribute :>> added="Close/drain/observer bookkeeping and retained unknowns"; attribute :>> condition="Authoritative writer and borrower closure"; }
part gain4:GainRow { attribute :>> key="modern-c"; attribute :>> avoided="Common generated root/scan/lifetime contract usable in C23"; attribute :>> added="GC protocol, metadata and proof maintenance remain"; attribute :>> condition="No Zig dependency required for these semantic benefits"; }
part gain5:GainRow { attribute :>> key="zig"; attribute :>> avoided="Potential safer local storage and typed ABI generation"; attribute :>> added="Second compiler/runtime ownership model and FFI integration"; attribute :>> condition="No demonstrated elimination of necessary root protocol; net advantage unresolved"; }
part def ContractRow { attribute fromNode:String; attribute toNode:String; attribute custody:String; }
part contract0:ContractRow { attribute :>> fromNode="SourceOwner"; attribute :>> toNode="SourcePin"; attribute :>> custody="Freeze source semantic generation"; }
part contract1:ContractRow { attribute :>> fromNode="SourcePin"; attribute :>> toNode="PrivateCarrier"; attribute :>> custody="Initialize under source root"; }
part contract2:ContractRow { attribute :>> fromNode="PrivateCarrier"; attribute :>> toNode="VMRegistry"; attribute :>> custody="Publish stable descriptor and writable slot"; }
part contract3:ContractRow { attribute :>> fromNode="VMRegistry"; attribute :>> toNode="PublicationReceipt"; attribute :>> custody="Exact keyed result or retain pin"; }
part contract4:ContractRow { attribute :>> fromNode="PublicationReceipt"; attribute :>> toNode="SourcePinRelease"; attribute :>> custody="Known registration only"; }
part contract5:ContractRow { attribute :>> fromNode="VMRegistry"; attribute :>> toNode="FrozenCensus"; attribute :>> custody="Enumerate active and closing entries every round"; }
part contract6:ContractRow { attribute :>> fromNode="FrozenCensus"; attribute :>> toNode="ScanClaim"; attribute :>> custody="Pin descriptor and claim round task"; }
part contract7:ContractRow { attribute :>> fromNode="ScanClaim"; attribute :>> toNode="UpdatedRoot"; attribute :>> custody="Forwarding updates registered slot"; }
part contract8:ContractRow { attribute :>> fromNode="UpdatedRoot"; attribute :>> toNode="ScanGrace"; attribute :>> custody="Finish after last slot use; unknown stays owned"; }
part contract9:ContractRow { attribute :>> fromNode="CloseAdmission"; attribute :>> toNode="FrozenCensus"; attribute :>> custody="Retain closing roots"; }
part contract10:ContractRow { attribute :>> fromNode="CloseAdmission"; attribute :>> toNode="UserDrain"; attribute :>> custody="Drain accepted users"; }
part contract11:ContractRow { attribute :>> fromNode="ScanGrace"; attribute :>> toNode="RetirementPermit"; attribute :>> custody="No scanner retains descriptor"; }
part contract12:ContractRow { attribute :>> fromNode="UserDrain"; attribute :>> toNode="RetirementPermit"; attribute :>> custody="No payload or receipt observer"; }
part contract13:ContractRow { attribute :>> fromNode="RetirementPermit"; attribute :>> toNode="DescriptorFree"; attribute :>> custody="Unlink and reclaim; prevent ABA"; }
part contract14:ContractRow { attribute :>> fromNode="PublicationReceipt"; attribute :>> toNode="SourceCleanupPermit"; attribute :>> custody="Known replacement root"; }
part contract15:ContractRow { attribute :>> fromNode="BackingStorageReceipt"; attribute :>> toNode="SourceCleanupPermit"; attribute :>> custody="Still arena and destructor custody"; }
part contract16:ContractRow { attribute :>> fromNode="SourcePinRelease"; attribute :>> toNode="SourceCleanupPermit"; attribute :>> custody="No source-local pin"; }
part contract17:ContractRow { attribute :>> fromNode="SourceCleanupPermit"; attribute :>> toNode="CleanupRC"; attribute :>> custody="Free source headers only"; }
part contract18:ContractRow { attribute :>> fromNode="RawInterference"; attribute :>> toNode="Quarantine"; attribute :>> custody="Deny optimized admission; retain custody"; }
part def BindingRow { attribute actionName:String; attribute lemma:String; attribute scope:String; }
part binding0:BindingRow { attribute :>> actionName="persistent_carrier_coverage.admitManagedWriters"; attribute :>> lemma="CarrierCoverage.admitManagedWritersPreserves"; attribute :>> scope="restricted typed IR transition; native simulation open"; }
part binding1:BindingRow { attribute :>> actionName="persistent_carrier_coverage.reserveCarrier"; attribute :>> lemma="CarrierCoverage.reserveCarrierPreserves"; attribute :>> scope="restricted typed IR transition; native simulation open"; }
part binding2:BindingRow { attribute :>> actionName="persistent_carrier_coverage.initializeCarrier"; attribute :>> lemma="CarrierCoverage.initializeCarrierPreserves"; attribute :>> scope="restricted typed IR transition; native simulation open"; }
part binding3:BindingRow { attribute :>> actionName="persistent_carrier_coverage.publishCarrier"; attribute :>> lemma="CarrierCoverage.publishCarrierPreserves"; attribute :>> scope="restricted typed IR transition; native simulation open"; }
part binding4:BindingRow { attribute :>> actionName="persistent_carrier_coverage.queryPublication"; attribute :>> lemma="CarrierCoverage.queryPublicationPreserves"; attribute :>> scope="restricted typed IR transition; native simulation open"; }
part binding5:BindingRow { attribute :>> actionName="persistent_carrier_coverage.returnSourcePin"; attribute :>> lemma="CarrierCoverage.returnSourcePinPreserves"; attribute :>> scope="restricted typed IR transition; native simulation open"; }
part binding6:BindingRow { attribute :>> actionName="persistent_carrier_coverage.borrowPayload"; attribute :>> lemma="CarrierCoverage.borrowPayloadPreserves"; attribute :>> scope="restricted typed IR transition; native simulation open"; }
part binding7:BindingRow { attribute :>> actionName="persistent_carrier_coverage.returnPayload"; attribute :>> lemma="CarrierCoverage.returnPayloadPreserves"; attribute :>> scope="restricted typed IR transition; native simulation open"; }
part binding8:BindingRow { attribute :>> actionName="persistent_carrier_coverage.observeReceipt"; attribute :>> lemma="CarrierCoverage.observeReceiptPreserves"; attribute :>> scope="restricted typed IR transition; native simulation open"; }
part binding9:BindingRow { attribute :>> actionName="persistent_carrier_coverage.releaseObserver"; attribute :>> lemma="CarrierCoverage.releaseObserverPreserves"; attribute :>> scope="restricted typed IR transition; native simulation open"; }
part binding10:BindingRow { attribute :>> actionName="persistent_carrier_coverage.revokeCarrier"; attribute :>> lemma="CarrierCoverage.revokeCarrierPreserves"; attribute :>> scope="restricted typed IR transition; native simulation open"; }
part binding11:BindingRow { attribute :>> actionName="persistent_carrier_coverage.closeSource"; attribute :>> lemma="CarrierCoverage.closeSourcePreserves"; attribute :>> scope="restricted typed IR transition; native simulation open"; }
part binding12:BindingRow { attribute :>> actionName="persistent_carrier_coverage.managedSetter"; attribute :>> lemma="CarrierCoverage.managedSetterPreserves"; attribute :>> scope="restricted typed IR transition; native simulation open"; }
part binding13:BindingRow { attribute :>> actionName="persistent_carrier_coverage.recordRawInterference"; attribute :>> lemma="CarrierCoverage.recordRawInterferencePreserves"; attribute :>> scope="restricted typed IR transition; native simulation open"; }
part binding14:BindingRow { attribute :>> actionName="persistent_carrier_coverage.storageHandoff"; attribute :>> lemma="CarrierCoverage.storageHandoffPreserves"; attribute :>> scope="restricted typed IR transition; native simulation open"; }
part binding15:BindingRow { attribute :>> actionName="persistent_carrier_coverage.cleanupSource"; attribute :>> lemma="CarrierCoverage.cleanupSourcePreserves"; attribute :>> scope="restricted typed IR transition; native simulation open"; }
part binding16:BindingRow { attribute :>> actionName="persistent_carrier_coverage.retireCarrier"; attribute :>> lemma="CarrierCoverage.retireCarrierPreserves"; attribute :>> scope="restricted typed IR transition; native simulation open"; }
part binding17:BindingRow { attribute :>> actionName="persistent_carrier_coverage.shrinkProcessors"; attribute :>> lemma="CarrierCoverage.shrinkProcessorsPreserves"; attribute :>> scope="restricted typed IR transition; native simulation open"; }
part binding18:BindingRow { attribute :>> actionName="persistent_carrier_coverage.freezeBoth"; attribute :>> lemma="CarrierCoverage.freezeBothPreserves"; attribute :>> scope="restricted typed IR transition; native simulation open"; }
part binding19:BindingRow { attribute :>> actionName="persistent_carrier_coverage.freezeSource"; attribute :>> lemma="CarrierCoverage.freezeSourcePreserves"; attribute :>> scope="restricted typed IR transition; native simulation open"; }
part binding20:BindingRow { attribute :>> actionName="persistent_carrier_coverage.freezeCarrier"; attribute :>> lemma="CarrierCoverage.freezeCarrierPreserves"; attribute :>> scope="restricted typed IR transition; native simulation open"; }
part binding21:BindingRow { attribute :>> actionName="persistent_carrier_coverage.freezeNeither"; attribute :>> lemma="CarrierCoverage.freezeNeitherPreserves"; attribute :>> scope="restricted typed IR transition; native simulation open"; }
part binding22:BindingRow { attribute :>> actionName="persistent_carrier_coverage.claim0"; attribute :>> lemma="CarrierCoverage.claim0Preserves"; attribute :>> scope="restricted typed IR transition; native simulation open"; }
part binding23:BindingRow { attribute :>> actionName="persistent_carrier_coverage.scanDone0"; attribute :>> lemma="CarrierCoverage.scanDone0Preserves"; attribute :>> scope="restricted typed IR transition; native simulation open"; }
part binding24:BindingRow { attribute :>> actionName="persistent_carrier_coverage.scanUnknown0"; attribute :>> lemma="CarrierCoverage.scanUnknown0Preserves"; attribute :>> scope="restricted typed IR transition; native simulation open"; }
part binding25:BindingRow { attribute :>> actionName="persistent_carrier_coverage.resolveScan0"; attribute :>> lemma="CarrierCoverage.resolveScan0Preserves"; attribute :>> scope="restricted typed IR transition; native simulation open"; }
part binding26:BindingRow { attribute :>> actionName="persistent_carrier_coverage.claim1"; attribute :>> lemma="CarrierCoverage.claim1Preserves"; attribute :>> scope="restricted typed IR transition; native simulation open"; }
part binding27:BindingRow { attribute :>> actionName="persistent_carrier_coverage.scanDone1"; attribute :>> lemma="CarrierCoverage.scanDone1Preserves"; attribute :>> scope="restricted typed IR transition; native simulation open"; }
part binding28:BindingRow { attribute :>> actionName="persistent_carrier_coverage.scanUnknown1"; attribute :>> lemma="CarrierCoverage.scanUnknown1Preserves"; attribute :>> scope="restricted typed IR transition; native simulation open"; }
part binding29:BindingRow { attribute :>> actionName="persistent_carrier_coverage.resolveScan1"; attribute :>> lemma="CarrierCoverage.resolveScan1Preserves"; attribute :>> scope="restricted typed IR transition; native simulation open"; }
part binding30:BindingRow { attribute :>> actionName="persistent_carrier_coverage.finishRound"; attribute :>> lemma="CarrierCoverage.finishRoundPreserves"; attribute :>> scope="restricted typed IR transition; native simulation open"; }
part def ProofRow { attribute key:String; attribute lemma:String; }
part proof0:ProofRow { attribute :>> key="stepPreserves"; attribute :>> lemma="CarrierCoverage.stepPreserves"; }
part proof1:ProofRow { attribute :>> key="reachableSafe"; attribute :>> lemma="CarrierCoverage.reachableSafe"; }
part proof2:ProofRow { attribute :>> key="activeCarrierEnumerated"; attribute :>> lemma="CarrierCoverage.activeCarrierEnumerated"; }
part proof3:ProofRow { attribute :>> key="closingCarrierRetained"; attribute :>> lemma="CarrierCoverage.closingCarrierRetained"; }
part proof4:ProofRow { attribute :>> key="readerRetainsDescriptor"; attribute :>> lemma="CarrierCoverage.readerRetainsDescriptor"; }
part proof5:ProofRow { attribute :>> key="unknownScanBlocksFinish"; attribute :>> lemma="CarrierCoverage.unknownScanBlocksFinish"; }
part proof6:ProofRow { attribute :>> key="observerBlocksRetirement"; attribute :>> lemma="CarrierCoverage.observerBlocksRetirement"; }
part proof7:ProofRow { attribute :>> key="interferenceBlocksAdmission"; attribute :>> lemma="CarrierCoverage.interferenceBlocksAdmission"; }
part proof8:ProofRow { attribute :>> key="setterPreservesOldBinding"; attribute :>> lemma="CarrierCoverage.setterPreservesOldBinding"; }
part proof9:ProofRow { attribute :>> key="shrinkPreservesRegistration"; attribute :>> lemma="CarrierCoverage.shrinkPreservesRegistration"; }
part proof10:ProofRow { attribute :>> key="unknownPublicationRetainsSource"; attribute :>> lemma="CarrierCoverage.unknownPublicationRetainsSource"; }
part proof11:ProofRow { attribute :>> key="complete"; attribute :>> lemma="PersistentCensus.complete"; }
part proof12:ProofRow { attribute :>> key="sound"; attribute :>> lemma="PersistentCensus.sound"; }
part proof13:ProofRow { attribute :>> key="closingIncluded"; attribute :>> lemma="PersistentCensus.closingIncluded"; }
part proof14:ProofRow { attribute :>> key="revokePreservesIds"; attribute :>> lemma="PersistentCensus.revokePreservesIds"; }
part proof15:ProofRow { attribute :>> key="parentQualificationBoundary"; attribute :>> lemma="CarrierCoverageBridge.parentQualificationBoundary"; }
part proof16:ProofRow { attribute :>> key="registeredClosingEnumerated"; attribute :>> lemma="CarrierCoverageBridge.registeredClosingEnumerated"; }
part proof17:ProofRow { attribute :>> key="cleanupRequiresBacking"; attribute :>> lemma="CarrierCoverageBridge.cleanupRequiresBacking"; }
part proof18:ProofRow { attribute :>> key="retirementRequiresIdle"; attribute :>> lemma="CarrierCoverageBridge.retirementRequiresIdle"; }
part def RouteRow { attribute component:String; attribute actionName:String; attribute lemma:String; attribute producerAnchor:String; attribute obligationId:String; }
part route0:RouteRow { attribute :>> component="registry"; attribute :>> actionName="persistent_carrier_coverage.publishCarrier"; attribute :>> lemma="CarrierCoverage.publishCarrierPreserves"; attribute :>> producerAnchor="rc-register"; attribute :>> obligationId="PC-source"; }
part route1:RouteRow { attribute :>> component="registry"; attribute :>> actionName="persistent_carrier_coverage.queryPublication"; attribute :>> lemma="CarrierCoverage.queryPublicationPreserves"; attribute :>> producerAnchor="register-export"; attribute :>> obligationId="PC-source"; }
part route2:RouteRow { attribute :>> component="roots"; attribute :>> actionName="persistent_carrier_coverage.freezeBoth"; attribute :>> lemma="CarrierCoverage.freezeBothPreserves"; attribute :>> producerAnchor="origin-publish"; attribute :>> obligationId="PC-roots"; }
part route3:RouteRow { attribute :>> component="roots"; attribute :>> actionName="persistent_carrier_coverage.freezeCarrier"; attribute :>> lemma="CarrierCoverage.freezeCarrierPreserves"; attribute :>> producerAnchor="vm-request-slots"; attribute :>> obligationId="PC-roots"; }
part route4:RouteRow { attribute :>> component="roots"; attribute :>> actionName="persistent_carrier_coverage.scanDone1"; attribute :>> lemma="CarrierCoverage.scanDone1Preserves"; attribute :>> producerAnchor="origin-finish"; attribute :>> obligationId="PC-roots"; }
part route5:RouteRow { attribute :>> component="roots"; attribute :>> actionName="persistent_carrier_coverage.resolveScan1"; attribute :>> lemma="CarrierCoverage.resolveScan1Preserves"; attribute :>> producerAnchor="view-drain"; attribute :>> obligationId="PC-roots"; }
part route6:RouteRow { attribute :>> component="writer"; attribute :>> actionName="persistent_carrier_coverage.managedSetter"; attribute :>> lemma="CarrierCoverage.managedSetterPreserves"; attribute :>> producerAnchor="rc-write"; attribute :>> obligationId="PC-writers"; }
part route7:RouteRow { attribute :>> component="writer"; attribute :>> actionName="persistent_carrier_coverage.recordRawInterference"; attribute :>> lemma="CarrierCoverage.recordRawInterferencePreserves"; attribute :>> producerAnchor="setter-export"; attribute :>> obligationId="PC-writers"; }
part route8:RouteRow { attribute :>> component="guard"; attribute :>> actionName="persistent_carrier_coverage.borrowPayload"; attribute :>> lemma="CarrierCoverage.borrowPayloadPreserves"; attribute :>> producerAnchor="tcl-call"; attribute :>> obligationId="PC-execution"; }
part route9:RouteRow { attribute :>> component="guard"; attribute :>> actionName="persistent_carrier_coverage.retireCarrier"; attribute :>> lemma="CarrierCoverage.retireCarrierPreserves"; attribute :>> producerAnchor="tcl-delete-native"; attribute :>> obligationId="PC-execution"; }
part route10:RouteRow { attribute :>> component="storage"; attribute :>> actionName="persistent_carrier_coverage.storageHandoff"; attribute :>> lemma="CarrierCoverage.storageHandoffPreserves"; attribute :>> producerAnchor="shrink-cleanup"; attribute :>> obligationId="PC-storage"; }
part route11:RouteRow { attribute :>> component="storage"; attribute :>> actionName="persistent_carrier_coverage.cleanupSource"; attribute :>> lemma="CarrierCoverage.cleanupSourcePreserves"; attribute :>> producerAnchor="rc-cleanup"; attribute :>> obligationId="PC-storage"; }
part def Need { attribute obligationId:String; attribute kind:String; attribute subjectPath:String; attribute subjectScope:String; ref owner:Owner; }
part formalNeed:Need { attribute :>> obligationId="PC-formal"; attribute :>> kind="induction"; attribute :>> subjectPath="dev/refactoring/modern-c/models/lean/CarrierCoverage.lean"; attribute :>> subjectScope="two descriptors; multi-round membership and scan/observer safety"; ref :>> owner=guardOwner; }
part bridgeNeed:Need { attribute :>> obligationId="PC-bridge"; attribute :>> kind="composition"; attribute :>> subjectPath="dev/refactoring/modern-c/models/lean/CarrierCoverageBridge.lean"; attribute :>> subjectScope="parent precondition and generic finite registry census; native fidelity open"; ref :>> owner=guardOwner; }
part sourceNeed:Need { attribute :>> obligationId="PC-source"; attribute :>> kind="source"; attribute :>> subjectPath="vendor/gambit/lib/memory/rc-allocation.inc"; attribute :>> subjectScope="complete persistent registration and identity census"; ref :>> owner=registryOwner; }
part executionNeed:Need { attribute :>> obligationId="PC-execution"; attribute :>> kind="source"; attribute :>> subjectPath="vendor/gambit/lib/c_intf.c"; attribute :>> subjectScope="real carrier result resolver and last-use observer drain"; ref :>> owner=guardOwner; }
part rootsNeed:Need { attribute :>> obligationId="PC-roots"; attribute :>> kind="source"; attribute :>> subjectPath="vendor/gambit/lib/memory/root-origins.inc"; attribute :>> subjectScope="all carrier slots every collector round; complete native mapping"; ref :>> owner=rootsOwner; }
part writersNeed:Need { attribute :>> obligationId="PC-writers"; attribute :>> kind="source"; attribute :>> subjectPath="vendor/gambit/lib/setup.c"; attribute :>> subjectScope="public direct indirect setters and out-of-tree authority closure"; ref :>> owner=writerOwner; }
part platformNeed:Need { attribute :>> obligationId="PC-platform"; attribute :>> kind="platform"; attribute :>> subjectPath="dev/refactoring/modern-c/language-baseline-design.org"; attribute :>> subjectScope="C23 atomics lock-free requirements Darwin ABI and generated header provenance"; ref :>> owner=guardOwner; }
part storageNeed:Need { attribute :>> obligationId="PC-storage"; attribute :>> kind="source"; attribute :>> subjectPath="vendor/gambit/lib/memory/memory-lifecycle.inc"; attribute :>> subjectScope="old still arena/destructor handoff before processor cleanup"; ref :>> owner=storageOwner; }
part proof19:ProofRow { attribute :>> key="privateInitializationBlocksFreeze"; attribute :>> lemma="CarrierCoverageBridge.privateInitializationBlocksFreeze"; }
part def CostRow { attribute key:String; attribute avoided:String; attribute added:String; attribute positiveCondition:String; attribute boundary:String; }
part cost0:CostRow { attribute :>> key="persistent-handoff"; attribute :>> avoided="C*(K-1)*H"; attribute :>> added="C*P + K*C*E + R"; attribute :>> positiveCondition="avoided > added"; attribute :>> boundary="H is not shown to be paid each round in current source; required slot updates remain"; }
part cost1:CostRow { attribute :>> key="classified-roots"; attribute :>> avoided="K*(N_RC-N_payload)*visit_cost"; attribute :>> added="classification + index + grace + unknown_retention"; attribute :>> positiveCondition="avoided > added"; attribute :>> boundary="Unknown native clients retain conservative roots; duplicate new and old scans can make savings zero"; }
part cost2:CostRow { attribute :>> key="processor-release"; attribute :>> avoided="Retained processor-only bytes and lifecycle coupling"; attribute :>> added="Descriptors + target backing + grace retention"; attribute :>> positiveCondition="All other context/arena users independently settled"; attribute :>> boundary="No measured byte estimate; source can_retire rejects RC without a freeze receipt"; }
part cost3:CostRow { attribute :>> key="zig-increment"; attribute :>> avoided="Concrete support actually retired relative to mandatory modern C"; attribute :>> added="Additional compiler + interop + duplicate ownership support"; attribute :>> positiveCondition="Retired support exceeds new support while preserving contracts"; attribute :>> boundary="No positive language-specific net benefit established"; }
}
