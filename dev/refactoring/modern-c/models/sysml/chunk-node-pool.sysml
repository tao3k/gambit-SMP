package GambitChunkNodePool { private import ScalarValues::*;
part def SourceRow { attribute key:String; attribute path:String; attribute needle:String; attribute obligation:String; }
part source0:SourceRow { attribute :>> key="chunk-start"; attribute :>> path="vendor/gambit/lib/mem.c"; attribute :>> needle="alloc_heap_chunk_limit = work->context->mem.alloc_heap_ptr_ + ___MSECTION_CHUNK;"; attribute :>> obligation="Threshold is a rollover trigger, not a minimum size for every closed chunk"; }
part source1:SourceRow { attribute :>> key="empty-close"; attribute :>> path="vendor/gambit/lib/mem.c"; attribute :>> needle="*work->context->mem.alloc_heap_ptr_++ = NULL_CHUNK_LINK;"; attribute :>> obligation="Even empty closure consumes a terminal word; prove non-reuse across manifest intervals"; }
part source2:SourceRow { attribute :>> key="node-alias"; attribute :>> path="vendor/gambit/lib/mem.c"; attribute :>> needle="___WORD *new_tail = alloc_heap_chunk_start-1;"; attribute :>> obligation="Replace old link address, not merely wrap enqueue"; }
part source3:SourceRow { attribute :>> key="section-slack"; attribute :>> path="vendor/gambit/lib/mem.c"; attribute :>> needle="work->context->mem.alloc_heap_limit_ -= 2;"; attribute :>> obligation="Two terminal markers; charge partial and empty sections separately"; }
part source4:SourceRow { attribute :>> key="section-prefix"; attribute :>> path="vendor/gambit/lib/mem.c"; attribute :>> needle="*work->context->mem.alloc_heap_ptr_++ = NULL_CHUNK_LINK; /* link of msection's first chunk */"; attribute :>> obligation="First prefix is not a new copied object"; }
part source5:SourceRow { attribute :>> key="no-fit"; attribute :>> path="vendor/gambit/lib/mem.c"; attribute :>> needle="work->context->mem.alloc_heap_limit_-alloc < required"; attribute :>> obligation="Partial section rollover occurs before next reservation"; }
part source6:SourceRow { attribute :>> key="private-rollback"; attribute :>> path="vendor/gambit/lib/mem.c"; attribute :>> needle="alloc = cancel_copy(work,&grant);"; attribute :>> obligation="Only failed forwarding CAS private reservation may roll back; no terminal/node duplication"; }
part source7:SourceRow { attribute :>> key="forwarding"; attribute :>> path="vendor/gambit/lib/mem.c"; attribute :>> needle="___COMPARE_AND_SWAP_WORD(&body[-1],"; attribute :>> obligation="Node capacity must precede winning forwarding; failure cannot abandon initialization"; }
part source8:SourceRow { attribute :>> key="custom-sections"; attribute :>> path="vendor/gambit/lib/mem.c"; attribute :>> needle="return custom_msection_alloc ();"; attribute :>> obligation="Reject uncertified address reuse or extension without atomic storage-plus-node budget admission"; }
part source9:SourceRow { attribute :>> key="shared-section"; attribute :>> path="vendor/gambit/lib/mem.c"; attribute :>> needle="result = ms;"; attribute :>> obligation="Distinct section identity alone does not establish disjoint heap lease intervals"; }
part source10:SourceRow { attribute :>> key="dequeue-head"; attribute :>> path="vendor/gambit/lib/mem.c"; attribute :>> needle="owner->heap_chunks_to_scan_head_ = node;"; attribute :>> obligation="Empty queue can retain last consumed address"; }
part source11:SourceRow { attribute :>> key="local-owned"; attribute :>> path="vendor/gambit/lib/mem.c"; attribute :>> needle="work->local_scan_chunk_ = ptr;"; attribute :>> obligation="Local frontier owns a private chunk; no extra admission on eventual publication"; }
part source12:SourceRow { attribute :>> key="weak-copy"; attribute :>> path="vendor/gambit/lib/mem.c"; attribute :>> needle="process_wills (work);"; attribute :>> obligation="Weak producers can add copies; strong-only budget is insufficient"; }
part source13:SourceRow { attribute :>> key="weak-end"; attribute :>> path="vendor/gambit/lib/mem.c"; attribute :>> needle="move_continuation (work);"; attribute :>> obligation="Final worker context restoration remains a future user until separately qualified"; }
part source14:SourceRow { attribute :>> key="cleanup-hash"; attribute :>> path="vendor/gambit/lib/mem.c"; attribute :>> needle="process_gc_hash_tables (work);"; attribute :>> obligation="Cleanup frontier not equivalent to weak scan completion"; }
part source15:SourceRow { attribute :>> key="cleanup-foreign"; attribute :>> path="vendor/gambit/lib/mem.c"; attribute :>> needle="___release_foreign"; attribute :>> obligation="Native callback potential must be closed or routed into next epoch"; }
part source16:SourceRow { attribute :>> key="destructor-call"; attribute :>> path="vendor/gambit/lib/c_intf.c"; attribute :>> needle="if ((e = release_fn (ptr)) != ___FIX(___NO_ERR))"; attribute :>> obligation="Unrestricted foreign destructor is not automatically a no-reentry user"; }
part source17:SourceRow { attribute :>> key="chunk-size"; attribute :>> path="vendor/gambit/lib/mem.h"; attribute :>> needle="#define ___MSECTION_CHUNK       ___MSECTION_BIGGEST"; attribute :>> obligation="Selected source threshold K=255; not proof of current compiled profile"; }
part source18:SourceRow { attribute :>> key="section-size"; attribute :>> path="vendor/gambit/lib/mem.h"; attribute :>> needle="#define ___MSECTION_SIZE        131072"; attribute :>> obligation="Illustrative half section 65536 words; actual lease manifest separately checked"; }
part source19:SourceRow { attribute :>> key="legacy-cas"; attribute :>> path="vendor/gambit/include/gambit.h.in"; attribute :>> needle="__sync_val_compare_and_swap(p,oldval,newval)"; attribute :>> obligation="Native adapter is not itself portable C11 proof"; }
part def CapacityRow { attribute key:String; attribute bound:String; attribute premise:String; attribute counterexample:String; attribute status:String; }
part capacity0:CapacityRow { attribute :>> key="physical-ceiling"; attribute :>> bound="Bdata <= W + P; Btotal = Bdata + D"; attribute :>> premise="Distinct terminal addresses in disjoint fixed epoch intervals W; at most P open chunks; D independent dummy nodes"; attribute :>> counterexample="Custom allocator repeats an interval or phase resets rewind its cursor"; attribute :>> status="conditional arithmetic proved; source injection open"; }
part capacity1:CapacityRow { attribute :>> key="charged-ceiling"; attribute :>> bound="255*Bdata <= A + 255*(V+P)"; attribute :>> premise="All threshold closures charged to disjoint 255-word spans; at most V partial section closes; private cancellation does not rewind committed spans"; attribute :>> counterexample="Count copied payload only; omit empty close or repeated lease visit"; attribute :>> status="conditional arithmetic proved; complete charge classification open"; }
part capacity2:CapacityRow { attribute :>> key="epoch-admission"; attribute :>> bound="capacity >= certified total demand including strong weak and restore users"; attribute :>> premise="Reserve all pool pages and check size arithmetic before flipping or forwarding; no GC-recursive fallback"; attribute :>> counterexample="Pool native allocation fails after forwarding is visible"; attribute :>> status="design; native preflight issuer absent"; }
part capacity3:CapacityRow { attribute :>> key="dense-fallback-cost"; attribute :>> bound="Selected 3-pointer fields: >=24*(W+P+D) bytes when Psizeof=8"; attribute :>> premise="Capacity is logical records, not just occupied/live records; allocator and pin bytes additional"; attribute :>> counterexample="Treat loose ceiling as a cheap production pool"; attribute :>> status="mathematical bound can be too costly; not accepted as performance design"; }
part capacity4:CapacityRow { attribute :>> key="tighter-example"; attribute :>> bound="A=65536 V=1 P=1 D=1 => Btotal<=260; fields>=6240 bytes"; attribute :>> premise="Illustrative certified one-lease geometry; physical case not measured; A includes allocation spans"; attribute :>> counterexample="Claim every real section produces exactly 260 nodes"; attribute :>> status="arithmetic example only"; }
part def ProgressRow { attribute key:String; attribute mechanism:String; attribute condition:String; attribute gap:String; }
part progress0:ProgressRow { attribute :>> key="no-node-wait"; attribute :>> mechanism="Every remaining certified demand has a free node since issued<budget<=capacity"; attribute :>> condition="Admission covers whole epoch; nodes retained, never depend on mid-epoch recycle"; attribute :>> gap="Formal space theorem; source demand permit injection remains open"; }
part progress1:ProgressRow { attribute :>> key="undersized-pool"; attribute :>> mechanism="Reject before admission or choose separately qualified plan before forwarding"; attribute :>> condition="Existing committed work keeps custody after any contract breach"; attribute :>> gap="Helping scan cannot free retained nodes; no post-forward rollback guarantee"; }
part progress2:ProgressRow { attribute :>> key="finite-drain"; attribute :>> mechanism="Rank=4*private+3*sealed+2*queued+owned decreases on each drain step"; attribute :>> condition="No new tasks; sealed payload ready; fair scheduling and terminating scan callbacks"; attribute :>> gap="Enabledness and rank proved; not fairness, wait-freedom, or full GC termination"; }
part progress3:ProgressRow { attribute :>> key="unknown-outcome"; attribute :>> mechanism="Same node and accepted task survive lost ack; observe receipt without reenqueuing"; attribute :>> condition="Stable epoch identity and protected custody slot; retries use identity"; attribute :>> gap="Aggregate model does not prove per-task replay deduplication"; }
part progress4:ProgressRow { attribute :>> key="late-child"; attribute :>> mechanism="Parent reserves child budget and node before final settlement, even after root close"; attribute :>> condition="Child remains within certified physical geometry; no implicit Scheme allocation"; attribute :>> gap="Children modeled as node tasks; non-node Tail/initialization debt imported separately"; }
part def ReceiptRow { attribute key:String; attribute issuer:String; attribute prerequisite:String; attribute revocation:String; attribute gap:String; }
part receipt0:ReceiptRow { attribute :>> key="pool-plan"; attribute :>> issuer="VM epoch coordinator plus storage manifest owner"; attribute :>> prerequisite="Disjoint leases; K/ABI; checked size; pool memory; all stage producers; stable roster"; attribute :>> revocation="Any resize extension allocator/profile change requires joint new admission before use"; attribute :>> gap="No current native issuer"; }
part receipt1:ReceiptRow { attribute :>> key="work-complete"; attribute :>> issuer="Global work ledger coordinator"; attribute :>> prerequisite="All roots/producers closed; delayed copies/Tail/owned/private tasks settled"; attribute :>> revocation="Late accepted work prevents signature or belongs to distinct later epoch"; attribute :>> gap="Model aggregate slice proved; all native producers open"; }
part receipt2:ReceiptRow { attribute :>> key="users-closed"; attribute :>> issuer="Epoch admission owner plus every queue/source reader"; attribute :>> prerequisite="Stop new borrowers and publishers; drain admitted users; cleanup callbacks rerouted or proven non-reentrant"; attribute :>> revocation="Late closure attempt fails rather than clearing debts"; attribute :>> gap="C gate linearization and callback closure open"; }
part receipt3:ReceiptRow { attribute :>> key="reclaim-permit"; attribute :>> issuer="Pool lifecycle coordinator under closure serialization"; attribute :>> prerequisite="Work complete + users closed + heads detached + all receipts/borrowers gone + generation match"; attribute :>> revocation="Single-use permit consumed once; never reopen same generation"; attribute :>> gap="Model safety proved; native generation and permit issuer open"; }
part def MemoryRow { attribute key:String; attribute ordering:String; attribute obligation:String; attribute gap:String; }
part memory0:MemoryRow { attribute :>> key="reserve"; attribute :>> ordering="Owner-local cursor or native pool gate acquire/release"; attribute :>> obligation="Reserve node and task responsibility before winning forwarding CAS; no failure in commit segment"; attribute :>> gap="Global lock fairness and owner interruption open"; }
part memory1:MemoryRow { attribute :>> key="publish"; attribute :>> ordering="Initialize immutable bounds and payload before release unlock; acquire before reading queue"; attribute :>> obligation="All next/head/tail accesses use same gate; scanner holds independent lifetime pin outside gate"; attribute :>> gap="Exact effective Darwin adapter and payload readiness mapping open"; }
part memory2:MemoryRow { attribute :>> key="last-user"; attribute :>> ordering="Final borrower release or RMW sequenced after last dereference; reclaimer acquire"; attribute :>> obligation="Admission close and borrower registration serialized; count zero after gate closure; no hidden reader"; attribute :>> gap="Acquire zero without closed admission is invalid"; }
part memory3:MemoryRow { attribute :>> key="receipt"; attribute :>> ordering="Serialized immutable receipt publication release; consumer acquire and generation check"; attribute :>> obligation="Must observe every last decrement through selected gate/RMW release sequence; no relaxed-zero shortcut"; attribute :>> gap="No operational C11 weak-memory model or compiled witness"; }
part memory4:MemoryRow { attribute :>> key="overflow"; attribute :>> ordering="Checked native size multiplications and counts before admission"; attribute :>> obligation="No wrap in capacity budget debt pin generation; saturation retains custody/rejects"; attribute :>> gap="Mathematical integers do not prove machine arithmetic safety"; }
part def GainRow { attribute key:String; attribute avoided:String; attribute added:String; attribute condition:String; }
part gain0:GainRow { attribute :>> key="ordinary-C-scan"; attribute :>> avoided="No whole-header atomic conversion or mutable sentinel classifier race"; attribute :>> added="Independent record initialization and queue transfer"; attribute :>> condition="Full source replacement and payload publication qualified"; }
part gain1:GainRow { attribute :>> key="capacity"; attribute :>> avoided="No allocation failure or free-node wait after winning forwarding"; attribute :>> added="Reserve Btotal*recordStride + pool/pin bookkeeping before epoch"; attribute :>> condition="Valid complete capacity receipt and admitted memory budget"; }
part gain2:GainRow { attribute :>> key="publication"; attribute :>> avoided="No extra work acceptance or debt when sealing/publishing"; attribute :>> added="O(1) state transition per transfer; aggregate counts or worker-local batches"; attribute :>> condition="Same logical task identity; no second enqueue after unknown ack"; }
part gain3:GainRow { attribute :>> key="retention"; attribute :>> avoided="No per-node reuse ABA within epoch; no per-node free in scan loop"; attribute :>> added="Retain every issued record through global reclamation cut"; attribute :>> condition="No overlapping epoch reuse; late pin can delay reclamation indefinitely"; }
part gain4:GainRow { attribute :>> key="tight-budget"; attribute :>> avoided="For illustrative one half-section K255 geometry fields lower bound6240 bytes (~1.19% of 524288 payload-space bytes)"; attribute :>> added="Actual stride pool padding global roots and late-epoch retention not included"; attribute :>> condition="Conditional geometry; not measured residency or speedup"; }
part gain5:GainRow { attribute :>> key="loose-budget"; attribute :>> avoided="Can state finite upper bound independently of payload occupancy"; attribute :>> added="At least ~3 times tospace bytes for dense three-pointer records at one record per word"; attribute :>> condition="Useful as safety ceiling; too costly to justify production selection alone"; }
part gain6:GainRow { attribute :>> key="net-benefit"; attribute :>> avoided="Saved header-atomic tax and useful scan overlap"; attribute :>> added="Node/pool cost + admission/custody + retention; reduced heap may cause more GC"; attribute :>> condition="Positive only if saved work exceeds total new cost and memory budget fits"; }
part gain7:GainRow { attribute :>> key="retirement"; attribute :>> avoided="Old terminal-as-next and implicit queue-head lifetime can retire"; attribute :>> added="Migrate enqueue/dequeue/classifier local frontier epoch setup cleanup debug all together"; attribute :>> condition="No speed credit for already-existing queue gate; no runtime replacement yet"; }
part def ContractRow { attribute fromNode:String; attribute toNode:String; attribute custody:String; }
part contract0:ContractRow { attribute :>> fromNode="manifest"; attribute :>> toNode="preflight"; attribute :>> custody="Disjoint spans and bounded producers yield pool demand budget"; }
part contract1:ContractRow { attribute :>> fromNode="preflight"; attribute :>> toNode="pool"; attribute :>> custody="Allocate before flip/forward; reject undersized plan"; }
part contract2:ContractRow { attribute :>> fromNode="pool"; attribute :>> toNode="copy"; attribute :>> custody="Reserve node with work debt before forwarding"; }
part contract3:ContractRow { attribute :>> fromNode="copy"; attribute :>> toNode="sealed"; attribute :>> custody="Complete payload and frame links; retain Tail debt"; }
part contract4:ContractRow { attribute :>> fromNode="sealed"; attribute :>> toNode="queue"; attribute :>> custody="Publish moves same accepted debt under queue gate"; }
part contract5:ContractRow { attribute :>> fromNode="queue"; attribute :>> toNode="scanner"; attribute :>> custody="Claim node while retaining lifetime outside gate"; }
part contract6:ContractRow { attribute :>> fromNode="scanner"; attribute :>> toNode="work-complete"; attribute :>> custody="Settle scan debt after deriving all children"; }
part contract7:ContractRow { attribute :>> fromNode="work-complete"; attribute :>> toNode="users-closed"; attribute :>> custody="Drain future publishers callbacks and borrowers separately"; }
part contract8:ContractRow { attribute :>> fromNode="users-closed"; attribute :>> toNode="receipt"; attribute :>> custody="Detach dummy heads and retire receipts and pins"; }
part contract9:ContractRow { attribute :>> fromNode="receipt"; attribute :>> toNode="reclaim"; attribute :>> custody="Generation-bound permission; epoch reuse only after consumption"; }
part def ObligationRow { attribute key:String; attribute status:String; attribute scope:String; attribute gap:String; }
part obligation0:ObligationRow { attribute :>> key="induction"; attribute :>> status="proved"; attribute :>> scope="Actual pool typed AST all-step and reachable safety"; attribute :>> gap="Abstract integers and atomic steps"; }
part obligation1:ObligationRow { attribute :>> key="capacity"; attribute :>> status="conditional-proved"; attribute :>> scope="Physical and threshold arithmetic plus permitted reserve room"; attribute :>> gap="Native geometry injection and all producer coverage open"; }
part obligation2:ObligationRow { attribute :>> key="progress"; attribute :>> status="conditional-proved"; attribute :>> scope="Drain enabledness and strictly decreasing pipeline rank"; attribute :>> gap="Fairness terminating callbacks and complete finite task supply open"; }
part obligation3:ObligationRow { attribute :>> key="composition"; attribute :>> status="proved-slice"; attribute :>> scope="17 pool actions simulate actual weak-admission AST or stutter; common delayed-ledger view"; attribute :>> gap="Per-object identity full marker product and native source composition open"; }
part obligation4:ObligationRow { attribute :>> key="reclaim"; attribute :>> status="proved-slice"; attribute :>> scope="No receipt with borrowers heads or unresolved receipts; no premature reclaim"; attribute :>> gap="Native late-registration exclusion and generation ABI open"; }
part obligation5:ObligationRow { attribute :>> key="C11"; attribute :>> status="open"; attribute :>> scope="Release/acquire handoffs and ordinary record accesses"; attribute :>> gap="No weak-memory execution/refinement checker claimed"; }
part obligation6:ObligationRow { attribute :>> key="net-benefit"; attribute :>> status="open"; attribute :>> scope="Cost inequalities and explicit memory ceilings"; attribute :>> gap="No native performance or runtime implementation"; }
part def BindingRow { attribute actionName:String; attribute lemma:String; attribute targetStep:String; attribute simulation:String; }
part binding0:BindingRow { attribute :>> actionName="chunk_node_pool.admit"; attribute :>> lemma="NodePool.admitPreserves"; attribute :>> targetStep="weak_producer_admission.stutter"; attribute :>> simulation="NodePoolComposition.admitSimulates"; }
part binding1:BindingRow { attribute :>> actionName="chunk_node_pool.reject"; attribute :>> lemma="NodePool.rejectPreserves"; attribute :>> targetStep="weak_producer_admission.stutter"; attribute :>> simulation="NodePoolComposition.rejectSimulates"; }
part binding2:BindingRow { attribute :>> actionName="chunk_node_pool.reserve"; attribute :>> lemma="NodePool.reservePreserves"; attribute :>> targetStep="weak_producer_admission.continuationProducer"; attribute :>> simulation="NodePoolComposition.reserveSimulates"; }
part binding3:BindingRow { attribute :>> actionName="chunk_node_pool.derive"; attribute :>> lemma="NodePool.derivePreserves"; attribute :>> targetStep="weak_producer_admission.deriveChild"; attribute :>> simulation="NodePoolComposition.deriveSimulates"; }
part binding4:BindingRow { attribute :>> actionName="chunk_node_pool.seal"; attribute :>> lemma="NodePool.sealPreserves"; attribute :>> targetStep="weak_producer_admission.stutter"; attribute :>> simulation="NodePoolComposition.sealSimulates"; }
part binding5:BindingRow { attribute :>> actionName="chunk_node_pool.publish"; attribute :>> lemma="NodePool.publishPreserves"; attribute :>> targetStep="weak_producer_admission.stutter"; attribute :>> simulation="NodePoolComposition.publishSimulates"; }
part binding6:BindingRow { attribute :>> actionName="chunk_node_pool.claim"; attribute :>> lemma="NodePool.claimPreserves"; attribute :>> targetStep="weak_producer_admission.stutter"; attribute :>> simulation="NodePoolComposition.claimSimulates"; }
part binding7:BindingRow { attribute :>> actionName="chunk_node_pool.finish"; attribute :>> lemma="NodePool.finishPreserves"; attribute :>> targetStep="weak_producer_admission.settleTask"; attribute :>> simulation="NodePoolComposition.finishSimulates"; }
part binding8:BindingRow { attribute :>> actionName="chunk_node_pool.observe"; attribute :>> lemma="NodePool.observePreserves"; attribute :>> targetStep="weak_producer_admission.stutter"; attribute :>> simulation="NodePoolComposition.observeSimulates"; }
part binding9:BindingRow { attribute :>> actionName="chunk_node_pool.borrow"; attribute :>> lemma="NodePool.borrowPreserves"; attribute :>> targetStep="weak_producer_admission.stutter"; attribute :>> simulation="NodePoolComposition.borrowSimulates"; }
part binding10:BindingRow { attribute :>> actionName="chunk_node_pool.returnBorrow"; attribute :>> lemma="NodePool.returnBorrowPreserves"; attribute :>> targetStep="weak_producer_admission.stutter"; attribute :>> simulation="NodePoolComposition.returnBorrowSimulates"; }
part binding11:BindingRow { attribute :>> actionName="chunk_node_pool.closeRoots"; attribute :>> lemma="NodePool.closeRootsPreserves"; attribute :>> targetStep="weak_producer_admission.closeRoots"; attribute :>> simulation="NodePoolComposition.closeRootsSimulates"; }
part binding12:BindingRow { attribute :>> actionName="chunk_node_pool.complete"; attribute :>> lemma="NodePool.completePreserves"; attribute :>> targetStep="weak_producer_admission.finishWeak"; attribute :>> simulation="NodePoolComposition.completeSimulates"; }
part binding13:BindingRow { attribute :>> actionName="chunk_node_pool.closeUsers"; attribute :>> lemma="NodePool.closeUsersPreserves"; attribute :>> targetStep="weak_producer_admission.stutter"; attribute :>> simulation="NodePoolComposition.closeUsersSimulates"; }
part binding14:BindingRow { attribute :>> actionName="chunk_node_pool.detachHead"; attribute :>> lemma="NodePool.detachHeadPreserves"; attribute :>> targetStep="weak_producer_admission.stutter"; attribute :>> simulation="NodePoolComposition.detachHeadSimulates"; }
part binding15:BindingRow { attribute :>> actionName="chunk_node_pool.certify"; attribute :>> lemma="NodePool.certifyPreserves"; attribute :>> targetStep="weak_producer_admission.stutter"; attribute :>> simulation="NodePoolComposition.certifySimulates"; }
part binding16:BindingRow { attribute :>> actionName="chunk_node_pool.reclaim"; attribute :>> lemma="NodePool.reclaimPreserves"; attribute :>> targetStep="weak_producer_admission.stutter"; attribute :>> simulation="NodePoolComposition.reclaimSimulates"; }
part def ProofRow { attribute key:String; attribute lemma:String; attribute scope:String; }
part proof0:ProofRow { attribute :>> key="room"; attribute :>> lemma="NodePool.permittedReserveHasSpace"; attribute :>> scope="Admitted remaining demand has free record"; }
part proof1:ProofRow { attribute :>> key="child-room"; attribute :>> lemma="NodePool.permittedChildHasSpace"; attribute :>> scope="Parent child budget remains bounded"; }
part proof2:ProofRow { attribute :>> key="balance"; attribute :>> lemma="NodePool.conservation"; attribute :>> scope="Issued equals retained done plus active debt"; }
part proof3:ProofRow { attribute :>> key="publish"; attribute :>> lemma="NodePool.publicationDoesNotAllocate"; attribute :>> scope="Queue publication allocates no additional record or debt"; }
part proof4:ProofRow { attribute :>> key="receipt"; attribute :>> lemma="NodePool.receiptExcludesUsers"; attribute :>> scope="Receipt excludes unresolved borrower/head/ack"; }
part proof5:ProofRow { attribute :>> key="enabled"; attribute :>> lemma="NodePool.drainAvailable"; attribute :>> scope="Some pipeline drain enabled for positive debt"; }
part proof6:ProofRow { attribute :>> key="coarse"; attribute :>> lemma="NodePool.coarseCapacity"; attribute :>> scope="Assumed terminal injection ceiling"; }
part proof7:ProofRow { attribute :>> key="charged"; attribute :>> lemma="NodePool.chargedCapacity"; attribute :>> scope="Assumed disjoint threshold charges"; }
part proof8:ProofRow { attribute :>> key="retained"; attribute :>> lemma="NodePool.fullRetainedPool"; attribute :>> scope="Zero debt and full pinned pool coexist"; }
part proof9:ProofRow { attribute :>> key="refinement"; attribute :>> lemma="NodePoolComposition.stepSimulates"; attribute :>> scope="Every actual pool action to old weak AST"; }
part proof10:ProofRow { attribute :>> key="common-ledger"; attribute :>> lemma="NodePoolComposition.commonWeakLedger"; attribute :>> scope="Aggregate and delayed slice share same weak ledger projection"; }
part proof11:ProofRow { attribute :>> key="reachable-refinement"; attribute :>> lemma="NodePoolComposition.reachableProjects"; attribute :>> scope="Actual pool initial projects to reachable old weak cut; steps preserve old reachability"; }
part proof12:ProofRow { attribute :>> key="strong-storage-carry"; attribute :>> lemma="NodePool.weakEntrySafe"; attribute :>> scope="Strong phase retained records receipts borrowers reduce remaining weak-phase capacity; source issuer open"; }
part proof13:ProofRow { attribute :>> key="warm-induction"; attribute :>> lemma="NodePool.runsFromSafe"; attribute :>> scope="Every pool step preserves safety from arbitrary qualified imported occupancy"; }
part proof14:ProofRow { attribute :>> key="warm-composition"; attribute :>> lemma="NodePoolComposition.weakEntryProjectIsWeakCut"; attribute :>> scope="Retained strong storage projects to the same old work-complete weak cut"; }
part history:GambitAssuranceRouting::ModelNeed { ref part :>> owner=GambitAssuranceRelations::modelUse3; attribute :>> obligationId="NP-history"; attribute :>> kind="interleaving"; attribute :>> subjectPath="dev/refactoring/modern-c/models/quint/chunk_node_pool.qnt"; attribute :>> subjectScope="Capacity publication pins and failure histories"; attribute :>> premise="Research only; no native or performance qualification"; }
part induction:GambitAssuranceRouting::ModelNeed { ref part :>> owner=GambitAssuranceRelations::modelUse3; attribute :>> obligationId="NP-induction"; attribute :>> kind="induction"; attribute :>> subjectPath="dev/refactoring/modern-c/models/lean/NodePool.lean"; attribute :>> subjectScope="Actual typed AST all-step safety and conditional capacity progress"; attribute :>> premise="Research only; no native or performance qualification"; }
part composition:GambitAssuranceRouting::ModelNeed { ref part :>> owner=GambitAssuranceRelations::modelUse3; attribute :>> obligationId="NP-composition"; attribute :>> kind="induction"; attribute :>> subjectPath="dev/refactoring/modern-c/models/lean/NodePoolComposition.lean"; attribute :>> subjectScope="Actual weak AST simulation and common delayed-ledger view"; attribute :>> premise="Research only; no native or performance qualification"; }
part projection:GambitAssuranceRouting::ModelNeed { ref part :>> owner=GambitAssuranceRelations::modelUse3; attribute :>> obligationId="NP-projection"; attribute :>> kind="restricted-projection"; attribute :>> subjectPath="dev/refactoring/modern-c/models/lean/NodePoolAst.lean"; attribute :>> subjectScope="Restricted scalar typed IR with binding validation"; attribute :>> premise="Research only; no native or performance qualification"; }
part source:GambitAssuranceRouting::ModelNeed { ref part :>> owner=GambitAssuranceRelations::modelUse3; attribute :>> obligationId="NP-source"; attribute :>> kind="source-refinement"; attribute :>> subjectPath="dev/refactoring/modern-c/chunk-node-pool-design.org"; attribute :>> subjectScope="Native geometry producers and epoch closure remain open"; attribute :>> premise="Research only; no native or performance qualification"; }
part platform:GambitAssuranceRouting::ModelNeed { ref part :>> owner=GambitAssuranceRelations::modelUse3; attribute :>> obligationId="NP-platform"; attribute :>> kind="native-memory-order"; attribute :>> subjectPath="dev/refactoring/modern-c/chunk-node-pool-design.org"; attribute :>> subjectScope="C11 storage memory order machine arithmetic and generation remain open"; attribute :>> premise="Research only; no native or performance qualification"; }
part def Seam { ref part producer:GambitRuntimeComposition::BlueprintModule; ref part consumer:GambitRuntimeComposition::BlueprintModule; attribute contract:String; attribute modelNeed:String; }
part seam0:Seam { ref part :>> producer=GambitRuntimeComposition::blueprintModule4; ref part :>> consumer=GambitRuntimeComposition::blueprintModule4; attribute :>> contract="Native node pool and total work ledger"; attribute :>> modelNeed="NP-induction"; }
part seam1:Seam { ref part :>> producer=GambitRuntimeComposition::blueprintModule4; ref part :>> consumer=GambitRuntimeComposition::blueprintModule5; attribute :>> contract="Epoch close and reclaim authorization"; attribute :>> modelNeed="NP-composition"; }
part seam2:Seam { ref part :>> producer=GambitRuntimeComposition::blueprintModule4; ref part :>> consumer=GambitRuntimeComposition::blueprintModule1; attribute :>> contract="Native storage publication C11"; attribute :>> modelNeed="NP-platform"; }
}
