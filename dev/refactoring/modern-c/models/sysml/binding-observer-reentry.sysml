package GambitBindingObserverReentry { private import ScalarValues::*;
part def SourceRow { attribute key:String; attribute path:String; attribute needle:String; attribute obligation:String; }
part source0:SourceRow { attribute :>> key="port-install"; attribute :>> path="vendor/gambit/gsc/_t-c-1.scm"; attribute :>> needle="(set! targ-port (open-output-file-preserving-case filename))"; attribute :>> obligation="Backend selects file port, not a caller-supplied arbitrary port"; }
part source1:SourceRow { attribute :>> key="host-file"; attribute :>> path="vendor/gambit/gsc/_host.scm"; attribute :>> needle="(define (open-output-file-preserving-case path)"; attribute :>> obligation="Gambit branch parameterizes readtable and calls file opener; host artifact binding external"; }
part source2:SourceRow { attribute :>> key="file-open"; attribute :>> path="vendor/gambit/lib/_io.scm"; attribute :>> needle="(define-prim (##open-output-file path-or-settings)"; attribute :>> obligation="File opener uses open-file-generic and device constructor"; }
part source3:SourceRow { attribute :>> key="device"; attribute :>> path="vendor/gambit/lib/_io.scm"; attribute :>> needle="(define-prim (##make-device-port device-name rdevice wdevice psettings)"; attribute :>> obligation="Default device writer uses ##wr; handler and timeout thunk initially false"; }
part source4:SourceRow { attribute :>> key="default-writer"; attribute :>> path="vendor/gambit/lib/_io.scm"; attribute :>> needle="(##wr we obj)"; attribute :>> obligation="Device writer calls mutable global formatter"; }
part source5:SourceRow { attribute :>> key="wr-hook"; attribute :>> path="vendor/gambit/lib/_io.scm"; attribute :>> needle="(define-prim (##wr-set! x)"; attribute :>> obligation="Actual hook setter; not evidence gsc installs a custom hook"; }
part source6:SourceRow { attribute :>> key="wr-write"; attribute :>> path="vendor/gambit/lib/_io.scm"; attribute :>> needle="(set! ##wr x)"; attribute :>> obligation="Formatting behavior may change without replacing port"; }
part source7:SourceRow { attribute :>> key="display"; attribute :>> path="vendor/gambit/gsc/_t-c-1.scm"; attribute :>> needle="(display x targ-port)"; attribute :>> obligation="Display crosses generic Scheme formatter"; }
part source8:SourceRow { attribute :>> key="generic"; attribute :>> path="vendor/gambit/lib/_io.scm"; attribute :>> needle="(define-prim (##write-generic-to-character-port style port rt force? limit obj)"; attribute :>> obligation="Mark and output passes both invoke writer dispatch; not one callback per display"; }
part source9:SourceRow { attribute :>> key="wr-substr"; attribute :>> path="vendor/gambit/lib/_io.scm"; attribute :>> needle="(##write-substring s i j port)"; attribute :>> obligation="Connect primitive string output to buffer drain/error"; }
part source10:SourceRow { attribute :>> key="drain"; attribute :>> path="vendor/gambit/lib/_io.scm"; attribute :>> needle="(let ((code ((macro-character-port-wbuf-drain port) port)))"; attribute :>> obligation="Buffer drain errors can raise after unlocking the port"; }
part source11:SourceRow { attribute :>> key="io-error"; attribute :>> path="vendor/gambit/lib/_io.scm"; attribute :>> needle="(define-prim (##raise-io-exception port exc)"; attribute :>> obligation="Port custom handler or dynamic raise channel"; }
part source12:SourceRow { attribute :>> key="port-handler"; attribute :>> path="vendor/gambit/lib/_io.scm"; attribute :>> needle="(define-prim (port-io-exception-handler-set! port handler)"; attribute :>> obligation="Requires actual port reference and caller installation"; }
part source13:SourceRow { attribute :>> key="timeout"; attribute :>> path="vendor/gambit/lib/_io.scm"; attribute :>> needle="(define-prim (output-port-timeout-set!"; attribute :>> obligation="Requires port capability and finite timeout/OS wait condition"; }
part source14:SourceRow { attribute :>> key="timeout-dispatch"; attribute :>> path="vendor/gambit/lib/_io.scm"; attribute :>> needle="((macro-port-wtimeout-thunk port))"; attribute :>> obligation="Reachable dispatch guarded by wait failure; not unconditional default callback"; }
part source15:SourceRow { attribute :>> key="runtime-handler"; attribute :>> path="vendor/gambit/lib/_thread#.scm"; attribute :>> needle="(##define-macro (macro-raise obj)"; attribute :>> obligation="Uses thread dynamic exception handler, separate from compiler-abort continuation"; }
part source16:SourceRow { attribute :>> key="dynamic-install"; attribute :>> path="vendor/gambit/lib/_thread.scm"; attribute :>> needle="(define-prim (with-exception-handler handler thunk)"; attribute :>> obligation="Embedding can establish dynamic handler without owning targ-port"; }
part source17:SourceRow { attribute :>> key="catcher"; attribute :>> path="vendor/gambit/lib/_thread.scm"; attribute :>> needle="(define-prim (##with-exception-catcher catcher thunk)"; attribute :>> obligation="Captures/grafts continuation; different from resumable return"; }
part source18:SourceRow { attribute :>> key="compiler-catch"; attribute :>> path="vendor/gambit/gsc/_utils.scm"; attribute :>> needle="(set! throw-to-exception-handler cont)"; attribute :>> obligation="Compiler wrapper changes its own variable, not dynamic runtime handler"; }
part source19:SourceRow { attribute :>> key="compiler-abort"; attribute :>> path="vendor/gambit/gsc/_utils.scm"; attribute :>> needle="(throw-to-exception-handler #f)"; attribute :>> obligation="Ordinary compiler abort targets outer captured continuation"; }
part source20:SourceRow { attribute :>> key="gc-register"; attribute :>> path="vendor/gambit/lib/_kernel.scm"; attribute :>> needle="(define-prim (##add-gc-interrupt-job! thunk)"; attribute :>> obligation="Global GC job registration is another callback producer"; }
part source21:SourceRow { attribute :>> key="gc-dispatch"; attribute :>> path="vendor/gambit/lib/_kernel.scm"; attribute :>> needle="(##execute-jobs! ##gc-interrupt-jobs)"; attribute :>> obligation="Runtime dispatch exists; exact poll position and current profile qualification OPEN"; }
part source22:SourceRow { attribute :>> key="will-dispatch"; attribute :>> path="vendor/gambit/lib/_kernel.scm"; attribute :>> needle="(action testator)"; attribute :>> obligation="Will action invokes Scheme callback; resource capabilities need closure"; }
part source23:SourceRow { attribute :>> key="table-reset"; attribute :>> path="vendor/gambit/gsc/_t-c-1.scm"; attribute :>> needle="(set! targ-glo-vars         (make-table 'test: eq?))"; attribute :>> obligation="Nested compilation changes table identity"; }
part source24:SourceRow { attribute :>> key="table-clear"; attribute :>> path="vendor/gambit/gsc/_t-c-1.scm"; attribute :>> needle="(set! targ-glo-vars #f)"; attribute :>> obligation="Normal nested cleanup can leave resumed outer helper with cleared table"; }
part source25:SourceRow { attribute :>> key="demand"; attribute :>> path="vendor/gambit/gsc/_t-c-1.scm"; attribute :>> needle="(targ-rsrc-demanders-set! (cdr x) '(\"\"))"; attribute :>> obligation="Named use-false canonicalizes same-entry demand"; }
part source26:SourceRow { attribute :>> key="supply"; attribute :>> path="vendor/gambit/gsc/_t-c-1.scm"; attribute :>> needle="(targ-rsrc-suppliers-set! (cdr x) '(\"\"))"; attribute :>> obligation="Named use-true preserves demand field"; }
part source27:SourceRow { attribute :>> key="raw-setter"; attribute :>> path="vendor/gambit/gsc/_t-c-1.scm"; attribute :>> needle="(vector-set! r 1 demanders)"; attribute :>> obligation="Raw setter can undo canonical value"; }
part source28:SourceRow { attribute :>> key="prm"; attribute :>> path="vendor/gambit/gsc/_t-c-1.scm"; attribute :>> needle="(def-mod-prm-glo \"DEF_MOD_PRM\")"; attribute :>> obligation="First effect before selected PRM text construction"; }
part source29:SourceRow { attribute :>> key="glo"; attribute :>> path="vendor/gambit/gsc/_t-c-1.scm"; attribute :>> needle="(def-mod-prm-glo \"DEF_MOD_GLO\")"; attribute :>> obligation="Second effect must not be deleted under raw write/entry replacement"; }
part source30:SourceRow { attribute :>> key="helper"; attribute :>> path="vendor/gambit/gsc/_t-c-1.scm"; attribute :>> needle="(targ-use-glo (string->symbol name) #f)"; attribute :>> obligation="Helper re-reads current global table; does not retain first entry"; }
part source31:SourceRow { attribute :>> key="namespace"; attribute :>> path="vendor/gambit/gsc/fixnum.scm"; attribute :>> needle="targ-use-glo"; attribute :>> obligation="Compiler namespace maps helper; namespace alone is not a full capability analysis"; }
part def RouteRow { attribute key:String; attribute producer:String; attribute dispatch:String; attribute capability:String; attribute status:String; }
part route0:RouteRow { attribute :>> key="formatter"; attribute :>> producer="##wr-set!"; attribute :>> dispatch="device write-datum -> ##wr"; attribute :>> capability="Hook registration and a closure capable of metadata access"; attribute :>> status="Actual mechanism; gsc registration and metadata effect not observed"; }
part route1:RouteRow { attribute :>> key="io-dynamic"; attribute :>> producer="with-exception-handler"; attribute :>> dispatch="IO error -> macro-raise -> current handler"; attribute :>> capability="Dynamic handler plus backend access; no port alias required"; attribute :>> status="Actual route under IO error; handler may return or escape"; }
part route2:RouteRow { attribute :>> key="io-port"; attribute :>> producer="port-io-exception-handler-set!"; attribute :>> dispatch="IO error -> port handler"; attribute :>> capability="Existing target-port reference and installed handler"; attribute :>> status="API exists; ordinary file initializes handler false"; }
part route3:RouteRow { attribute :>> key="timeout"; attribute :>> producer="output-port-timeout-set!"; attribute :>> dispatch="EAGAIN -> wait failure -> thunk"; attribute :>> capability="Port reference, timeout setting, wait outcome"; attribute :>> status="Conditional route; not evidence default gsc callback"; }
part route4:RouteRow { attribute :>> key="gc"; attribute :>> producer="GC job or will registration"; attribute :>> dispatch="handle-gc-interrupt -> jobs / action"; attribute :>> capability="Registered closure, permitted poll and backend capability"; attribute :>> status="Dispatch established; exact interpass scheduling OPEN"; }
part route5:RouteRow { attribute :>> key="compiler-abort"; attribute :>> producer="compiler-error -> compiler-abort"; attribute :>> dispatch="throw-to-exception-handler"; attribute :>> capability="Compiler wrapper continuation"; attribute :>> status="Does not itself resume failed helper or install dynamic EH"; }
part route6:RouteRow { attribute :>> key="raw-resume"; attribute :>> producer="capture inside admitted callback"; attribute :>> dispatch="saved continuation -> old locals and current globals"; attribute :>> capability="Capture site, multi-shot continuation, resource lifetime"; attribute :>> status="Source-composable conditional path; no native reproduction"; }
part def ClaimRow { attribute key:String; attribute mechanism:String; attribute condition:String; attribute result:String; attribute gap:String; }
part claim0:ClaimRow { attribute :>> key="first"; attribute :>> mechanism="Observe demand through capable formatter/handler"; attribute :>> condition="Actual callback registration and resource read capability"; attribute :>> result="First normalization is observable in that domain"; attribute :>> gap="No current default-gsc malicious/metadata callback asserted"; }
part claim1:ClaimRow { attribute :>> key="second"; attribute :>> mechanism="Canonicality-preserving writer closure"; attribute :>> condition="Same entry/generation and only named demand/supply writes"; attribute :>> result="Second value normalization redundant even with intermediate writes"; attribute :>> gap="Setter identity/events and raw writes outside theorem"; }
part claim2:ClaimRow { attribute :>> key="error"; attribute :>> mechanism="Returning handler can let caller continue"; attribute :>> condition="IO failure plus a returning runtime or port handler"; attribute :>> result="Successful close alone cannot certify no prior lost bytes"; attribute :>> gap="Sticky error or independent byte validation needs concrete adapter"; }
part claim3:ClaimRow { attribute :>> key="continuation"; attribute :>> mechanism="Retained roots and multiple resumes"; attribute :>> condition="Real capture plus stable entry/output operation identity"; attribute :>> result="Capture does not become consumed after first return"; attribute :>> gap="Detachment source proof and byte cursor refinement OPEN"; }
part def GainRow { attribute key:String; attribute avoided:String; attribute added:String; attribute condition:String; }
part gain0:GainRow { attribute :>> key="first"; attribute :>> avoided="Up to P first demand writes"; attribute :>> added="Callback effect audit plus plan/root ownership"; attribute :>> condition="No observer and matching fault semantics; P=455 is prior artifact count, not timing"; }
part gain1:GainRow { attribute :>> key="second"; attribute :>> avoided="Up to P second normalizations"; attribute :>> added="Writer-class/canonicality and identity qualification"; attribute :>> condition="Allows named writers instead of a blanket no-writer condition"; }
part gain2:GainRow { attribute :>> key="both"; attribute :>> avoided="Up to 2P late mutation-capable uses"; attribute :>> added="Shared immutable plan, owned buffers, capture custody and validation"; attribute :>> condition="Lookup/validation may move rather than disappear"; }
part gain3:GainRow { attribute :>> key="hooked"; attribute :>> avoided="No guaranteed first-write saving"; attribute :>> added="Preserve supported callback observations; raw writes may retain second effect"; attribute :>> condition="Default file port does not close formatter or dynamic exception capabilities"; }
part gain4:GainRow { attribute :>> key="net"; attribute :>> avoided="Removed duplicate work D and proven redundant work W"; attribute :>> added="Plan K + ownership S + observer audit H + verification V"; attribute :>> condition="Positive only if D+W>K+S+H+V; no native speedup established"; }
part def ContractRow { attribute fromNode:String; attribute toNode:String; attribute custody:String; }
part contract0:ContractRow { attribute :>> fromNode="File opener"; attribute :>> toNode="Device writer"; attribute :>> custody="initial defaults"; }
part contract1:ContractRow { attribute :>> fromNode="Device writer"; attribute :>> toNode="Formatter hook"; attribute :>> custody="mutable dispatch"; }
part contract2:ContractRow { attribute :>> fromNode="Formatter hook"; attribute :>> toNode="Capability audit"; attribute :>> custody="closure effects"; }
part contract3:ContractRow { attribute :>> fromNode="IO fault"; attribute :>> toNode="Dynamic handler"; attribute :>> custody="independent channel"; }
part contract4:ContractRow { attribute :>> fromNode="Dynamic handler"; attribute :>> toNode="Capability audit"; attribute :>> custody="return or escape"; }
part contract5:ContractRow { attribute :>> fromNode="GC and timeout"; attribute :>> toNode="Capability audit"; attribute :>> custody="conditional callbacks"; }
part contract6:ContractRow { attribute :>> fromNode="Capability audit"; attribute :>> toNode="First-effect decision"; attribute :>> custody="observer closure"; }
part contract7:ContractRow { attribute :>> fromNode="First-effect decision"; attribute :>> toNode="Canonical writer closure"; attribute :>> custody="same entry"; }
part contract8:ContractRow { attribute :>> fromNode="Canonical writer closure"; attribute :>> toNode="Second-effect decision"; attribute :>> custody="preserve value"; }
part contract9:ContractRow { attribute :>> fromNode="Second-effect decision"; attribute :>> toNode="Completion guard"; attribute :>> custody="byte and error status"; }
part contract10:ContractRow { attribute :>> fromNode="Captured continuation"; attribute :>> toNode="Completion guard"; attribute :>> custody="retained root debt"; }
part contract11:ContractRow { attribute :>> fromNode="Completion guard"; attribute :>> toNode="Retirement receipt"; attribute :>> custody="no stale resume"; }
part def BindingRow { attribute actionName:String; attribute lemma:String; attribute scope:String; }
part binding0:BindingRow { attribute :>> actionName="binding_observer_reentry.plainProfile"; attribute :>> lemma="BindingObserver.plainProfilePreserves"; attribute :>> scope="Interpass abstract action; actual producer qualification and source refinement external"; }
part binding1:BindingRow { attribute :>> actionName="binding_observer_reentry.useOnlyProfile"; attribute :>> lemma="BindingObserver.useOnlyProfilePreserves"; attribute :>> scope="Interpass abstract action; actual producer qualification and source refinement external"; }
part binding2:BindingRow { attribute :>> actionName="binding_observer_reentry.rawProfile"; attribute :>> lemma="BindingObserver.rawProfilePreserves"; attribute :>> scope="Interpass abstract action; actual producer qualification and source refinement external"; }
part binding3:BindingRow { attribute :>> actionName="binding_observer_reentry.seal"; attribute :>> lemma="BindingObserver.sealPreserves"; attribute :>> scope="Interpass abstract action; actual producer qualification and source refinement external"; }
part binding4:BindingRow { attribute :>> actionName="binding_observer_reentry.firstElide"; attribute :>> lemma="BindingObserver.firstElidePreserves"; attribute :>> scope="Interpass abstract action; actual producer qualification and source refinement external"; }
part binding5:BindingRow { attribute :>> actionName="binding_observer_reentry.firstRetain"; attribute :>> lemma="BindingObserver.firstRetainPreserves"; attribute :>> scope="Interpass abstract action; actual producer qualification and source refinement external"; }
part binding6:BindingRow { attribute :>> actionName="binding_observer_reentry.enterFormatter"; attribute :>> lemma="BindingObserver.enterFormatterPreserves"; attribute :>> scope="Interpass abstract action; actual producer qualification and source refinement external"; }
part binding7:BindingRow { attribute :>> actionName="binding_observer_reentry.enterIOHandler"; attribute :>> lemma="BindingObserver.enterIOHandlerPreserves"; attribute :>> scope="Interpass abstract action; actual producer qualification and source refinement external"; }
part binding8:BindingRow { attribute :>> actionName="binding_observer_reentry.enterTimeout"; attribute :>> lemma="BindingObserver.enterTimeoutPreserves"; attribute :>> scope="Interpass abstract action; actual producer qualification and source refinement external"; }
part binding9:BindingRow { attribute :>> actionName="binding_observer_reentry.enterGC"; attribute :>> lemma="BindingObserver.enterGCPreserves"; attribute :>> scope="Interpass abstract action; actual producer qualification and source refinement external"; }
part binding10:BindingRow { attribute :>> actionName="binding_observer_reentry.readObserver"; attribute :>> lemma="BindingObserver.readObserverPreserves"; attribute :>> scope="Interpass abstract action; actual producer qualification and source refinement external"; }
part binding11:BindingRow { attribute :>> actionName="binding_observer_reentry.namedDemand"; attribute :>> lemma="BindingObserver.namedDemandPreserves"; attribute :>> scope="Interpass abstract action; actual producer qualification and source refinement external"; }
part binding12:BindingRow { attribute :>> actionName="binding_observer_reentry.namedSupply"; attribute :>> lemma="BindingObserver.namedSupplyPreserves"; attribute :>> scope="Interpass abstract action; actual producer qualification and source refinement external"; }
part binding13:BindingRow { attribute :>> actionName="binding_observer_reentry.rawWrite"; attribute :>> lemma="BindingObserver.rawWritePreserves"; attribute :>> scope="Interpass abstract action; actual producer qualification and source refinement external"; }
part binding14:BindingRow { attribute :>> actionName="binding_observer_reentry.leaveHook"; attribute :>> lemma="BindingObserver.leaveHookPreserves"; attribute :>> scope="Interpass abstract action; actual producer qualification and source refinement external"; }
part binding15:BindingRow { attribute :>> actionName="binding_observer_reentry.secondReadonly"; attribute :>> lemma="BindingObserver.secondReadonlyPreserves"; attribute :>> scope="Interpass abstract action; actual producer qualification and source refinement external"; }
part binding16:BindingRow { attribute :>> actionName="binding_observer_reentry.secondUnobserved"; attribute :>> lemma="BindingObserver.secondUnobservedPreserves"; attribute :>> scope="Interpass abstract action; actual producer qualification and source refinement external"; }
part binding17:BindingRow { attribute :>> actionName="binding_observer_reentry.secondNormalize"; attribute :>> lemma="BindingObserver.secondNormalizePreserves"; attribute :>> scope="Interpass abstract action; actual producer qualification and source refinement external"; }
part binding18:BindingRow { attribute :>> actionName="binding_observer_reentry.ioFailure"; attribute :>> lemma="BindingObserver.ioFailurePreserves"; attribute :>> scope="Interpass abstract action; actual producer qualification and source refinement external"; }
part binding19:BindingRow { attribute :>> actionName="binding_observer_reentry.compilerAbort"; attribute :>> lemma="BindingObserver.compilerAbortPreserves"; attribute :>> scope="Interpass abstract action; actual producer qualification and source refinement external"; }
part binding20:BindingRow { attribute :>> actionName="binding_observer_reentry.nestedCompilation"; attribute :>> lemma="BindingObserver.nestedCompilationPreserves"; attribute :>> scope="Interpass abstract action; actual producer qualification and source refinement external"; }
part binding21:BindingRow { attribute :>> actionName="binding_observer_reentry.rejectStale"; attribute :>> lemma="BindingObserver.rejectStalePreserves"; attribute :>> scope="Interpass abstract action; actual producer qualification and source refinement external"; }
part binding22:BindingRow { attribute :>> actionName="binding_observer_reentry.capture"; attribute :>> lemma="BindingObserver.capturePreserves"; attribute :>> scope="Interpass abstract action; actual producer qualification and source refinement external"; }
part binding23:BindingRow { attribute :>> actionName="binding_observer_reentry.resumeCaptured"; attribute :>> lemma="BindingObserver.resumeCapturedPreserves"; attribute :>> scope="Interpass abstract action; actual producer qualification and source refinement external"; }
part binding24:BindingRow { attribute :>> actionName="binding_observer_reentry.certifyNoResume"; attribute :>> lemma="BindingObserver.certifyNoResumePreserves"; attribute :>> scope="Interpass abstract action; actual producer qualification and source refinement external"; }
part binding25:BindingRow { attribute :>> actionName="binding_observer_reentry.closeOutput"; attribute :>> lemma="BindingObserver.closeOutputPreserves"; attribute :>> scope="Interpass abstract action; actual producer qualification and source refinement external"; }
part binding26:BindingRow { attribute :>> actionName="binding_observer_reentry.issue"; attribute :>> lemma="BindingObserver.issuePreserves"; attribute :>> scope="Interpass abstract action; actual producer qualification and source refinement external"; }
part binding27:BindingRow { attribute :>> actionName="binding_observer_reentry.unknownExit"; attribute :>> lemma="BindingObserver.unknownExitPreserves"; attribute :>> scope="Interpass abstract action; actual producer qualification and source refinement external"; }
part def ProofRow { attribute key:String; attribute lemma:String; }
part proof0:ProofRow { attribute :>> key="steps"; attribute :>> lemma="BindingObserver.stepPreserves"; }
part proof1:ProofRow { attribute :>> key="reachable"; attribute :>> lemma="BindingObserver.reachableSafe"; }
part proof2:ProofRow { attribute :>> key="error"; attribute :>> lemma="BindingObserver.errorBlocksReceipt"; }
part proof3:ProofRow { attribute :>> key="capture"; attribute :>> lemma="BindingObserver.captureBlocksReceipt"; }
part proof4:ProofRow { attribute :>> key="custody"; attribute :>> lemma="BindingObserver.unknownKeepsCustody"; }
part proof5:ProofRow { attribute :>> key="demand"; attribute :>> lemma="BindingWriterClosure.demandCanonical"; }
part proof6:ProofRow { attribute :>> key="supply"; attribute :>> lemma="BindingWriterClosure.supplyKeepsCanonical"; }
part proof7:ProofRow { attribute :>> key="one-writer"; attribute :>> lemma="BindingWriterClosure.stepKeepsCanonical"; }
part proof8:ProofRow { attribute :>> key="all-writers"; attribute :>> lemma="BindingWriterClosure.historyKeepsCanonical"; }
part proof9:ProofRow { attribute :>> key="second"; attribute :>> lemma="BindingWriterClosure.secondAfterNamedHistory"; }
part proof10:ProofRow { attribute :>> key="first-counterexample"; attribute :>> lemma="BindingWriterClosure.firstObservable"; }
part proof11:ProofRow { attribute :>> key="raw-counterexample"; attribute :>> lemma="BindingWriterClosure.rawWriterBreaks"; }
part proof12:ProofRow { attribute :>> key="identity"; attribute :>> lemma="BindingWriterClosure.namesDoNotReplaceIdentity"; }
part def MigrationRow { attribute key:String; attribute producerAnchor:String; attribute consumerAnchor:String; attribute actionName:String; attribute lemma:String; }
part migration0:MigrationRow { attribute :>> key="formatter"; attribute :>> producerAnchor="wr-write"; attribute :>> consumerAnchor="default-writer"; attribute :>> actionName="binding_observer_reentry.enterFormatter"; attribute :>> lemma="BindingObserver.enterFormatterPreserves"; }
part migration1:MigrationRow { attribute :>> key="io-channel"; attribute :>> producerAnchor="io-error"; attribute :>> consumerAnchor="runtime-handler"; attribute :>> actionName="binding_observer_reentry.enterIOHandler"; attribute :>> lemma="BindingObserver.enterIOHandlerPreserves"; }
part migration2:MigrationRow { attribute :>> key="timeout"; attribute :>> producerAnchor="timeout"; attribute :>> consumerAnchor="timeout-dispatch"; attribute :>> actionName="binding_observer_reentry.enterTimeout"; attribute :>> lemma="BindingObserver.enterTimeoutPreserves"; }
part migration3:MigrationRow { attribute :>> key="gc"; attribute :>> producerAnchor="gc-register"; attribute :>> consumerAnchor="gc-dispatch"; attribute :>> actionName="binding_observer_reentry.enterGC"; attribute :>> lemma="BindingObserver.enterGCPreserves"; }
part migration4:MigrationRow { attribute :>> key="canonical"; attribute :>> producerAnchor="supply"; attribute :>> consumerAnchor="glo"; attribute :>> actionName="binding_observer_reentry.secondReadonly"; attribute :>> lemma="BindingWriterClosure.secondAfterNamedHistory"; }
part migration5:MigrationRow { attribute :>> key="nested"; attribute :>> producerAnchor="table-reset"; attribute :>> consumerAnchor="helper"; attribute :>> actionName="binding_observer_reentry.rejectStale"; attribute :>> lemma="BindingWriterClosure.namesDoNotReplaceIdentity"; }
part migration6:MigrationRow { attribute :>> key="abort"; attribute :>> producerAnchor="compiler-abort"; attribute :>> consumerAnchor="compiler-catch"; attribute :>> actionName="binding_observer_reentry.compilerAbort"; attribute :>> lemma="BindingObserver.compilerAbortPreserves"; }
part history:GambitAssuranceRouting::ModelNeed { ref part :>> owner=GambitAssuranceRelations::modelUse2; attribute :>> obligationId="BO-history"; attribute :>> kind="interleaving"; attribute :>> subjectPath="dev/refactoring/modern-c/models/quint/binding_observer_reentry.qnt"; attribute :>> subjectScope="20 interpass histories; named/raw writers error return capture debt and stale context"; attribute :>> premise="C23 source/formal study; no native admission"; }
part induction:GambitAssuranceRouting::ModelNeed { ref part :>> owner=GambitAssuranceRelations::modelUse2; attribute :>> obligationId="BO-induction"; attribute :>> kind="induction"; attribute :>> subjectPath="dev/refactoring/modern-c/models/lean/BindingObserver.lean"; attribute :>> subjectScope="All projected steps preserve conditional slice invariant"; attribute :>> premise="C23 source/formal study; no native admission"; }
part closure:GambitAssuranceRouting::ModelNeed { ref part :>> owner=GambitAssuranceRelations::modelUse2; attribute :>> obligationId="BO-closure"; attribute :>> kind="induction"; attribute :>> subjectPath="dev/refactoring/modern-c/models/lean/BindingWriterClosure.lean"; attribute :>> subjectScope="Canonicality under all finite histories of named same-entry demand/supply operations"; attribute :>> premise="C23 source/formal study; no native admission"; }
part projection:GambitAssuranceRouting::ModelNeed { ref part :>> owner=GambitAssuranceRelations::modelUse2; attribute :>> obligationId="BO-projection"; attribute :>> kind="restricted-projection"; attribute :>> subjectPath="dev/refactoring/modern-c/models/lean/BindingObserverAst.lean"; attribute :>> subjectScope="Actual binding IDs field kinds expressions roster; parser trusted"; attribute :>> premise="C23 source/formal study; no native admission"; }
part source:GambitAssuranceRouting::ModelNeed { ref part :>> owner=GambitAssuranceRelations::modelUse2; attribute :>> obligationId="BO-source"; attribute :>> kind="source-refinement"; attribute :>> subjectPath="dev/refactoring/modern-c/binding-observer-reentry-design.org"; attribute :>> subjectScope="Actual installed callbacks full capability/alias closure poll positions and capture detachment OPEN"; attribute :>> premise="C23 source/formal study; no native admission"; }
part exceptions:GambitAssuranceRouting::ModelNeed { ref part :>> owner=GambitAssuranceRelations::modelUse2; attribute :>> obligationId="BO-exceptions"; attribute :>> kind="exception-equivalence"; attribute :>> subjectPath="dev/refactoring/modern-c/binding-observer-reentry-design.org"; attribute :>> subjectScope="Fault-prefix equality returning handler byte loss and operation replay OPEN"; attribute :>> premise="C23 source/formal study; no native admission"; }
part platform:GambitAssuranceRouting::ModelNeed { ref part :>> owner=GambitAssuranceRelations::modelUse2; attribute :>> obligationId="BO-platform"; attribute :>> kind="c23-platform-qualification"; attribute :>> subjectPath="dev/refactoring/modern-c/language-baseline-design.org"; attribute :>> subjectScope="C23 owner/publication/lifetime and actual host artifact qualification OPEN"; attribute :>> premise="C23 source/formal study; no native admission"; }
part emission:GambitAssuranceRouting::ModelNeed { ref part :>> owner=GambitAssuranceRelations::modelUse2; attribute :>> obligationId="BO-emission"; attribute :>> kind="emitter-fidelity"; attribute :>> subjectPath="dev/refactoring/modern-c/binding-observer-reentry-design.org"; attribute :>> subjectScope="Complete byte mapping and before/after-interpass composition OPEN"; attribute :>> premise="C23 source/formal study; no native admission"; }

part def InventoryRow { attribute key:String; attribute path:String; attribute pattern:String; attribute count:String; attribute scope:String; }
part inventory0:InventoryRow { attribute :>> key="formatter"; attribute :>> path="vendor/gambit/lib/_io.scm"; attribute :>> pattern="##wr-set!(?![A-Za-z0-9?!-])"; attribute :>> count="1"; attribute :>> scope="Exact lexical token footprint including definitions/comments; installed capability closure OPEN"; }
part inventory1:InventoryRow { attribute :>> key="port-ref"; attribute :>> path="vendor/gambit/gsc/_t-c-1.scm"; attribute :>> pattern="targ-port(?![A-Za-z0-9?!-])"; attribute :>> count="13"; attribute :>> scope="Exact lexical token footprint including definitions/comments; installed capability closure OPEN"; }
part inventory2:InventoryRow { attribute :>> key="compiler-error"; attribute :>> path="vendor/gambit/gsc/_utils.scm"; attribute :>> pattern="throw-to-exception-handler(?![A-Za-z0-9?!-])"; attribute :>> count="5"; attribute :>> scope="Exact lexical token footprint including definitions/comments; installed capability closure OPEN"; }
part inventory3:InventoryRow { attribute :>> key="io-raise"; attribute :>> path="vendor/gambit/lib/_io.scm"; attribute :>> pattern="##raise-io-exception(?![A-Za-z0-9?!-])"; attribute :>> count="5"; attribute :>> scope="Exact lexical token footprint including definitions/comments; installed capability closure OPEN"; }

part def PolicyRow { attribute key:String; attribute writerClass:String; attribute assumptions:String; attribute firstExpected:String; attribute secondExpected:String; attribute scope:String; }
part policy0:PolicyRow { attribute :>> key="current-no-qualified-closure"; attribute :>> writerClass="none"; attribute :>> assumptions=""; attribute :>> firstExpected="false"; attribute :>> secondExpected="false"; attribute :>> scope="Assumption-only sufficient contract profile; not source or native admission"; }
part policy1:PolicyRow { attribute :>> key="synthetic-unobserved"; attribute :>> writerClass="none"; attribute :>> assumptions="no-observers;same-entry;writer-closure;fault-equivalence;lifetime-closed"; attribute :>> firstExpected="true"; attribute :>> secondExpected="false"; attribute :>> scope="Assumption-only sufficient contract profile; not source or native admission"; }
part policy2:PolicyRow { attribute :>> key="synthetic-named"; attribute :>> writerClass="named-only"; attribute :>> assumptions="first-retained;same-entry;writer-closure;fault-equivalence;lifetime-closed;setter-events-unobservable"; attribute :>> firstExpected="false"; attribute :>> secondExpected="true"; attribute :>> scope="Assumption-only sufficient contract profile; not source or native admission"; }
part policy3:PolicyRow { attribute :>> key="synthetic-raw"; attribute :>> writerClass="raw"; attribute :>> assumptions="first-retained;same-entry;writer-closure;fault-equivalence;lifetime-closed;setter-events-unobservable"; attribute :>> firstExpected="false"; attribute :>> secondExpected="false"; attribute :>> scope="Assumption-only sufficient contract profile; not source or native admission"; }
part policy4:PolicyRow { attribute :>> key="synthetic-swapped"; attribute :>> writerClass="named-only"; attribute :>> assumptions="first-retained;writer-closure;fault-equivalence;lifetime-closed;setter-events-unobservable"; attribute :>> firstExpected="false"; attribute :>> secondExpected="false"; attribute :>> scope="Assumption-only sufficient contract profile; not source or native admission"; }
part policy5:PolicyRow { attribute :>> key="synthetic-returned-error"; attribute :>> writerClass="named-only"; attribute :>> assumptions="first-retained;same-entry;writer-closure;lifetime-closed;setter-events-unobservable"; attribute :>> firstExpected="false"; attribute :>> secondExpected="false"; attribute :>> scope="Assumption-only sufficient contract profile; not source or native admission"; }
part policy6:PolicyRow { attribute :>> key="synthetic-live-capture"; attribute :>> writerClass="named-only"; attribute :>> assumptions="first-retained;same-entry;writer-closure;fault-equivalence;setter-events-unobservable"; attribute :>> firstExpected="false"; attribute :>> secondExpected="false"; attribute :>> scope="Assumption-only sufficient contract profile; not source or native admission"; }

part claim4:ClaimRow { attribute :>> key="registration"; attribute :>> mechanism="Close or version every callback producer"; attribute :>> condition="Formatter port handlers timeout dynamic denv and GC job effects remain admitted throughout output window"; attribute :>> result="Pinned data alone is insufficient for elision"; attribute :>> gap="Current source has no unified callback-policy receipt; model profile is conditional"; }
part claim5:ClaimRow { attribute :>> key="scope"; attribute :>> mechanism="Session and environment-qualified identity"; attribute :>> condition="Nested compilation shares the same compiler bindings; distinct VM isolation separately qualified"; attribute :>> result="Same symbol does not prove same resource or output operation"; attribute :>> gap="Per-VM/global layout and host binary provenance OPEN"; }

part source32:SourceRow { attribute :>> key="debug-install"; attribute :>> path="vendor/gambit/gsc/_gscdebug.scm"; attribute :>> needle="(##wr-set!"; attribute :>> obligation="Interactive compiler has a real formatter registration, not merely an API"; }
part source33:SourceRow { attribute :>> key="debug-default"; attribute :>> path="vendor/gambit/gsc/_gscdebug.scm"; attribute :>> needle="(##default-wr we"; attribute :>> obligation="Scalar/non-vector operands take default branch under stable debug bindings"; }
part source34:SourceRow { attribute :>> key="debug-restore"; attribute :>> path="vendor/gambit/gsc/_gscdebug.scm"; attribute :>> needle="(##wr-set! save-wr)"; attribute :>> obligation="Special vector branch restores global hook by normal statement, not guard"; }
part source35:SourceRow { attribute :>> key="debug-transform"; attribute :>> path="vendor/gambit/gsc/_gscdebug.scm"; attribute :>> needle="(c#parse-tree->expression obj)"; attribute :>> obligation="Special var/ptree formatting has a different effect closure"; }
part source36:SourceRow { attribute :>> key="igsc-module"; attribute :>> path="vendor/gambit/gsc/igsc.scm"; attribute :>> needle="\"_gscdebug\""; attribute :>> obligation="Interactive compiler module roster includes formatter registration"; }
part source37:SourceRow { attribute :>> key="igsc-load"; attribute :>> path="vendor/gambit/gsc/igsc.scm"; attribute :>> needle="(for-each (load-from-root \"gsc/\") gsc-modules)"; attribute :>> obligation="Roster is actually loaded before main entry"; }
part source38:SourceRow { attribute :>> key="var-predicate"; attribute :>> path="vendor/gambit/gsc/_envadt.scm"; attribute :>> needle="(define (var? x)"; attribute :>> obligation="First test is vector?; strings and integers excluded"; }
part source39:SourceRow { attribute :>> key="ptree-predicate"; attribute :>> path="vendor/gambit/gsc/_ptreeadt.scm"; attribute :>> needle="(define (ptree? obj)"; attribute :>> obligation="First test is vector?; strings and integers excluded"; }
part route7:RouteRow { attribute :>> key="igsc-debug"; attribute :>> producer="igsc loads _gscdebug"; attribute :>> dispatch="##wr hook -> var/ptree predicate -> default writer for scalar"; attribute :>> capability="Stable hook and predicate bindings, selected string/integer output"; attribute :>> status="Actual source registration; direct scalar branch excludes resource access, asynchronous effects separate"; }
part binding28:BindingRow { attribute :>> actionName="binding_observer_reentry.debugScalarPass"; attribute :>> lemma="BindingObserver.debugScalarPassPreserves"; attribute :>> scope="Conditional scalar debug branch; actual Scheme value-to-class reflection external"; }
part migration7:MigrationRow { attribute :>> key="debug-scalar"; attribute :>> producerAnchor="debug-install"; attribute :>> consumerAnchor="debug-default"; attribute :>> actionName="binding_observer_reentry.debugScalarPass"; attribute :>> lemma="BindingObserver.debugScalarPassPreserves"; }

part contract12:ContractRow { attribute :>> fromNode="igsc loader"; attribute :>> toNode="Formatter hook"; attribute :>> custody="debug registration"; }
part contract13:ContractRow { attribute :>> fromNode="Scalar predicates"; attribute :>> toNode="Capability audit"; attribute :>> custody="selected payload"; }
}
