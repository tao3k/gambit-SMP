package GambitCollectorCapability {
  private import ScalarValues::*;
  ref part delivery=GambitModernCOutcomes::collector;
  ref part comparison=GambitBaselineFailure::testGate;
  attribute scope:String="Correct the existing collector fixture's compiled-population precondition. Runtime/collector architecture, official Make/workflow names and scheduler sources stay unchanged. Single-root common behavior is tested explicitly; W<R remains a real three-root admission on an SMP-capable product.";
  attribute stage:String="Collector integration2/4 local results remains unchanged. This is a capability correction, not result3 or independent SMP advancement.99 unrelated vendor paths remain separately owned review work.";
  attribute formalDuty:String="No runtime transition or arithmetic law changes: reuse existing collector QNT and Lean evidence without writing or counting a duplicate proof. Native SysML projects capability/source/native cases into existing ASCENT case closure and five-gate policy. Local same-consumer comparison cannot discharge remote runner environment equivalence or prove failure rates.";
  attribute sourceCases:String="compiled-capability;owner-range;worker-population;shared-control;runtime-disjoint;reuse-publication";
  attribute requiredCases:String="single-root;three-root;implementation-replay-shrink;original-gsi;remaining-make;consumer-pair;products-reused";
  attribute graph:String="compiled -> single; compiled -> smp; single -> common; smp -> common; smp -> replay; common -> original; original -> audit; ci_failure -> retained; retained -> attribution; attribution -> audit; audit -> existing_pr; pending -> later_results;";
  attribute remoteBoundary:String="Linux MAX_PROCESSORS=1 ABI and macOS hosted runner remain exact-revision CI observations. Native R1 on an SMP product is not MAX_PROCESSORS=1 build qualification. Retain old macOS issue_216 second-interrupt failure; no scheduler change or retry-until-green. Same local GSI input projection proves only this fixture correction cannot alter that consumer.";
  part def Source { attribute id:String; attribute path:String; attribute anchor:String; attribute obligation:String; }
  part capability:Source { attribute :>> id="compiled-capability"; attribute :>> path="tests/root-task.scm"; attribute :>> anchor="(define (collector-integration-suite)"; attribute :>> obligation="Compile maximum and current active count are distinct. Do not call resize3 or processor1/2 when the compiled slots cannot represent that topology. Single-root path retains GC, continuation, owner cleanup, shrink and refusal checks."; }
  part owner:Source { attribute :>> id="owner-range"; attribute :>> path="tests/root-task.scm"; attribute :>> anchor="collector owner is outside the current root population"; attribute :>> obligation="Validate active owner range before evaluating ##processor or indexing native owner records."; }
  part workers:Source { attribute :>> id="worker-population"; attribute :>> path="tests/root-task.scm"; attribute :>> anchor="(collector-coherent? (collector-domain-count) count)"; attribute :>> obligation="Use actual R for coherence; W may not exceed R. R1 does not count as proof of W<R or three-root PBT."; }
  part shared:Source { attribute :>> id="shared-control"; attribute :>> path="tests/root-task.scm"; attribute :>> anchor="(define (collector-map-suite)"; attribute :>> obligation="Both topology paths share all three expected map values and six dynamic-wind entries. Existing SMP histories and shrink/replay remain executed."; }
  part disjoint:Source { attribute :>> id="runtime-disjoint"; attribute :>> path="tests/makefile.in"; attribute :>> anchor="ut ut-C:"; attribute :>> obligation="GSI test11 reads original driver/unit closure, not root-task.scm. Changed tree excludes every production source, official unit and workflow. Compare linked runtime and complete original unit inputs, not test names alone."; }
  part publication:Source { attribute :>> id="reuse-publication"; attribute :>> path="tests/root-task.scm"; attribute :>> anchor="COLLECTOR-SINGLE-ROOT-PASS"; attribute :>> obligation="Reuse only a complete producer whose qualified tree equals the published HEAD tree, then compare canonical sources, native products and generated C before mutation. Capability fixture products rebuild once; original consumer executions still occur."; }
  part def Need { ref part gate:GambitCommitGates::Gate; attribute id:String; attribute method:String; attribute artifact:String; attribute scope:String; }
  part tests:Need { ref part :>> gate=GambitCommitGates::tests; attribute :>> id="CAPABILITY-NATIVE"; attribute :>> method="native"; attribute :>> artifact="evidence/research/retained/modern-c/collector-capability-publication/receipt.json"; attribute :>> scope="Same profile/cache, original408 GSI cases and full remaining Make, explicit R1 common cases and R3/W1,2,3 PBT with serialized replay/shrink. Existing production identity reused; remote MAX1 ABI remains asynchronous CI."; }
  part learning:Need { ref part :>> gate=GambitCommitGates::learning; attribute :>> id="CAPABILITY-LEARNING"; attribute :>> method="source-analysis"; attribute :>> artifact="dev/refactoring/modern-c/collector-capability.org"; attribute :>> scope="Compiled capacity, active roots and workers are separate; failed resize assumptions must not select unchecked owner addresses. No runtime performance claim."; }
  part process:Need { ref part :>> gate=GambitCommitGates::process; attribute :>> id="CAPABILITY-PROCESS"; attribute :>> method="source-analysis"; attribute :>> artifact="dev/refactoring/modern-c/collector-capability.org"; attribute :>> scope="Scope is fixture correction;2/4 main results and1/12 independent SMP unchanged.99 vendor residual paths remain owned by SysML and source/version receipts."; }
  part models:Need { ref part :>> gate=GambitCommitGates::models; attribute :>> id="CAPABILITY-MODELS"; attribute :>> method="source-refinement"; attribute :>> artifact="evidence/research/retained/modern-c/collector-capability-publication/case-closure.json"; attribute :>> scope="Actual SysML source/native requirements drive ASCENT and missing-case controls. No new runtime QNT or Lean proof is needed for a fixture-only topology precondition."; }
  part questions:Need { ref part :>> gate=GambitCommitGates::questions; attribute :>> id="CAPABILITY-QUESTIONS"; attribute :>> method="source-analysis"; attribute :>> artifact="dev/refactoring/modern-c/collector-capability.org"; attribute :>> scope="Why not skip collector entirely? Why is local R1 not single-processor ABI proof? Why is issue216 retained? How does the shared continuation test amplify Gambit's frame semantics without changing them?"; }
}
