package GambitHeaderBuildAudit {
 private import ScalarValues::*;
 attribute scope:String="Complete single-inventory header-build evidence and CI tool/fixture identity correction. No runtime changes, extra executor, source-copy generation or independent SMP-family promotion.";
 attribute stage:String="header-build-complete";
 attribute formalDuty:String="Native OpenSysML SDK resolves the four build owners; ASCENT binds exact selected framework tests and the admitted vendor source. Existing QNT schedules and Lean frame/ownership laws keep distinct duties without duplication.";
 part submission:GambitCommitGates::SubmissionUnit {
  attribute :>> kind="support"; attribute :>> result=""; attribute :>> progressDelta=0;
  attribute :>> supportPaths=".github/actions/framework/action.yml;.github/workflows/gambit.yml;.github/workflows/verify.yml;dev/modeling/models/sysml/commit-gates.sysml;dev/refactoring/modern-c/branch-checklist.org;dev/refactoring/modern-c/header-build.d2;dev/refactoring/modern-c/header-build.org;dev/refactoring/modern-c/models/sysml/header-build-audit.sysml;dev/refactoring/modern-c/models/sysml/header-build.sysml;evidence/research/retained/modern-c/header-build/ci-failures.json;evidence/research/retained/modern-c/header-build/counterexamples.json;evidence/research/retained/modern-c/header-build/framework-validation.json;evidence/research/retained/modern-c/header-build/model-binding.json;evidence/research/retained/modern-c/header-build/native.json;evidence/research/retained/modern-c/header-build/source-refinement.json;evidence/research/retained/modern-c/header-build/vendor-matrix.json;evidence/research/retained/modern-c/header-build/vendor-observations.json;evidence/research/retained/modern-c/header-build/vendor-submission/admission.json;evidence/research/retained/modern-c/header-build/vendor-submission/comment.json;evidence/research/retained/modern-c/header-build/vendor-submission/model-contract.json;evidence/research/retained/modern-c/header-build/vendor-submission/revision.json;evidence/research/retained/modern-c/header-build/vendor-submission/source-manifest.json;evidence/research/retained/modern-c/header-build/vendor-submission/source.json;src/gambit_smp/header_organization.py;tests/test_ci_tool_identity.py;tests/test_header_organization.py;tests/test_revision_matrix.py;tests/test_revision_submission.py;tests/test_stress_inventory.py";
  attribute :>> testModules="tests/test_header_organization.py;tests/test_stress_inventory.py;tests/test_ci_tool_identity.py;tests/test_revision_submission.py;tests/test_revision_matrix.py";
 }
 part def Need { ref part gate:GambitCommitGates::Gate; attribute id:String; attribute method:String; attribute artifact:String; attribute scope:String; }
 part tests:Need { ref part :>> gate=GambitCommitGates::tests; attribute :>> id="HEADER-AUDIT-TESTS"; attribute :>> method="native"; attribute :>> artifact="evidence/research/retained/modern-c/header-build/framework-validation.json"; attribute :>> scope="Exact selected whole test consumers finish with zero skips; preserve all stress inventory assertions. Separate native15-check campaign, recovered products and retained failures."; }
 part learning:Need { ref part :>> gate=GambitCommitGates::learning; attribute :>> id="HEADER-AUDIT-LEARNING"; attribute :>> method="source-analysis"; attribute :>> artifact="dev/refactoring/modern-c/header-build.org"; attribute :>> scope="One existing manifest drives all build consumers; one Make publisher preserves content timestamps. Separate build work savings from unmeasured runtime efficiency."; }
 part process:Need { ref part :>> gate=GambitCommitGates::process; attribute :>> id="HEADER-AUDIT-PROCESS"; attribute :>> method="source-analysis"; attribute :>> artifact="dev/refactoring/modern-c/branch-checklist.org"; attribute :>> scope="Keep four accepted SMP families and eight open. Exclude pending runtime, Recipe relocation, publication-storage and scheduler proposals."; }
 part models:Need { ref part :>> gate=GambitCommitGates::models; attribute :>> id="HEADER-AUDIT-MODELS"; attribute :>> method="native"; attribute :>> artifact="evidence/research/retained/modern-c/header-build/model-binding.json"; attribute :>> scope="Strict pinned OpenSysML Python SDK resolves all four owners; source-bound vendor admission and existing ASCENT gates/rejection controls. No duplicate QNT/Lean."; }
 part questions:Need { ref part :>> gate=GambitCommitGates::questions; attribute :>> id="HEADER-AUDIT-QUESTIONS"; attribute :>> method="source-analysis"; attribute :>> artifact="dev/refactoring/modern-c/header-build.org"; attribute :>> scope="Explain unchanged payload and multi-shot/GC semantics, failures, source/profile equality, net build work, added fixed costs and unmeasured/remote boundaries."; }
}
