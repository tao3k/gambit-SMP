package GambitBootstrapArtifactCustody {
  private import ScalarValues::*;
  ref part orderedWord:GambitOrderedSynchronization::Responsibility=GambitOrderedSynchronization::word;
  ref part gcStop:GambitOrderedSynchronization::Responsibility=GambitOrderedSynchronization::stop;
  attribute sourceLock:String="evidence/research/ordered-sync/initialization/source.lock.json";
  attribute profile:String="evidence/fixtures/gerbil-bazel-build-profile/profile.json";
  attribute recipe:String="evidence/research/bootstrap-artifact-custody/journal-bootstrap.recipe.json";
  attribute scope:String="Darwin/GCC modern-C synchronization and immutable bootstrap artifact boundary; no full0-12 SMP, unknown-owner recovery or other-platform release admission";
  attribute formalBoundary:String="No new QNT/Lean. Existing continuation schedule/permit histories and issued-view algebra retain their owners. Artifact source refinement, adverse real-filesystem tests, exact producer receipts and native Scheme tests deliver distinct evidence";
  attribute wholeBudget:Integer=600;
  attribute targetPasses:Integer=2;
  part def Component { attribute id:String; attribute source:String; attribute anchor:String; attribute invariant:String; attribute retirement:String; attribute cost:String; }
  part input:Component { attribute :>> id="compiler-input"; attribute :>> source="src/gambit_smp/bootstrap_artifacts.py"; attribute :>> anchor="def qualified_host"; attribute :>> invariant="Actual completed host receipt and child/identity hashes bind the complete current Scheme generator graph. Compiler-only identity contains no target GSI/library assertion"; attribute :>> retirement="Extra target seed core before standard two target passes"; attribute :>> cost="Host/source/configuration hashing; no target runtime inherited or target pass skipped"; }
  part retained:Component { attribute :>> id="completed-snapshot"; attribute :>> source="src/gambit_smp/bootstrap_artifacts.py"; attribute :>> anchor="def preserve"; attribute :>> invariant="Source and copy identities match before publishing completion. No hardlinks. Partial copy, drift or missing preservation receipt grants no completed authority"; attribute :>> retirement="Completed seed and bootstrap outputs aliasing mutable rebuild inputs"; attribute :>> cost="APFS COW or explicit byte-copy fallback plus bounded metadata and hash work; no claimed peak-RSS saving"; }
  part workspace:Component { attribute :>> id="private-rebuild"; attribute :>> source="src/gambit_smp/native_capabilities.py"; attribute :>> anchor="def clone"; attribute :>> invariant="Destructive bootstrap always gets a private registered generation; completed runtime consumers never mutate the producer. Changed private generations require explicit recovery"; attribute :>> retirement="In-place policy conflating completed artifact ownership with working-tree ownership"; attribute :>> cost="One role/content-bound registered generation per input; no attempt-directory source escape"; }
  part routing:Component { attribute :>> id="exact-routing"; attribute :>> source="src/gambit_smp/workspace.py"; attribute :>> anchor="def validate_build_derivation"; attribute :>> invariant="Same compiler, flags and environment plus role and input digest determine storage identity. Existing actual task and workspace lease checks remain mandatory"; attribute :>> retirement="Treating a path or generic state inventory as a backup or successful producer"; attribute :>> cost="Small derivation record; stale/partial products fail closed"; }
  part build:Component { attribute :>> id="two-target-passes"; attribute :>> source="vendor/gambit/makefile.in"; attribute :>> anchor="from-scratch: fake_target"; attribute :>> invariant="Existing Make from-scratch must complete both phase1..phase4 passes. Seven announcements or a completed source seed cannot become a bootstrap seal"; attribute :>> retirement="One redundant target build, no semantic pass or original deadline removed"; attribute :>> cost="Two complete target source builds remain; whole600, existing step limits and no heap override"; }
  part reuse:Component { attribute :>> id="producer-consumption"; attribute :>> source="src/gambit_smp/completed_producer.py"; attribute :>> anchor="def bootstrap_ancestry"; attribute :>> invariant="Compiler-only ancestry is distinct from target seed ancestry; only actual complete two-pass output can issue a reusable runtime proof. Source/profile/toolchain drift refuses reuse"; attribute :>> retirement="Recompilation merely to recover an existing exact completed target"; attribute :>> cost="Original expenditures and identities retained; reused output is not fresh native execution"; }
  part def Transfer { ref part origin:Component; ref part destination:Component; attribute condition:String; }
  part hostBinding:Transfer { ref part :>> origin=input; ref part :>> destination=workspace; attribute :>> condition="Qualified generator host prepares only a bootstrap input; full target ABI is rebuilt"; }
  part isolate:Transfer { ref part :>> origin=retained; ref part :>> destination=workspace; attribute :>> condition="Checked copy and actual lease precede destructive bootclean; producer remains intact"; }
  part actualBuild:Transfer { ref part :>> origin=workspace; ref part :>> destination=build; attribute :>> condition="Same profile and original whole/step budgets; no pre-target-seed build"; }
  part complete:Transfer { ref part :>> origin=build; ref part :>> destination=retained; attribute :>> condition="Actual exit0, quiescence, full phase inventory and source stability precede preserved completed output"; }
  part consume:Transfer { ref part :>> origin=retained; ref part :>> destination=reuse; attribute :>> condition="Exact source/configuration/toolchain/producer identity authorizes use; no success inferred from directory existence"; }
  part def Obligation { attribute id:String; attribute method:String; attribute criterion:String; }
  part source:Obligation { attribute :>> id="source-contract"; attribute :>> method="source-refinement"; attribute :>> criterion="Real source constructors, guards, destructive consumers and retired third-build boundary accounted"; }
  part adverse:Obligation { attribute :>> id="artifact-custody"; attribute :>> method="filesystem-and-typing-tests"; attribute :>> criterion="Real lease, independent snapshot, deletion/drift/partial transfer, host mismatch and semantic misuse refusal"; }
  part budgets:Obligation { attribute :>> id="unchanged-limits"; attribute :>> method="declaration-comparison"; attribute :>> criterion="Original profile, whole600 and all surviving stage/fixture limits; failures retained"; }
  part bootstrap:Obligation { attribute :>> id="complete-bootstrap"; attribute :>> method="native-two-pass"; attribute :>> criterion="Exact source, actual both phase1..4 passes, exit0, reaped/quiescent, preserved output"; }
  part gc:Obligation { attribute :>> id="gc-mailbox-stop"; attribute :>> method="native-scheme"; attribute :>> criterion="Four blocked senders, held mailbox permit through actual GC,128 shared messages; current target"; }
  part map:Obligation { attribute :>> id="map-multishot"; attribute :>> method="native-scheme"; attribute :>> criterion="Current target map continuation captured and restored repeatedly, wide roots and GC; full shared multi-shot semantics"; }
  part suite:Obligation { attribute :>> id="named-suite"; attribute :>> method="native-thirteen-lanes"; attribute :>> criterion="Current-source independent namespaces and receipts, including dynamic-wind and ownership kernels; remote CI separate"; }
  part exactReuse:Obligation { attribute :>> id="exact-reuse"; attribute :>> method="native-producer-consumption"; attribute :>> criterion="Source-bound completed producer actually consumed with original expenditure, no bootstrap rerun; wrong identity refuses"; }
  part def Gate { attribute id:String; attribute criterion:String; }
  part tests:Gate { attribute :>> id="tests"; attribute :>> criterion="All scoped obligations delivered; no timeout or partial receipt promoted"; }
  part architecture:Gate { attribute :>> id="architecture"; attribute :>> criterion="Completed artifacts separated from working state, two target passes retained; ordered mailbox/GC boundaries explained"; }
  part process:Gate { attribute :>> id="process"; attribute :>> criterion="Stage names and exact source evidence identify implemented versus open responsibilities and legacy retirement"; }
  part models:Gate { attribute :>> id="models"; attribute :>> criterion="Native SysML drives actual ASCENT requirements; QNT/Lean remain unchanged and nonduplicated"; }
  part questions:Gate { attribute :>> id="questions"; attribute :>> criterion="Gambit tail calls, shared values, full multi-shot continuation and physical GC stop preserved and exercised; unsupported migration/owner-death not claimed"; }
}
