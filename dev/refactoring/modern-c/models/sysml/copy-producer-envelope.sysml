package GambitCopyProducerEnvelope { private import ScalarValues::*;
part def SourceRow { attribute key:String; attribute path:String; attribute needle:String; attribute obligation:String; }
part source0:SourceRow { attribute :>> key="validated-fs"; attribute :>> path="vendor/gambit/gsc/_t-c-3.scm"; attribute :>> needle="(integer? fs) (exact? fs) (<= 0 fs) (< fs 16384)"; attribute :>> obligation="Stored-size check is active in constructor, unlike unused 4096 declaration"; }
part source1:SourceRow { attribute :>> key="mutable-spec"; attribute :>> path="vendor/gambit/gsc/_t-c-3.scm"; attribute :>> needle="(vector 'frame-spec kind fs actual-fs link gc-map out-of-line?)"; attribute :>> obligation="Returned Scheme vector is mutable; emission needs private sealed view"; }
part source2:SourceRow { attribute :>> key="effective-fs"; attribute :>> path="vendor/gambit/gsc/_t-c-3.scm"; attribute :>> needle="(define (targ-internal-fs fs)"; attribute :>> obligation="Producer computes aligned stored size plus saved-register layout"; }
part source3:SourceRow { attribute :>> key="link-map"; attribute :>> path="vendor/gambit/gsc/_t-c-3.scm"; attribute :>> needle="(< gc-map (expt 2 actual-fs))"; attribute :>> obligation="Bounds root-map integer but not module/native root coverage"; }
part source4:SourceRow { attribute :>> key="wrappers"; attribute :>> path="vendor/gambit/gsc/_t-c-2.scm"; attribute :>> needle="(targ-make-frame-spec 'internal fs link gc-map)"; attribute :>> obligation="Actual internal-label constructor path"; }
part source5:SourceRow { attribute :>> key="liveness"; attribute :>> path="vendor/gambit/gsc/_t-c-2.scm"; attribute :>> needle="all saved GVM regs are live"; attribute :>> obligation="RETI generation constructs physical saved-register root map"; }
part source6:SourceRow { attribute :>> key="emit"; attribute :>> path="vendor/gambit/gsc/_t-c-1.scm"; attribute :>> needle="(fs (targ-frame-spec-stored-fs info))"; attribute :>> obligation="Emitter consumes stored frame size from retained spec"; }
part source7:SourceRow { attribute :>> key="ofd"; attribute :>> path="vendor/gambit/include/gambit.h.in"; attribute :>> needle="#define ___OFD_FS_WIDTH 14"; attribute :>> obligation="Native packed descriptor matches checked stored-size field"; }
part source8:SourceRow { attribute :>> key="decode"; attribute :>> path="vendor/gambit/include/gambit.h.in"; attribute :>> needle="frame.fs = internal ? ___RETI_CFS_TO_FS(frame.stored_fs) : frame.stored_fs;"; attribute :>> obligation="Consumer expands internal layout exactly once"; }
part source9:SourceRow { attribute :>> key="runtime-reti"; attribute :>> path="vendor/gambit/include/gambit.h.in"; attribute :>> needle="#define ___RETI_CFS_TO_FS(fs)"; attribute :>> obligation="Consumer depends on native register count and alignment"; }
part source10:SourceRow { attribute :>> key="source-span"; attribute :>> path="vendor/gambit/include/gambit.h.in"; attribute :>> needle="#define ___FRAME_SPACE(n)"; attribute :>> obligation="Rounded physical frame charge differs from copied fs plus two"; }
part source11:SourceRow { attribute :>> key="push"; attribute :>> path="vendor/gambit/lib/_kernel.scm"; attribute :>> needle="___PUSH_REGS /* push all GVM registers (live or not) */"; attribute :>> obligation="Three handler producers save native registers"; }
part source12:SourceRow { attribute :>> key="align-push"; attribute :>> path="vendor/gambit/lib/_kernel.scm"; attribute :>> needle="___ADJFP(___ROUND_TO_MULT(fs,___FRAME_ALIGN)-fs)"; attribute :>> obligation="Padding produced before saved registers"; }
part source13:SourceRow { attribute :>> key="captured"; attribute :>> path="vendor/gambit/lib/mem.c"; attribute :>> needle="words = fs + ___FRAME_EXTRA_SLOTS;"; attribute :>> obligation="Captured-frame copy grant has one extra slot plus object header"; }
part source14:SourceRow { attribute :>> key="frame-header"; attribute :>> path="vendor/gambit/lib/mem.c"; attribute :>> needle="#error \"___SUBTYPED_BODY != 1\""; attribute :>> obligation="Captured path explicitly excludes handle body layout"; }
part source15:SourceRow { attribute :>> key="frame-forward"; attribute :>> path="vendor/gambit/lib/mem.c"; attribute :>> needle="___FP_SET_STK(fp,link+1,forw)"; attribute :>> obligation="Canonical frame forwarding must support one source charge"; }
part source16:SourceRow { attribute :>> key="inline-guard"; attribute :>> path="vendor/gambit/lib/_kernel.scm"; attribute :>> needle="if (words > ___MSECTION_BIGGEST)"; attribute :>> obligation="Dynamic constructor-family split is not a global ordinary-object bound"; }
part source17:SourceRow { attribute :>> key="runtime-frame"; attribute :>> path="vendor/gambit/lib/_kernel.scm"; attribute :>> needle="___ALLOC_SCMOBJ_INLINE(FRAME, ___WORD, n, 0);"; attribute :>> obligation="make-frame producer follows inline/still split and descriptor-derived length"; }
part source18:SourceRow { attribute :>> key="temporary"; attribute :>> path="vendor/gambit/lib/_kernel.scm"; attribute :>> needle="___BEGIN_ALLOC_VECTOR(np)"; attribute :>> obligation="Rest and keyword-rest temporary roots bypass generic small-family split"; }
part source19:SourceRow { attribute :>> key="np"; attribute :>> path="vendor/gambit/include/gambit.h.in"; attribute :>> needle="#define ___NBPARMS_WIDTH 12"; attribute :>> obligation="Decoded temporary argument-vector np is below 4096"; }
part source20:SourceRow { attribute :>> key="static-vector"; attribute :>> path="vendor/gambit/gsc/_t-c-2.scm"; attribute :>> needle="(targ-c-unsigned-long n)))"; attribute :>> obligation="Static generator lengths must be enumerated per operation and module"; }
part source21:SourceRow { attribute :>> key="vector-generator"; attribute :>> path="vendor/gambit/gsc/_t-c-2.scm"; attribute :>> needle="(define (targ-apply-vector proc-safe? kind)"; attribute :>> obligation="Literal arity controls emitted allocation; no 255 branch in this emitter"; }
part source22:SourceRow { attribute :>> key="closure-generator"; attribute :>> path="vendor/gambit/gsc/_t-c-2.scm"; attribute :>> needle="(list \"ALLOC_CLO\" (targ-c-unsigned-long (length opnds)))"; attribute :>> obligation="Closure capture count is another static producer"; }
part source23:SourceRow { attribute :>> key="closure-native"; attribute :>> path="vendor/gambit/include/gambit.h.in"; attribute :>> needle="#define ___CLO_FREEVARS (1+___CLO_LOWLEVEL_TRAMPOLINE_SIZE)"; attribute :>> obligation="Include lowlevel trampoline and native header when computing G"; }
part source24:SourceRow { attribute :>> key="heap-check"; attribute :>> path="vendor/gambit/gsc/_t-c-2.scm"; attribute :>> needle="(targ-update-fr-and-check-heap space sn)"; attribute :>> obligation="Safepoint accounting is not a per-object still-allocation decision"; }
part source25:SourceRow { attribute :>> key="flonum"; attribute :>> path="vendor/gambit/include/gambit.h.in"; attribute :>> needle="#define ___MEM_ALLOCATED_FLONUM_ALLOC(val)"; attribute :>> obligation="Boxing materialization versus self-tagged/NAN profile changes coverage"; }
part source26:SourceRow { attribute :>> key="weak-object"; attribute :>> path="vendor/gambit/lib/_system.scm"; attribute :>> needle="if (words > ___MSECTION_BIGGEST)"; attribute :>> obligation="GC hash table constructor has its own size/heap/still policy"; }
part source27:SourceRow { attribute :>> key="bignum"; attribute :>> path="vendor/gambit/lib/_num.scm"; attribute :>> needle="if (words > ___MSECTION_BIGGEST)"; attribute :>> obligation="Bignum constructor has base-width and alignment-specific policy"; }
part source28:SourceRow { attribute :>> key="origin"; attribute :>> path="vendor/gambit/lib/mem.c"; attribute :>> needle="GC copy source is not in frozen fromspace"; attribute :>> obligation="Header origin alone does not prove body range or a source partition"; }
part source29:SourceRow { attribute :>> key="census"; attribute :>> path="vendor/gambit/lib/mem.c"; attribute :>> needle="#define words_movable_objs(ps)"; attribute :>> obligation="Factor-two accounting does not establish unique physical Q"; }
part source30:SourceRow { attribute :>> key="threshold"; attribute :>> path="vendor/gambit/lib/mem.c"; attribute :>> needle="alloc_heap_chunk_limit = work->context->mem.alloc_heap_ptr_ + ___MSECTION_CHUNK;"; attribute :>> obligation="Threshold overhead must share the same nonrefundable source envelope"; }
part source31:SourceRow { attribute :>> key="regs-profile"; attribute :>> path="vendor/gambit/gsc/_t-c-1.scm"; attribute :>> needle="nb-gvm-regs <= ___NB_GVM_REGS"; attribute :>> obligation="Existing option relation is weaker than matched producer/consumer effective-layout receipt"; }
part def InventoryRow { attribute key:String; attribute path:String; attribute pattern:String; attribute count:String; attribute scope:String; }
part inventory0:InventoryRow { attribute :>> key="inline-family"; attribute :>> path="vendor/gambit/lib/_kernel.scm"; attribute :>> pattern="^___ALLOC_SCMOBJ_INLINE\\("; attribute :>> count="16"; attribute :>> scope="Lexical invocation inventory; macro definition excluded; no external native closure"; }
part inventory1:InventoryRow { attribute :>> key="temporary-vectors"; attribute :>> path="vendor/gambit/lib/_kernel.scm"; attribute :>> pattern="___BEGIN_ALLOC_VECTOR\\(np\\)"; attribute :>> count="2"; attribute :>> scope="Rest and keyword-rest producer blocks only"; }
part inventory2:InventoryRow { attribute :>> key="native-reti"; attribute :>> path="vendor/gambit/lib/_kernel.scm"; attribute :>> pattern="/\\* setup internal return continuation frame \\*/"; attribute :>> count="3"; attribute :>> scope="Stack-limit heap-limit force blocks only"; }
part inventory3:InventoryRow { attribute :>> key="typed-return-wrappers"; attribute :>> path="vendor/gambit/gsc/_t-c-2.scm"; attribute :>> pattern="\\(targ-make-frame-spec '(?:normal|task|internal)"; attribute :>> count="3"; attribute :>> scope="Local return-label wrappers; raw native/manual metadata outside closure"; }
part def ClaimRow { attribute key:String; attribute mechanism:String; attribute condition:String; attribute result:String; attribute gap:String; }
part claim0:ClaimRow { attribute :>> key="frame-cap"; attribute :>> mechanism="Active stored-size validation plus expanded RETI arithmetic"; attribute :>> condition="Unmodified spec; supported body1 alignment4 reserve3 and matched ABI"; attribute :>> result="Normal/task <=16385; default five-reg RETI <=16395; <=25-reg RETI <=16415"; attribute :>> gap="Accepted-range bounds, not emitted maxima or all native frame producers"; }
part claim1:ClaimRow { attribute :>> key="ordinary-cap"; attribute :>> mechanism="Separate guarded dynamic and emitted static/native constructors"; attribute :>> condition="Per-constructor ObjectSpec incl bytes header padding trampoline and completion"; attribute :>> result="Small family <=255 on 64-bit, conservatively <=256 on 32-bit; static max is per module"; attribute :>> gap="No universal 255 theorem; unsafe raw C and unknown aliases route to alternative"; }
part claim2:ClaimRow { attribute :>> key="B"; attribute :>> mechanism="Canonical physical source charges + alignment + threshold count"; attribute :>> condition="Identity keyed by allocation/epoch/physical offset, not descriptor spelling; complete old source"; attribute :>> result="B>=U+T; frame destination strictly smaller than full rounded stack source"; attribute :>> gap="Source writer/alias partition, newer VM resize-request roots and all-phase charge injection still open"; }
part claim3:ClaimRow { attribute :>> key="issuer"; attribute :>> mechanism="Scheme generator seals validated FrameSpec; runtime combines profiles and source epoch"; attribute :>> condition="Independent object/root/source witnesses and all live old-module descriptors"; attribute :>> result="FrameSpec signs local size/layout witness, not whole VM capacity by itself"; attribute :>> gap="Native relocation, post-validation mutation and unknown modules prevent tight admission"; }
part claim4:ClaimRow { attribute :>> key="reuse"; attribute :>> mechanism="Retain immutable producer summaries across builds and GC rounds"; attribute :>> condition="Bind generator source, ABI, module identity and constructor manifest"; attribute :>> result="Reuse size maxima and root layouts; recompute frozen source occupancy each round"; attribute :>> gap="Summary invalidation and old-code retirement remain mandatory"; }
part def MemoryRow { attribute key:String; attribute publication:String; attribute consumer:String; attribute gap:String; }
part memory0:MemoryRow { attribute :>> key="seal"; attribute :>> publication="Complete immutable/private view before release publication"; attribute :>> consumer="Emitter/native loader acquires exact identity and ABI"; attribute :>> gap="A mutable Scheme vector is not the sealed record"; }
part memory1:MemoryRow { attribute :>> key="old-module"; attribute :>> publication="Pin all descriptors reachable from live frames before snapshot"; attribute :>> consumer="Module summaries retired only after continuation/frame/maintenance users"; attribute :>> gap="Unloaded public entry does not imply descriptor dead"; }
part memory2:MemoryRow { attribute :>> key="source"; attribute :>> publication="Root writers close before validating physical source coverage"; attribute :>> consumer="GC updates root values under existing authority; control endpoints remain frozen"; attribute :>> gap="Lease/root publication plus C11 adapters still open"; }
part memory3:MemoryRow { attribute :>> key="activation"; attribute :>> publication="New module or raw native producer cannot enter frozen scope"; attribute :>> consumer="Before-copy change revokes receipt; during-copy activation deferred"; attribute :>> gap="No use of a stale lower G after activation"; }
part memory4:MemoryRow { attribute :>> key="budget"; attribute :>> publication="Strong-to-weak preserves U/B/source identities and spent credit"; attribute :>> consumer="Forwarding losers reclaim private reservation without refunding canonical committed charge"; attribute :>> gap="All-source native uniqueness and marker mapping remain open"; }
part def GainRow { attribute key:String; attribute avoided:String; attribute added:String; attribute condition:String; }
part gain0:GainRow { attribute :>> key="active-check"; attribute :>> avoided="Replace unproved reliance on unused 4096/8192 macros"; attribute :>> added="Per-label semantic and layout validation; private emission snapshot"; attribute :>> condition="Current active 14-bit constructor check supports local arithmetic only"; }
part gain1:GainRow { attribute :>> key="module-summary"; attribute :>> avoided="Avoid rescanning every old descriptor for each GC"; attribute :>> added="Maintain maxima and constructor coverage for every still-live module"; attribute :>> condition="Costs amortize only with exact ABI/invalidation and old-code pins"; }
part gain2:GainRow { attribute :>> key="ordinary-spec"; attribute :>> avoided="Use actual static object/closure maxima instead of generic half-section cap"; attribute :>> added="New ObjectSpec inventory and native producer maintenance"; attribute :>> condition="No benefit if any live producer lacks a finite qualified cap"; }
part gain3:GainRow { attribute :>> key="source-envelope"; attribute :>> avoided="Reuse producer charge lemmas while freezing actual source Q"; attribute :>> added="Root/alias/extent witness and threshold accounting per GC"; attribute :>> condition="FrameSpec alone cannot issue B"; }
part gain4:GainRow { attribute :>> key="retirement"; attribute :>> avoided="Retire repeated C layout interpretation and manual duplicated bounds"; attribute :>> added="Generated C and runtime must consume the same sealed semantic record"; attribute :>> condition="No runtime path retired by this research; Zig not required"; }
part def ContractRow { attribute fromNode:String; attribute toNode:String; attribute custody:String; }
part contract0:ContractRow { attribute :>> fromNode="semantic-FrameSpec"; attribute :>> toNode="private-emission-view"; attribute :>> custody="Validate stored actual link root-map and full ABI; exclude mutable aliases"; }
part contract1:ContractRow { attribute :>> fromNode="private-emission-view"; attribute :>> toNode="frame-size-witness"; attribute :>> custody="Reconcile stored encoding with native RETI reconstruction"; }
part contract2:ContractRow { attribute :>> fromNode="ObjectSpec"; attribute :>> toNode="ordinary-size-witness"; attribute :>> custody="Enumerate guarded static closure temporary and boxing producers"; }
part contract3:ContractRow { attribute :>> fromNode="old-module-pins"; attribute :>> toNode="profile-union"; attribute :>> custody="Keep descriptors from live older continuations in the maximum"; }
part contract4:ContractRow { attribute :>> fromNode="frame-size-witness"; attribute :>> toNode="profile-union"; attribute :>> custody="Use actual effective fs plus captured header/extra slot"; }
part contract5:ContractRow { attribute :>> fromNode="ordinary-size-witness"; attribute :>> toNode="profile-union"; attribute :>> custody="No global 255 shortcut; raw producers require their own scope"; }
part contract6:ContractRow { attribute :>> fromNode="profile-union"; attribute :>> toNode="G-receipt"; attribute :>> custody="All live producer families covered; ABI and generation agree"; }
part contract7:ContractRow { attribute :>> fromNode="frozen-source"; attribute :>> toNode="B-receipt"; attribute :>> custody="Disjoint canonical physical Q plus alignment and nonrefundable threshold charge"; }
part contract8:ContractRow { attribute :>> fromNode="G-receipt"; attribute :>> toNode="capacity-receipt"; attribute :>> custody="Use prior contiguous packing theorem with actual G"; }
part contract9:ContractRow { attribute :>> fromNode="B-receipt"; attribute :>> toNode="capacity-receipt"; attribute :>> custody="Use same source epoch across strong and weak phases"; }
part contract10:ContractRow { attribute :>> fromNode="capacity-receipt"; attribute :>> toNode="copy-entry"; attribute :>> custody="Start only with current signed scopes and all old modules pinned"; }
part contract11:ContractRow { attribute :>> fromNode="profile-change"; attribute :>> toNode="alternative-or-defer"; attribute :>> custody="Revoke before start; defer activation after start; keep old roots"; }
part def BindingRow { attribute actionName:String; attribute lemma:String; attribute scope:String; }
part binding0:BindingRow { attribute :>> actionName="copy_producer_envelope.coverObjects"; attribute :>> lemma="ProducerEnvelope.coverObjectsPreserves"; attribute :>> scope="Actual typed-IR action preservation; witness realization remains source obligation"; }
part binding1:BindingRow { attribute :>> actionName="copy_producer_envelope.coverFrames"; attribute :>> lemma="ProducerEnvelope.coverFramesPreserves"; attribute :>> scope="Actual typed-IR action preservation; witness realization remains source obligation"; }
part binding2:BindingRow { attribute :>> actionName="copy_producer_envelope.chooseCap"; attribute :>> lemma="ProducerEnvelope.chooseCapPreserves"; attribute :>> scope="Actual typed-IR action preservation; witness realization remains source obligation"; }
part binding3:BindingRow { attribute :>> actionName="copy_producer_envelope.abiMismatch"; attribute :>> lemma="ProducerEnvelope.abiMismatchPreserves"; attribute :>> scope="Actual typed-IR action preservation; witness realization remains source obligation"; }
part binding4:BindingRow { attribute :>> actionName="copy_producer_envelope.opaqueProducer"; attribute :>> lemma="ProducerEnvelope.opaqueProducerPreserves"; attribute :>> scope="Actual typed-IR action preservation; witness realization remains source obligation"; }
part binding5:BindingRow { attribute :>> actionName="copy_producer_envelope.missingOldModule"; attribute :>> lemma="ProducerEnvelope.missingOldModulePreserves"; attribute :>> scope="Actual typed-IR action preservation; witness realization remains source obligation"; }
part binding6:BindingRow { attribute :>> actionName="copy_producer_envelope.missingSourceWitness"; attribute :>> lemma="ProducerEnvelope.missingSourceWitnessPreserves"; attribute :>> scope="Actual typed-IR action preservation; witness realization remains source obligation"; }
part binding7:BindingRow { attribute :>> actionName="copy_producer_envelope.freeze64"; attribute :>> lemma="ProducerEnvelope.freeze64Preserves"; attribute :>> scope="Actual typed-IR action preservation; witness realization remains source obligation"; }
part binding8:BindingRow { attribute :>> actionName="copy_producer_envelope.freeze32"; attribute :>> lemma="ProducerEnvelope.freeze32Preserves"; attribute :>> scope="Actual typed-IR action preservation; witness realization remains source obligation"; }
part binding9:BindingRow { attribute :>> actionName="copy_producer_envelope.issue"; attribute :>> lemma="ProducerEnvelope.issuePreserves"; attribute :>> scope="Actual typed-IR action preservation; witness realization remains source obligation"; }
part binding10:BindingRow { attribute :>> actionName="copy_producer_envelope.start"; attribute :>> lemma="ProducerEnvelope.startPreserves"; attribute :>> scope="Actual typed-IR action preservation; witness realization remains source obligation"; }
part binding11:BindingRow { attribute :>> actionName="copy_producer_envelope.consume"; attribute :>> lemma="ProducerEnvelope.consumePreserves"; attribute :>> scope="Actual typed-IR action preservation; witness realization remains source obligation"; }
part binding12:BindingRow { attribute :>> actionName="copy_producer_envelope.weakCut"; attribute :>> lemma="ProducerEnvelope.weakCutPreserves"; attribute :>> scope="Actual typed-IR action preservation; witness realization remains source obligation"; }
part binding13:BindingRow { attribute :>> actionName="copy_producer_envelope.deferLateModule"; attribute :>> lemma="ProducerEnvelope.deferLateModulePreserves"; attribute :>> scope="Actual typed-IR action preservation; witness realization remains source obligation"; }
part binding14:BindingRow { attribute :>> actionName="copy_producer_envelope.replaceBeforeStart"; attribute :>> lemma="ProducerEnvelope.replaceBeforeStartPreserves"; attribute :>> scope="Actual typed-IR action preservation; witness realization remains source obligation"; }
part def ProofRow { attribute key:String; attribute lemma:String; }
part proof0:ProofRow { attribute :>> key="normal-span"; attribute :>> lemma="ProducerCapacity.normalCapturedFits"; }
part proof1:ProofRow { attribute :>> key="internal-span"; attribute :>> lemma="ProducerCapacity.internalSpanExact"; }
part proof2:ProofRow { attribute :>> key="internal-copy"; attribute :>> lemma="ProducerCapacity.internalCapturedFits"; }
part proof3:ProofRow { attribute :>> key="normal-cap"; attribute :>> lemma="ProducerCapacity.normalStoredCap"; }
part proof4:ProofRow { attribute :>> key="default-reti"; attribute :>> lemma="ProducerCapacity.defaultInternalCap"; }
part proof5:ProofRow { attribute :>> key="supported-reti"; attribute :>> lemma="ProducerCapacity.supportedRegisterCap"; }
part proof6:ProofRow { attribute :>> key="abi-counter"; attribute :>> lemma="ProducerCapacity.abiMismatchIsReal"; }
part proof7:ProofRow { attribute :>> key="layout-equivalence"; attribute :>> lemma="ProducerCapacity.producerConsumerArithmetic"; }
part proof8:ProofRow { attribute :>> key="descriptor-roundtrip"; attribute :>> lemma="ProducerCapacity.descriptorStoredRoundTrip"; }
part proof9:ProofRow { attribute :>> key="small64"; attribute :>> lemma="ProducerCapacity.smallConstructorCap64"; }
part proof10:ProofRow { attribute :>> key="small32"; attribute :>> lemma="ProducerCapacity.smallConstructorCap32"; }
part proof11:ProofRow { attribute :>> key="rest-vector"; attribute :>> lemma="ProducerCapacity.argumentVectorCap"; }
part proof12:ProofRow { attribute :>> key="closure"; attribute :>> lemma="ProducerCapacity.closureBound"; }
part proof13:ProofRow { attribute :>> key="threshold"; attribute :>> lemma="ProducerCapacity.thresholdBudget"; }
part proof14:ProofRow { attribute :>> key="source-handoff"; attribute :>> lemma="ProducerCapacity.sourceBudgetHandoff"; }
part proof15:ProofRow { attribute :>> key="packing-handoff"; attribute :>> lemma="ProducerCapacity.packingHandoff"; }
part proof16:ProofRow { attribute :>> key="live-scope"; attribute :>> lemma="ProducerCapacity.startedScope"; }
part proof17:ProofRow { attribute :>> key="ordinary-counter"; attribute :>> lemma="ProducerCapacity.directObjectCounterexample"; }
part proof18:ProofRow { attribute :>> key="budget-cut"; attribute :>> lemma="ProducerEnvelope.weakCutKeepsEnvelope"; }
part proof19:ProofRow { attribute :>> key="source-cover"; attribute :>> lemma="ProducerCapacity.coverBounds"; }
part proof20:ProofRow { attribute :>> key="source-budget"; attribute :>> lemma="ProducerCapacity.sourceCoverBudget"; }
part proof21:ProofRow { attribute :>> key="overlap-control"; attribute :>> lemma="ProducerCapacity.overlapRejected"; }
part history:GambitAssuranceRouting::ModelNeed { ref part :>> owner=GambitAssuranceRelations::modelUse3; attribute :>> obligationId="PE-history"; attribute :>> kind="interleaving"; attribute :>> subjectPath="dev/refactoring/modern-c/models/quint/copy_producer_envelope.qnt"; attribute :>> subjectScope="Module profile coverage publication invalidation and strong weak source credit histories"; attribute :>> premise="Research only; arithmetic and finite model proofs are not native admission"; }
part induction:GambitAssuranceRouting::ModelNeed { ref part :>> owner=GambitAssuranceRelations::modelUse3; attribute :>> obligationId="PE-induction"; attribute :>> kind="induction"; attribute :>> subjectPath="dev/refactoring/modern-c/models/lean/ProducerEnvelope.lean"; attribute :>> subjectScope="All actual typed producer-envelope AST actions"; attribute :>> premise="Research only; arithmetic and finite model proofs are not native admission"; }
part composition:GambitAssuranceRouting::ModelNeed { ref part :>> owner=GambitAssuranceRelations::modelUse3; attribute :>> obligationId="PE-composition"; attribute :>> kind="induction"; attribute :>> subjectPath="dev/refactoring/modern-c/models/lean/ProducerCapacity.lean"; attribute :>> subjectScope="Exact size arithmetic plus handoff to preceding symbolic packing proof"; attribute :>> premise="Research only; arithmetic and finite model proofs are not native admission"; }
part projection:GambitAssuranceRouting::ModelNeed { ref part :>> owner=GambitAssuranceRelations::modelUse3; attribute :>> obligationId="PE-projection"; attribute :>> kind="restricted-projection"; attribute :>> subjectPath="dev/refactoring/modern-c/models/lean/ProducerEnvelopeAst.lean"; attribute :>> subjectScope="Typed JSON bound-state identity extraction"; attribute :>> premise="Research only; arithmetic and finite model proofs are not native admission"; }
part source:GambitAssuranceRouting::ModelNeed { ref part :>> owner=GambitAssuranceRelations::modelUse3; attribute :>> obligationId="PE-source"; attribute :>> kind="source-refinement"; attribute :>> subjectPath="dev/refactoring/modern-c/copy-producer-envelope-design.org"; attribute :>> subjectScope="Actual all-producer closure immutable view old module pins and canonical source partition open"; attribute :>> premise="Research only; arithmetic and finite model proofs are not native admission"; }
part platform:GambitAssuranceRouting::ModelNeed { ref part :>> owner=GambitAssuranceRelations::modelUse3; attribute :>> obligationId="PE-platform"; attribute :>> kind="native-memory-order"; attribute :>> subjectPath="dev/refactoring/modern-c/copy-producer-envelope-design.org"; attribute :>> subjectScope="Effective ABI native relocation alias closure and C11 receipt publication open"; attribute :>> premise="Research only; arithmetic and finite model proofs are not native admission"; }
part priorPacking:GambitAssuranceRouting::ModelNeed { ref part :>> owner=GambitAssuranceRelations::modelUse3; attribute :>> obligationId="PE-prior-packing"; attribute :>> kind="dependency"; attribute :>> subjectPath="dev/refactoring/modern-c/models/lean/CopyCapacityComposition.lean"; attribute :>> subjectScope="Exact previous enoughHeapSections imported in packingHandoff"; attribute :>> premise="Preserve prior input digest and source hypotheses"; }
}
