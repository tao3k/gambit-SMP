package GambitExecutionStorage {
  private import ScalarValues::*;
  ref part selected=GambitRevisionDelivery::runtimeBinding;
  attribute scope:String="VM-owned execution-root storage:10 root field families,19 handwritten paths and their producer-qualified distribution products. Public GVM accessors, flat header, synchronous binding, pstate_mem, collector algorithm and official build names remain. This is an ownership prerequisite, not participant/worker decoupling or whole-SMP acceptance";
  attribute stage:String="First independently qualified role-ownership cut after published0c3ef7e5. RootOrigin/RootTask dispatch, worker arena/restoration and lifetime services require separate trees and observations. Configured-tool cleanup, bootstrap loop policy and tfib diagnosis are parked";
  attribute status:String="Native-qualified scoped storage cut: final default two-pass bootstrap and full original check pass; SMP root/continuation consumers and original GSI pass, original embedding still fails on baseline and candidate. Every publication requires an exact frozen source/layout/audit and ASCENT five-gate admission. No whole-SMP acceptance";
  attribute layoutDependency:String="Carrier-only Scheme field coordinates are checked against real C offsetof; C bridge root and return-slot operands use offsetof directly. Existing instruction dispatch/register allocator remain unchanged. Five CPU generators and bridge compile projections qualify their stated units, not native foreign-architecture execution. Root/call/allocator lifecycle is not independently migratable";
  attribute formalDuty:String="Source refinement of a storage-coordinate mapping plus actual native root/accessor, module-loader and semantic consumers. This cut adds no concurrent transition or algebraic law: do not copy the existing runtime_roles QNT schedules or RuntimeRoles Lean laws as evidence. Their participant/worker premises belong to later cuts. SysML drives the existing ASCENT five-gate checks";
  part def Need { ref part gate:GambitCommitGates::Gate; attribute id:String; attribute method:String; attribute artifact:String; attribute scope:String; }
  part source:Need { ref part :>> gate=GambitCommitGates::tests; attribute :>> id="ES-SOURCE"; attribute :>> method="source-refinement"; attribute :>> artifact=".cache/tasks/modern-c-frame-contract/runs/execution-storage-submission/evidence/source-refinement.json"; attribute :>> scope="exact moved declarations and all direct/macro/embedded-C consumers; early primary and ordinary setup binding precede helpers; original collector transformations are field-coordinate substitutions only; module descriptor/version retained; size/version rejection precedes cached completion and any fixup mutation; official names/build entries unchanged"; }
  part native:Need { ref part :>> gate=GambitCommitGates::tests; attribute :>> id="ES-NATIVE"; attribute :>> method="native"; attribute :>> artifact=".cache/tasks/modern-c-frame-contract/runs/execution-storage-submission/evidence/tests.json"; attribute :>> scope="same Modern C workspace/Bazel profile, complete bootstrap <=600s; actual accessor/save-reload controls and rejected old field access; held old-layout module repeatedly rejected before body and flag mutation; complete existing default GSI/check plus SMP root consumers and explicit baseline failure disposition; frame roots, multi-shot continuation and map consumers; exact default generated products separately qualified"; }
  part layout:Need { ref part :>> gate=GambitCommitGates::tests; attribute :>> id="ES-LAYOUT"; attribute :>> method="native"; attribute :>> artifact=".cache/tasks/modern-c-frame-contract/runs/execution-storage-submission/evidence/layout.json"; attribute :>> scope="Actual frame fixture carrier/root coordinates, current public accessor/root-bank controls, five actual CPU generators and five compile-only bridge projections with matched baseline; native foreign-architecture execution not claimed"; }
  part baseline:Need { ref part :>> gate=GambitCommitGates::questions; attribute :>> id="ES-BASELINE"; attribute :>> method="native"; attribute :>> artifact=".cache/tasks/modern-c-frame-contract/runs/execution-storage-submission/evidence/baseline-comparison.json"; attribute :>> scope="Preserve complete original SMP results. Thread inactive class reproduced with actual baseline child at same path; embedding exit70 reproduced before setup returns on baseline and candidate. No failure-rate claim, SMP pass, assertion change or internal startup-root-cause proof. Final scoped validation and future owner explicit"; }
  part audit:Need { ref part :>> gate=GambitCommitGates::learning; attribute :>> id="ES-AUDIT"; attribute :>> method="source-analysis"; attribute :>> artifact="dev/refactoring/modern-c/execution-storage-audit.org"; attribute :>> scope="Every handwritten file and generated-product family states necessity, old responsibility retired, measurable benefit/cost, actual validation and exclusion; no official public namespace, configure/Make entry or CI command rename"; }
  part learning:Need { ref part :>> gate=GambitCommitGates::learning; attribute :>> id="ES-LEARNING"; attribute :>> method="source-analysis"; attribute :>> artifact="dev/refactoring/modern-c/execution-storage.org"; attribute :>> scope="Root storage identity no longer equals carrier storage identity. One context pointer and stable VM slots are added; allocation and worker ownership are deliberately not relabeled. No speedup or W<R claim"; }
  part processNeed:Need { ref part :>> gate=GambitCommitGates::process; attribute :>> id="ES-PROCESS"; attribute :>> method="source-analysis"; attribute :>> artifact="dev/refactoring/modern-c/models/sysml/revision-delivery.sysml"; attribute :>> scope="Exact first source cut and participant/worker successors, entry and lifetime side dependencies, required tests and retired responsibilities; pending mixed index/working content is not the submission tree"; }
  part models:Need { ref part :>> gate=GambitCommitGates::models; attribute :>> id="ES-MODELS"; attribute :>> method="native-model-projection"; attribute :>> artifact=".cache/tasks/modern-c-frame-contract/runs/execution-storage-submission/evidence/model.json"; attribute :>> scope="strict native SysML projection, existing ASCENT scoped gates, missing-native/stale-tree/wrong-profile/wrong-artifact/model-only rejection; no duplicated QNT/Lean obligation"; }
  part questions:Need { ref part :>> gate=GambitCommitGates::questions; attribute :>> id="ES-QUESTIONS"; attribute :>> method="source-analysis"; attribute :>> artifact="dev/refactoring/modern-c/execution-storage.org"; attribute :>> scope="Explain Gambit GVM/multi-shot/C portability amplification, initialization order, source callers and binary rejection, added indirection/fixed-slot memory, no live rebinding permission, remaining carrier/GC/worker coupling and counterexamples. Unanswered mandatory scoped questions block submission"; }
}
