package GambitTicketCapabilityRetirement { private import ScalarValues::*;
part def Owner { attribute componentId:String; }
part settlementOwner:Owner { attribute :>> componentId="settlement"; }
part captureOwner:Owner { attribute :>> componentId="capture"; }
part rootsOwner:Owner { attribute :>> componentId="roots"; }
part def SourceRow { attribute key:String; attribute path:String; attribute needle:String; attribute obligation:String; }
part source0:SourceRow { attribute :>> key="will-load"; attribute :>> path="vendor/gambit/lib/_kernel.scm"; attribute :>> needle="(let ((testator (##will-testator will))"; attribute :>> obligation="Loaded operands survive field clearing; no keyed completion ledger here"; }
part source1:SourceRow { attribute :>> key="will-clear"; attribute :>> path="vendor/gambit/lib/_kernel.scm"; attribute :>> needle="(##will-action-set! will #f)"; attribute :>> obligation="Severs one field; not a duplicate settlement or last-capture receipt"; }
part source2:SourceRow { attribute :>> key="will-invoke"; attribute :>> path="vendor/gambit/lib/_kernel.scm"; attribute :>> needle="(action testator)"; attribute :>> obligation="Actual invocation; stable outer exit signer and exact TicketId absent in this slice"; }
part source3:SourceRow { attribute :>> key="will-loop"; attribute :>> path="vendor/gambit/lib/_kernel.scm"; attribute :>> needle="(macro-fifo-remove-all! registry)"; attribute :>> obligation="Removed list remains in continuation/local loop state"; }
part source4:SourceRow { attribute :>> key="reify"; attribute :>> path="vendor/gambit/lib/_thread.scm"; attribute :>> needle="(define (reify-continuation cont)"; attribute :>> obligation="Reified procedure captures raw cont"; }
part source5:SourceRow { attribute :>> key="resume"; attribute :>> path="vendor/gambit/lib/_thread.scm"; attribute :>> needle="(##continuation-return-aux cont val1 val2 val3 others)"; attribute :>> obligation="Reified closure repeatedly restores same continuation"; }
part source6:SourceRow { attribute :>> key="unwrapped"; attribute :>> path="vendor/gambit/lib/_thread.scm"; attribute :>> needle="(##closure-ref proc 1)"; attribute :>> obligation="procedure->continuation exposes raw cont; wrapping alone does not close aliases"; }
part source7:SourceRow { attribute :>> key="wind-normal"; attribute :>> path="vendor/gambit/lib/_thread.scm"; attribute :>> needle="(define-prim (##dynamic-wind before thunk after)"; attribute :>> obligation="Normal before/after is a dynamic crossing, not unique invocation ID"; }
part source8:SourceRow { attribute :>> key="wind-after"; attribute :>> path="vendor/gambit/lib/_thread.scm"; attribute :>> needle="((macro-dynwind-after src))"; attribute :>> obligation="Unwind executes user after thunk; may escape or be repeated"; }
part source9:SourceRow { attribute :>> key="wind-before"; attribute :>> path="vendor/gambit/lib/_thread.scm"; attribute :>> needle="((macro-dynwind-before dst))"; attribute :>> obligation="Re-entry executes user before thunk"; }
part source10:SourceRow { attribute :>> key="restore-fast"; attribute :>> path="vendor/gambit/lib/_thread.scm"; attribute :>> needle="(if (or (##eq? src dst) ;; check common case (same dynamic-wind context)"; attribute :>> obligation="Same-dynwind restore bypasses before hook; native resume admission needed"; }
part source11:SourceRow { attribute :>> key="copy"; attribute :>> path="vendor/gambit/lib/_kernel.scm"; attribute :>> needle="(define-prim (##continuation-copy cont)"; attribute :>> obligation="New continuation shell shares frame and denv"; }
part source12:SourceRow { attribute :>> key="frame-ref"; attribute :>> path="vendor/gambit/lib/_kernel.scm"; attribute :>> needle="___SCMOBJ frame = ___CONTINUATION_FRAME_FIELD(cont);"; attribute :>> obligation="Continuation physical graph may be aliased"; }
part source13:SourceRow { attribute :>> key="slot-write"; attribute :>> path="vendor/gambit/lib/_kernel.scm"; attribute :>> needle="(define-prim (##continuation-set! cont i val)"; attribute :>> obligation="Frame mutation requires authority and generation qualification"; }
part source14:SourceRow { attribute :>> key="frame-write"; attribute :>> path="vendor/gambit/lib/_kernel.scm"; attribute :>> needle="(macro-continuation-frame-set! cont frame)"; attribute :>> obligation="Raw representation writer"; }
part source15:SourceRow { attribute :>> key="denv-write"; attribute :>> path="vendor/gambit/lib/_kernel.scm"; attribute :>> needle="(macro-continuation-denv-set! cont denv)"; attribute :>> obligation="Restored dynamic environment can change"; }
part source16:SourceRow { attribute :>> key="serial-explode"; attribute :>> path="vendor/gambit/lib/_io.scm"; attribute :>> needle="(define-prim (##explode-continuation cont)"; attribute :>> obligation="Serial representation includes frame and denv"; }
part source17:SourceRow { attribute :>> key="serial-implode"; attribute :>> path="vendor/gambit/lib/_io.scm"; attribute :>> needle="(define-prim (##implode-continuation re fields)"; attribute :>> obligation="Importer constructs continuation; derived capability registration required"; }
part source18:SourceRow { attribute :>> key="closure-explode"; attribute :>> path="vendor/gambit/lib/_io.scm"; attribute :>> needle="(define-prim (##explode-closure closure)"; attribute :>> obligation="Closure captures can be externally represented"; }
part source19:SourceRow { attribute :>> key="rc-release"; attribute :>> path="vendor/gambit/lib/memory/rc-allocation.inc"; attribute :>> needle="if (--h->refcount == 0)"; attribute :>> obligation="RC header count is explicit native object ownership, not Scheme alias census"; }
part source20:SourceRow { attribute :>> key="rc-addref"; attribute :>> path="vendor/gambit/lib/memory/rc-allocation.inc"; attribute :>> needle="h->refcount++;"; attribute :>> obligation="Raw native alias operation needs participant identity; not globally atomic root retirement"; }
part source21:SourceRow { attribute :>> key="rc-scan"; attribute :>> path="vendor/gambit/lib/memory/rc-roots.inc"; attribute :>> needle="mark_array (work, &h->data, 1);"; attribute :>> obligation="Actual moving-GC slot consumer; scan lease/close protocol not supplied here"; }
part source22:SourceRow { attribute :>> key="frame-scan"; attribute :>> path="vendor/gambit/lib/memory/continuation-roots.inc"; attribute :>> needle="while (___frame_root_next_run (&cursor, &first, &past))"; attribute :>> obligation="Actual captured-frame consumer; complete generation match remains open"; }
part source23:SourceRow { attribute :>> key="poll"; attribute :>> path="vendor/gambit/lib/_kernel.c"; attribute :>> needle="___JUMPGENNOTSAFE(___SET_NARGS(1),___R3)"; attribute :>> obligation="Checked-in will call artifact; no matching current Darwin receipt inferred"; }
part source24:SourceRow { attribute :>> key="will-resurrect"; attribute :>> path="vendor/gambit/doc/gambit.txi"; attribute :>> needle="A remarkable feature of wills is that an action procedure can"; attribute :>> obligation="GC notification can execute arbitrary action and resurrect its testator"; }
part source25:SourceRow { attribute :>> key="dead-roots"; attribute :>> path="vendor/gambit/doc/gambit.txi"; attribute :>> needle="continuations will contain the dead variables."; attribute :>> obligation="Source deadness/return cannot sign physical retirement"; }
part source26:SourceRow { attribute :>> key="raw-write"; attribute :>> path="vendor/gambit/gsc/_t-c-1.scm"; attribute :>> needle="(vector-set! r 1 demanders)"; attribute :>> obligation="Source permission that a frozen-plan admission must close"; }
part source27:SourceRow { attribute :>> key="second"; attribute :>> path="vendor/gambit/gsc/_t-c-1.scm"; attribute :>> needle="(def-mod-prm-glo \"DEF_MOD_GLO\")"; attribute :>> obligation="Actual second normalization site; full equivalence remains required"; }
part def IdentityRow { attribute key:String; attribute structure:String; attribute rule:String; attribute caveat:String; }
part identity0:IdentityRow { attribute :>> key="ticket"; attribute :>> structure="SessionNonce + DomainId + Generation + AttemptId"; attribute :>> rule="One terminal outcome per complete key; immutable payload binding"; attribute :>> caveat="A slot, object address or payload hash is not the key"; }
part identity1:IdentityRow { attribute :>> key="capture"; attribute :>> structure="CaptureDomainId + CaptureId + Generation"; attribute :>> rule="All derived raw copies or managed exports belong to a tracked lineage"; attribute :>> caveat="Object inequality does not imply independent frame/denv authority"; }
part identity2:IdentityRow { attribute :>> key="transport"; attribute :>> structure="OperationId + TicketId + immutable argument digest"; attribute :>> rule="Lost reply queries the same record; pending is not absent"; attribute :>> caveat="Same payload does not identify semantic re-execution"; }
part identity3:IdentityRow { attribute :>> key="resume"; attribute :>> structure="CaptureId + fresh AttemptId minted by external restore gateway"; attribute :>> rule="Each true multi-shot invocation gets a distinct ticket"; attribute :>> caveat="Do not mint from a counter/token stored inside restored Scheme frames"; }
part identity4:IdentityRow { attribute :>> key="handle"; attribute :>> structure="CaptureId + HandleId + Generation"; attribute :>> rule="Drop same handle is idempotent and does not release another handle"; attribute :>> caveat="Managed handles do not count arbitrary Scheme/raw aliases"; }
part identity5:IdentityRow { attribute :>> key="borrow"; attribute :>> structure="CaptureId + BorrowId + participant generation"; attribute :>> rule="Return one borrower; duplicate return cannot decrement another"; attribute :>> caveat="Native participant roster and out-of-band aliases still require closure"; }
part identity6:IdentityRow { attribute :>> key="scanner"; attribute :>> structure="RootDomain + ScanBorrowId + generation"; attribute :>> rule="Maintenance admission closes; admitted scans release by exact ID"; attribute :>> caveat="Authority closure alone does not authorize root unlinking"; }
part identity7:IdentityRow { attribute :>> key="terminal"; attribute :>> structure="Immutable outcome or non-reused tombstone"; attribute :>> rule="Late query returns prior outcome or a defined non-replay status"; attribute :>> caveat="Physical tombstone reclamation and crash persistence are not proved"; }
part def IssuerRow { attribute key:String; attribute proposedIssuer:String; attribute actualSource:String; attribute status:String; attribute responsibility:String; }
part issuer0:IssuerRow { attribute :>> key="exit"; attribute :>> proposedIssuer="Stable runtime completion guard outside restored frames"; attribute :>> actualSource="will-execute! and continuation unwind/return are located; no such keyed guard identified"; attribute :>> status="Required refactoring; cannot fabricate receipt from return/after"; attribute :>> responsibility="Retains scanned activation roots until exit outcome and handoff are classified"; }
part issuer1:IssuerRow { attribute :>> key="settlement"; attribute :>> proposedIssuer="Ledger linearization owner"; attribute :>> actualSource="No existing TicketId ledger identified in inspected executor paths"; attribute :>> status="Model assumes trusted executor witness bound to this key and payload"; attribute :>> responsibility="Atomically retain terminal outcome and ownership result before reply"; }
part issuer2:IssuerRow { attribute :>> key="query"; attribute :>> proposedIssuer="Same ledger owner with record/read lease"; attribute :>> actualSource="No existing keyed query service in inspected paths"; attribute :>> status="Required service boundary; timeout caller is not an absence issuer"; attribute :>> responsibility="Answer pending/completed/conflict without replaying execution"; }
part issuer3:IssuerRow { attribute :>> key="fresh-attempt"; attribute :>> proposedIssuer="Runtime restore gateway before no-winding/graft/thread restoration"; attribute :>> actualSource="Same-dynwind fast path directly restores; Scheme before hook not complete"; attribute :>> status="GVM/native contract insertion points still require a complete inventory"; attribute :>> responsibility="Mint ID outside capture; duplicate delivery keeps the existing ID"; }
part issuer4:IssuerRow { attribute :>> key="alias-census"; attribute :>> proposedIssuer="Capture-domain exporter/importer owner"; attribute :>> actualSource="callcc/copy/unwrap/serialization and representation writers create open alias paths"; attribute :>> status="No generic last-Scheme-reference signer found"; attribute :>> responsibility="Close producers, account derived lineages or deny optimization receipt"; }
part issuer5:IssuerRow { attribute :>> key="authority-close"; attribute :>> proposedIssuer="Stable capture-domain owner"; attribute :>> actualSource="Current callcc closure has no unified managed admission gate"; attribute :>> status="Only for a fully admitted managed scope"; attribute :>> responsibility="Drain handles, native borrowers and accepted activation tickets; preserve unrestricted Scheme fallback"; }
part issuer6:IssuerRow { attribute :>> key="root-detach"; attribute :>> proposedIssuer="GC RootRegistry/scan-gate owner"; attribute :>> actualSource="mark_rc and captured frame scanners consume slots; no new gate implemented"; attribute :>> status="Root mapping, producer/consumer generation and real scan leases unresolved"; attribute :>> responsibility="Keep root storage pinned after authority closes until maintenance scans drain"; }
part issuer7:IssuerRow { attribute :>> key="absence"; attribute :>> proposedIssuer="Creation/commit owner after reservation outcome is resolved"; attribute :>> actualSource="No absence oracle supplied by clearing will fields or empty registry"; attribute :>> status="Unknown outcome stays owned; process death is not an absence receipt"; attribute :>> responsibility="Retain record/root or reconcile against the exact commit identity"; }
part def ClaimRow { attribute key:String; attribute mechanism:String; attribute condition:String; attribute result:String; attribute gap:String; }
part claim0:ClaimRow { attribute :>> key="per-id"; attribute :>> mechanism="Two explicit ticket slots with distinct keys and immutable outcomes"; attribute :>> condition="Trusted keyed exit witness; no identity reuse"; attribute :>> result="Repeated completion/query cannot retire another active ticket"; attribute :>> gap="Finite product alone is not an unbounded scheduler/alias graph proof"; }
part claim1:ClaimRow { attribute :>> key="generic"; attribute :>> mechanism="Functional keyed ledger and handle map in Lean"; attribute :>> condition="Lookup/update are faithful and equality is full-key equality"; attribute :>> result="Other-key noninterference, idempotence and terminal outcome retention hold for arbitrary keys"; attribute :>> gap="Hash collision, parser/payload coding and current C source refinement unproved"; }
part claim2:ClaimRow { attribute :>> key="projection"; attribute :>> mechanism="Concrete commit/query AST to generic per-key record"; attribute :>> condition="Typed AST binds same ticket fields and fixed abstract payload"; attribute :>> result="Commit/query correspondence and other-slot noninterference proved where stated"; attribute :>> gap="Does not establish arbitrary real Scheme value encoding or all-model simulation"; }
part claim3:ClaimRow { attribute :>> key="multi-shot"; attribute :>> mechanism="True continuation invocation reserves a fresh ticket"; attribute :>> condition="Stable external gateway covers no-winding and all restore paths"; attribute :>> result="Retaining CaptureId supports multiple invocations without ticket reuse"; attribute :>> gap="Current source has no complete gateway insertion/caller census"; }
part claim4:ClaimRow { attribute :>> key="cap-retirement"; attribute :>> mechanism="Close managed admission before census; keep root until scan cut"; attribute :>> condition="No raw escape and all exact handles/borrows/accepted attempts accounted"; attribute :>> result="Authority closure and physical root retirement are distinct states"; attribute :>> gap="Generic Scheme last-reference retirement remains unresolved"; }
part claim5:ClaimRow { attribute :>> key="ack-loss"; attribute :>> mechanism="Outcome commits before reply; record survives observation loss"; attribute :>> condition="Single surviving owner/ledger instance; no blind retry"; attribute :>> result="Same TicketId query returns original outcome"; attribute :>> gap="Crash recovery/durable exactly-once external effects not proved"; }
part claim6:ClaimRow { attribute :>> key="semantics"; attribute :>> mechanism="Raw/unknown escape keeps optimization unavailable"; attribute :>> condition="No forced single-shot conversion or global ban on Scheme restoration"; attribute :>> result="Safe fallback can preserve original continuation behavior"; attribute :>> gap="Actual fallback and full second-normalization equivalence still open"; }
part def MemoryRow { attribute key:String; attribute publication:String; attribute observation:String; attribute obligation:String; attribute overhead:String; }
part memory0:MemoryRow { attribute :>> key="commit"; attribute :>> publication="C23 owner critical section publishes key, state, outcome and root custody together"; attribute :>> observation="Reply or query reads same pinned immutable record"; attribute :>> obligation="No decrement-then-record gap; no lock held across Scheme/GC/FFI"; attribute :>> overhead="Per-key record plus synchronization"; }
part memory1:MemoryRow { attribute :>> key="resume"; attribute :>> publication="Register fresh activation and root carrier before restoring execution"; attribute :>> observation="Restored code uses current stable guard, not captured old ticket token"; attribute :>> obligation="All no-winding, scheduler and native callback entries must refine this ordering"; attribute :>> overhead="One admission/settlement per real activation"; }
part memory2:MemoryRow { attribute :>> key="close"; attribute :>> publication="One domain gate closes exports and managed resumes"; attribute :>> observation="All prior reservations remain visible until settled"; attribute :>> obligation="Close is not arbitrary raw alias revocation; generation cannot wrap silently"; attribute :>> overhead="Handle/borrow identities and overflow checks"; }
part memory3:MemoryRow { attribute :>> key="scan"; attribute :>> publication="Close maintenance admission after authority receipt"; attribute :>> observation="Drain preexisting exact scan borrowers before unlink"; attribute :>> obligation="Moving slot updates and C23 release/acquire publication need source proof"; attribute :>> overhead="Scan records/root pin outlive user callback return"; }
part memory4:MemoryRow { attribute :>> key="tombstone"; attribute :>> publication="Retain terminal record before acknowledging settlement"; attribute :>> observation="Old keys cannot be reused while delayed requests exist"; attribute :>> obligation="C23 visibility does not supply durable persistence or transport failure detection"; attribute :>> overhead="Storage may grow with outstanding retry windows/capabilities"; }
part def GainRow { attribute key:String; attribute avoided:String; attribute added:String; attribute condition:String; }
part gain0:GainRow { attribute :>> key="dedup"; attribute :>> avoided="Repeated settlement/query causes zero extra execution and zero additional settlement in model"; attribute :>> added="Retained per-key outcome/tombstone; O(1) logical keyed operation with an appropriate index"; attribute :>> condition="Lookup implementation and native cost not measured; general map lookup complexity not assumed"; }
part gain1:GainRow { attribute :>> key="captures"; attribute :>> avoided="Avoid waiting for all Scheme continuations in the VM"; attribute :>> added="Exact managed handle/native/scan records; unknown raw escape remains blocked"; attribute :>> condition="Only fully scoped authority qualifies; no guaranteed generic last-reference census"; }
part gain2:GainRow { attribute :>> key="reuse"; attribute :>> avoided="0..N second helper calls removable; first N retained"; attribute :>> added="P plan work + V validation + incremental ledger/root/capture cost"; attribute :>> condition="Positive iff saved helper work exceeds marginal added work; current admitted N=0"; }
part gain3:GainRow { attribute :>> key="amortization"; attribute :>> avoided="Share necessary runtime guard/root/identity support across services"; attribute :>> added="Charge common support once and each extra per-operation path explicitly"; attribute :>> condition="Shared support is neither free nor charged repeatedly to every helper removal"; }
part gain4:GainRow { attribute :>> key="memory"; attribute :>> avoided="No admitted early reclamation from return or GC callback alone"; attribute :>> added="Terminal payload roots and live capture storage retained"; attribute :>> condition="No guaranteed memory saving; unbounded retention/crash recovery need separate policies"; }
part gain5:GainRow { attribute :>> key="language"; attribute :>> avoided="Same semantic obligations in modern C23 and Zig"; attribute :>> added="Both require keyed custody, generated root coverage and capability closure"; attribute :>> condition="No additional Zig-specific benefit established here"; }
part def ContractRow { attribute fromNode:String; attribute toNode:String; attribute custody:String; }
part contract0:ContractRow { attribute :>> fromNode="SysML"; attribute :>> toNode="ASCENT"; attribute :>> custody="Component owner / source / action / theorem / receipt scope"; }
part contract1:ContractRow { attribute :>> fromNode="ASCENT"; attribute :>> toNode="QNT"; attribute :>> custody="Missing or forged coverage keeps actual retirement denied"; }
part contract2:ContractRow { attribute :>> fromNode="QNT"; attribute :>> toNode="Lean"; attribute :>> custody="Typed IR safety plus explicitly checked generic projection"; }
part contract3:ContractRow { attribute :>> fromNode="executor"; attribute :>> toNode="keyed ledger"; attribute :>> custody="Exit witness belongs to the exact TicketId and payload"; }
part contract4:ContractRow { attribute :>> fromNode="keyed ledger"; attribute :>> toNode="reply"; attribute :>> custody="Terminal record commits before reply; lost reply does not undo commit"; }
part contract5:ContractRow { attribute :>> fromNode="retry query"; attribute :>> toNode="keyed ledger"; attribute :>> custody="Same ID reads pending or cached outcome; does not execute again"; }
part contract6:ContractRow { attribute :>> fromNode="restore gateway"; attribute :>> toNode="keyed ledger"; attribute :>> custody="Fresh AttemptId before every semantic restore; outside captured frames"; }
part contract7:ContractRow { attribute :>> fromNode="capture exports"; attribute :>> toNode="authority gate"; attribute :>> custody="Track exact handle and native borrower identities; raw escape blocks census"; }
part contract8:ContractRow { attribute :>> fromNode="authority gate"; attribute :>> toNode="root registry"; attribute :>> custody="Authority closes only after accepted activations and managed holders drain"; }
part contract9:ContractRow { attribute :>> fromNode="root registry"; attribute :>> toNode="scan borrowers"; attribute :>> custody="Maintenance admission closes; existing readers retain storage"; }
part contract10:ContractRow { attribute :>> fromNode="scan borrowers"; attribute :>> toNode="root detach receipt"; attribute :>> custody="Exact scan returns before root storage unlink"; }
part contract11:ContractRow { attribute :>> fromNode="root detach receipt"; attribute :>> toNode="second normalization"; attribute :>> custody="Full emission/metadata equivalence still required; no native admission"; }
part def BindingRow { attribute actionName:String; attribute lemma:String; attribute scope:String; }
part binding0:BindingRow { attribute :>> actionName="ticket_capability_retirement.reserve0"; attribute :>> lemma="TicketCapability.reserve0Preserves"; attribute :>> scope="Two-ticket one-capture tracked-holder product; external source receipts unproved"; }
part binding1:BindingRow { attribute :>> actionName="ticket_capability_retirement.enter0"; attribute :>> lemma="TicketCapability.enter0Preserves"; attribute :>> scope="Two-ticket one-capture tracked-holder product; external source receipts unproved"; }
part binding2:BindingRow { attribute :>> actionName="ticket_capability_retirement.observeSuccess0"; attribute :>> lemma="TicketCapability.observeSuccess0Preserves"; attribute :>> scope="Two-ticket one-capture tracked-holder product; external source receipts unproved"; }
part binding3:BindingRow { attribute :>> actionName="ticket_capability_retirement.observeFailure0"; attribute :>> lemma="TicketCapability.observeFailure0Preserves"; attribute :>> scope="Two-ticket one-capture tracked-holder product; external source receipts unproved"; }
part binding4:BindingRow { attribute :>> actionName="ticket_capability_retirement.commit0"; attribute :>> lemma="TicketCapability.commit0Preserves"; attribute :>> scope="Two-ticket one-capture tracked-holder product; external source receipts unproved"; }
part binding5:BindingRow { attribute :>> actionName="ticket_capability_retirement.query0"; attribute :>> lemma="TicketCapability.query0Preserves"; attribute :>> scope="Two-ticket one-capture tracked-holder product; external source receipts unproved"; }
part binding6:BindingRow { attribute :>> actionName="ticket_capability_retirement.queryPending0"; attribute :>> lemma="TicketCapability.queryPending0Preserves"; attribute :>> scope="Two-ticket one-capture tracked-holder product; external source receipts unproved"; }
part binding7:BindingRow { attribute :>> actionName="ticket_capability_retirement.conflictingSettle0"; attribute :>> lemma="TicketCapability.conflictingSettle0Preserves"; attribute :>> scope="Two-ticket one-capture tracked-holder product; external source receipts unproved"; }
part binding8:BindingRow { attribute :>> actionName="ticket_capability_retirement.loseReply0"; attribute :>> lemma="TicketCapability.loseReply0Preserves"; attribute :>> scope="Two-ticket one-capture tracked-holder product; external source receipts unproved"; }
part binding9:BindingRow { attribute :>> actionName="ticket_capability_retirement.retainTombstone0"; attribute :>> lemma="TicketCapability.retainTombstone0Preserves"; attribute :>> scope="Two-ticket one-capture tracked-holder product; external source receipts unproved"; }
part binding10:BindingRow { attribute :>> actionName="ticket_capability_retirement.reserve1"; attribute :>> lemma="TicketCapability.reserve1Preserves"; attribute :>> scope="Two-ticket one-capture tracked-holder product; external source receipts unproved"; }
part binding11:BindingRow { attribute :>> actionName="ticket_capability_retirement.enter1"; attribute :>> lemma="TicketCapability.enter1Preserves"; attribute :>> scope="Two-ticket one-capture tracked-holder product; external source receipts unproved"; }
part binding12:BindingRow { attribute :>> actionName="ticket_capability_retirement.observeSuccess1"; attribute :>> lemma="TicketCapability.observeSuccess1Preserves"; attribute :>> scope="Two-ticket one-capture tracked-holder product; external source receipts unproved"; }
part binding13:BindingRow { attribute :>> actionName="ticket_capability_retirement.observeFailure1"; attribute :>> lemma="TicketCapability.observeFailure1Preserves"; attribute :>> scope="Two-ticket one-capture tracked-holder product; external source receipts unproved"; }
part binding14:BindingRow { attribute :>> actionName="ticket_capability_retirement.commit1"; attribute :>> lemma="TicketCapability.commit1Preserves"; attribute :>> scope="Two-ticket one-capture tracked-holder product; external source receipts unproved"; }
part binding15:BindingRow { attribute :>> actionName="ticket_capability_retirement.query1"; attribute :>> lemma="TicketCapability.query1Preserves"; attribute :>> scope="Two-ticket one-capture tracked-holder product; external source receipts unproved"; }
part binding16:BindingRow { attribute :>> actionName="ticket_capability_retirement.queryPending1"; attribute :>> lemma="TicketCapability.queryPending1Preserves"; attribute :>> scope="Two-ticket one-capture tracked-holder product; external source receipts unproved"; }
part binding17:BindingRow { attribute :>> actionName="ticket_capability_retirement.conflictingSettle1"; attribute :>> lemma="TicketCapability.conflictingSettle1Preserves"; attribute :>> scope="Two-ticket one-capture tracked-holder product; external source receipts unproved"; }
part binding18:BindingRow { attribute :>> actionName="ticket_capability_retirement.loseReply1"; attribute :>> lemma="TicketCapability.loseReply1Preserves"; attribute :>> scope="Two-ticket one-capture tracked-holder product; external source receipts unproved"; }
part binding19:BindingRow { attribute :>> actionName="ticket_capability_retirement.retainTombstone1"; attribute :>> lemma="TicketCapability.retainTombstone1Preserves"; attribute :>> scope="Two-ticket one-capture tracked-holder product; external source receipts unproved"; }
part binding20:BindingRow { attribute :>> actionName="ticket_capability_retirement.cloneHandle1"; attribute :>> lemma="TicketCapability.cloneHandle1Preserves"; attribute :>> scope="Two-ticket one-capture tracked-holder product; external source receipts unproved"; }
part binding21:BindingRow { attribute :>> actionName="ticket_capability_retirement.dropHandle0"; attribute :>> lemma="TicketCapability.dropHandle0Preserves"; attribute :>> scope="Two-ticket one-capture tracked-holder product; external source receipts unproved"; }
part binding22:BindingRow { attribute :>> actionName="ticket_capability_retirement.dropHandle1"; attribute :>> lemma="TicketCapability.dropHandle1Preserves"; attribute :>> scope="Two-ticket one-capture tracked-holder product; external source receipts unproved"; }
part binding23:BindingRow { attribute :>> actionName="ticket_capability_retirement.duplicateDrop0"; attribute :>> lemma="TicketCapability.duplicateDrop0Preserves"; attribute :>> scope="Two-ticket one-capture tracked-holder product; external source receipts unproved"; }
part binding24:BindingRow { attribute :>> actionName="ticket_capability_retirement.borrowNative0"; attribute :>> lemma="TicketCapability.borrowNative0Preserves"; attribute :>> scope="Two-ticket one-capture tracked-holder product; external source receipts unproved"; }
part binding25:BindingRow { attribute :>> actionName="ticket_capability_retirement.returnNative0"; attribute :>> lemma="TicketCapability.returnNative0Preserves"; attribute :>> scope="Two-ticket one-capture tracked-holder product; external source receipts unproved"; }
part binding26:BindingRow { attribute :>> actionName="ticket_capability_retirement.borrowNative1"; attribute :>> lemma="TicketCapability.borrowNative1Preserves"; attribute :>> scope="Two-ticket one-capture tracked-holder product; external source receipts unproved"; }
part binding27:BindingRow { attribute :>> actionName="ticket_capability_retirement.returnNative1"; attribute :>> lemma="TicketCapability.returnNative1Preserves"; attribute :>> scope="Two-ticket one-capture tracked-holder product; external source receipts unproved"; }
part binding28:BindingRow { attribute :>> actionName="ticket_capability_retirement.duplicateNativeReturn0"; attribute :>> lemma="TicketCapability.duplicateNativeReturn0Preserves"; attribute :>> scope="Two-ticket one-capture tracked-holder product; external source receipts unproved"; }
part binding29:BindingRow { attribute :>> actionName="ticket_capability_retirement.closeCapability"; attribute :>> lemma="TicketCapability.closeCapabilityPreserves"; attribute :>> scope="Two-ticket one-capture tracked-holder product; external source receipts unproved"; }
part binding30:BindingRow { attribute :>> actionName="ticket_capability_retirement.discoverRawEscape"; attribute :>> lemma="TicketCapability.discoverRawEscapePreserves"; attribute :>> scope="Two-ticket one-capture tracked-holder product; external source receipts unproved"; }
part binding31:BindingRow { attribute :>> actionName="ticket_capability_retirement.attestAliasCensus"; attribute :>> lemma="TicketCapability.attestAliasCensusPreserves"; attribute :>> scope="Two-ticket one-capture tracked-holder product; external source receipts unproved"; }
part binding32:BindingRow { attribute :>> actionName="ticket_capability_retirement.attestRootMaps"; attribute :>> lemma="TicketCapability.attestRootMapsPreserves"; attribute :>> scope="Two-ticket one-capture tracked-holder product; external source receipts unproved"; }
part binding33:BindingRow { attribute :>> actionName="ticket_capability_retirement.closeAuthority"; attribute :>> lemma="TicketCapability.closeAuthorityPreserves"; attribute :>> scope="Two-ticket one-capture tracked-holder product; external source receipts unproved"; }
part binding34:BindingRow { attribute :>> actionName="ticket_capability_retirement.pinScanner0"; attribute :>> lemma="TicketCapability.pinScanner0Preserves"; attribute :>> scope="Two-ticket one-capture tracked-holder product; external source receipts unproved"; }
part binding35:BindingRow { attribute :>> actionName="ticket_capability_retirement.unpinScanner0"; attribute :>> lemma="TicketCapability.unpinScanner0Preserves"; attribute :>> scope="Two-ticket one-capture tracked-holder product; external source receipts unproved"; }
part binding36:BindingRow { attribute :>> actionName="ticket_capability_retirement.pinScanner1"; attribute :>> lemma="TicketCapability.pinScanner1Preserves"; attribute :>> scope="Two-ticket one-capture tracked-holder product; external source receipts unproved"; }
part binding37:BindingRow { attribute :>> actionName="ticket_capability_retirement.unpinScanner1"; attribute :>> lemma="TicketCapability.unpinScanner1Preserves"; attribute :>> scope="Two-ticket one-capture tracked-holder product; external source receipts unproved"; }
part binding38:BindingRow { attribute :>> actionName="ticket_capability_retirement.closeMaintenance"; attribute :>> lemma="TicketCapability.closeMaintenancePreserves"; attribute :>> scope="Two-ticket one-capture tracked-holder product; external source receipts unproved"; }
part binding39:BindingRow { attribute :>> actionName="ticket_capability_retirement.retireRoot"; attribute :>> lemma="TicketCapability.retireRootPreserves"; attribute :>> scope="Two-ticket one-capture tracked-holder product; external source receipts unproved"; }
part binding40:BindingRow { attribute :>> actionName="ticket_capability_retirement.selectStaleGeneration"; attribute :>> lemma="TicketCapability.selectStaleGenerationPreserves"; attribute :>> scope="Two-ticket one-capture tracked-holder product; external source receipts unproved"; }
part binding41:BindingRow { attribute :>> actionName="ticket_capability_retirement.selectCurrentGeneration"; attribute :>> lemma="TicketCapability.selectCurrentGenerationPreserves"; attribute :>> scope="Two-ticket one-capture tracked-holder product; external source receipts unproved"; }
part binding42:BindingRow { attribute :>> actionName="ticket_capability_retirement.rejectStaleRequest"; attribute :>> lemma="TicketCapability.rejectStaleRequestPreserves"; attribute :>> scope="Two-ticket one-capture tracked-holder product; external source receipts unproved"; }
part def ProofRow { attribute key:String; attribute lemma:String; }
part proof0:ProofRow { attribute :>> key="step"; attribute :>> lemma="TicketCapability.stepPreserves"; }
part proof1:ProofRow { attribute :>> key="reachable"; attribute :>> lemma="TicketCapability.reachableSafe"; }
part proof2:ProofRow { attribute :>> key="once0"; attribute :>> lemma="TicketCapability.atMostOnce0"; }
part proof3:ProofRow { attribute :>> key="once1"; attribute :>> lemma="TicketCapability.atMostOnce1"; }
part proof4:ProofRow { attribute :>> key="terminal0"; attribute :>> lemma="TicketCapability.terminal0Stable"; }
part proof5:ProofRow { attribute :>> key="terminal1"; attribute :>> lemma="TicketCapability.terminal1Stable"; }
part proof6:ProofRow { attribute :>> key="scan"; attribute :>> lemma="TicketCapability.rootNeedsScannerDrain"; }
part proof7:ProofRow { attribute :>> key="stale"; attribute :>> lemma="TicketCapability.staleCannotReserve"; }
part proof8:ProofRow { attribute :>> key="generic-other"; attribute :>> lemma="TicketIdentityAlgebra.settleOther"; }
part proof9:ProofRow { attribute :>> key="generic-idempotent"; attribute :>> lemma="TicketIdentityAlgebra.settleIdempotent"; }
part proof10:ProofRow { attribute :>> key="generic-terminal"; attribute :>> lemma="TicketIdentityAlgebra.existingOutcomeRetained"; }
part proof11:ProofRow { attribute :>> key="handle-other"; attribute :>> lemma="TicketIdentityAlgebra.dropOther"; }
part proof12:ProofRow { attribute :>> key="handle-idempotent"; attribute :>> lemma="TicketIdentityAlgebra.dropIdempotent"; }
part proof13:ProofRow { attribute :>> key="generation"; attribute :>> lemma="TicketIdentityAlgebra.differentGeneration"; }
part proof14:ProofRow { attribute :>> key="commit-projection"; attribute :>> lemma="TicketIdentityAlgebra.commitProjection0"; }
part proof15:ProofRow { attribute :>> key="query-projection"; attribute :>> lemma="TicketIdentityAlgebra.queryProjection0"; }
part proof16:ProofRow { attribute :>> key="other-slot"; attribute :>> lemma="TicketIdentityAlgebra.commit0PreservesOtherIdentity"; }
part def RouteRow { attribute component:String; attribute actionName:String; attribute lemma:String; attribute producerAnchor:String; attribute obligationId:String; }
part route0:RouteRow { attribute :>> component="settlement"; attribute :>> actionName="ticket_capability_retirement.commit0"; attribute :>> lemma="TicketCapability.commit0Preserves"; attribute :>> producerAnchor="will-invoke"; attribute :>> obligationId="TC-execution"; }
part route1:RouteRow { attribute :>> component="settlement"; attribute :>> actionName="ticket_capability_retirement.query0"; attribute :>> lemma="TicketCapability.query0Preserves"; attribute :>> producerAnchor="will-clear"; attribute :>> obligationId="TC-execution"; }
part route2:RouteRow { attribute :>> component="settlement"; attribute :>> actionName="ticket_capability_retirement.conflictingSettle0"; attribute :>> lemma="TicketCapability.conflictingSettle0Preserves"; attribute :>> producerAnchor="will-loop"; attribute :>> obligationId="TC-execution"; }
part route3:RouteRow { attribute :>> component="capture"; attribute :>> actionName="ticket_capability_retirement.reserve0"; attribute :>> lemma="TicketCapability.reserve0Preserves"; attribute :>> producerAnchor="restore-fast"; attribute :>> obligationId="TC-capture"; }
part route4:RouteRow { attribute :>> component="capture"; attribute :>> actionName="ticket_capability_retirement.reserve1"; attribute :>> lemma="TicketCapability.reserve1Preserves"; attribute :>> producerAnchor="resume"; attribute :>> obligationId="TC-capture"; }
part route5:RouteRow { attribute :>> component="capture"; attribute :>> actionName="ticket_capability_retirement.cloneHandle1"; attribute :>> lemma="TicketCapability.cloneHandle1Preserves"; attribute :>> producerAnchor="copy"; attribute :>> obligationId="TC-capture"; }
part route6:RouteRow { attribute :>> component="capture"; attribute :>> actionName="ticket_capability_retirement.dropHandle0"; attribute :>> lemma="TicketCapability.dropHandle0Preserves"; attribute :>> producerAnchor="unwrapped"; attribute :>> obligationId="TC-capture"; }
part route7:RouteRow { attribute :>> component="capture"; attribute :>> actionName="ticket_capability_retirement.discoverRawEscape"; attribute :>> lemma="TicketCapability.discoverRawEscapePreserves"; attribute :>> producerAnchor="serial-implode"; attribute :>> obligationId="TC-capture"; }
part route8:RouteRow { attribute :>> component="capture"; attribute :>> actionName="ticket_capability_retirement.closeAuthority"; attribute :>> lemma="TicketCapability.closeAuthorityPreserves"; attribute :>> producerAnchor="reify"; attribute :>> obligationId="TC-capture"; }
part route9:RouteRow { attribute :>> component="roots"; attribute :>> actionName="ticket_capability_retirement.returnNative0"; attribute :>> lemma="TicketCapability.returnNative0Preserves"; attribute :>> producerAnchor="rc-release"; attribute :>> obligationId="TC-roots"; }
part route10:RouteRow { attribute :>> component="roots"; attribute :>> actionName="ticket_capability_retirement.unpinScanner0"; attribute :>> lemma="TicketCapability.unpinScanner0Preserves"; attribute :>> producerAnchor="rc-scan"; attribute :>> obligationId="TC-roots"; }
part route11:RouteRow { attribute :>> component="roots"; attribute :>> actionName="ticket_capability_retirement.retireRoot"; attribute :>> lemma="TicketCapability.retireRootPreserves"; attribute :>> producerAnchor="frame-scan"; attribute :>> obligationId="TC-roots"; }
part def Need { attribute obligationId:String; attribute kind:String; attribute subjectPath:String; attribute subjectScope:String; ref owner:Owner; }
part formal:Need { attribute :>> obligationId="TC-formal"; attribute :>> kind="induction"; attribute :>> subjectPath="dev/refactoring/modern-c/models/lean/TicketCapability.lean"; attribute :>> subjectScope="finite identity-aware product safety and step terminal immutability"; ref :>> owner=settlementOwner; }
part algebra:Need { attribute :>> obligationId="TC-algebra"; attribute :>> kind="algebra"; attribute :>> subjectPath="dev/refactoring/modern-c/models/lean/TicketIdentityAlgebra.lean"; attribute :>> subjectScope="arbitrary-key mathematical operations and stated concrete commit/query projection"; ref :>> owner=settlementOwner; }
part execution:Need { attribute :>> obligationId="TC-execution"; attribute :>> kind="source"; attribute :>> subjectPath="vendor/gambit/lib/_kernel.scm"; attribute :>> subjectScope="real trusted executor ExitWitness and stable TicketId settlement/query source refinement"; ref :>> owner=settlementOwner; }
part capture:Need { attribute :>> obligationId="TC-capture"; attribute :>> kind="source"; attribute :>> subjectPath="vendor/gambit/lib/_thread.scm"; attribute :>> subjectScope="all restore/copy/import/raw aliases and real managed-authority retirement signer"; ref :>> owner=captureOwner; }
part roots:Need { attribute :>> obligationId="TC-roots"; attribute :>> kind="source"; attribute :>> subjectPath="vendor/gambit/lib/memory/rc-roots.inc"; attribute :>> subjectScope="moving-GC root transfer and exact scanner/native-borrow retirement source refinement"; ref :>> owner=rootsOwner; }
part platform:Need { attribute :>> obligationId="TC-platform"; attribute :>> kind="platform"; attribute :>> subjectPath="dev/refactoring/modern-c/language-baseline-design.org"; attribute :>> subjectScope="C23 atomic publication, finite keys/overflow/ABA and matching Darwin generated profile"; ref :>> owner=settlementOwner; }
part emission:Need { attribute :>> obligationId="TC-emission"; attribute :>> kind="equivalence"; attribute :>> subjectPath="dev/refactoring/modern-c/will-action-drain-design.org"; attribute :>> subjectScope="complete effect/creator/carry/exception and legacy observer equivalence before retiring helper"; ref :>> owner=captureOwner; }
}
