package GambitFormatterLegalOutput { private import ScalarValues::*;
part def SourceRow { attribute key:String; attribute path:String; attribute needle:String; attribute obligation:String; }
part source0:SourceRow { attribute :>> key="igsc"; attribute :>> path="vendor/gambit/gsc/igsc.scm"; attribute :>> needle="\"_gscdebug\""; attribute :>> obligation="Hook is loaded by the interpreted compiler debug session, not automatically by every gxc/gsc mode"; }
part source1:SourceRow { attribute :>> key="env-init"; attribute :>> path="vendor/gambit/gsc/_env.scm"; attribute :>> needle="(define (env.begin!)"; attribute :>> obligation="Initialize real stamp producer before make-temp-var"; }
part source2:SourceRow { attribute :>> key="var-producer"; attribute :>> path="vendor/gambit/gsc/_env.scm"; attribute :>> needle="(define (make-temp-var name)"; attribute :>> obligation="Real VAR producer preserves constructor invariants for interned long symbol"; }
part source3:SourceRow { attribute :>> key="var-constructor"; attribute :>> path="vendor/gambit/gsc/_envadt.scm"; attribute :>> needle="(vector var-tag name bound refs sets source #f #f (next-var-stamp) #f #f temp?)"; attribute :>> obligation="Valid VAR, no tag forgery"; }
part source4:SourceRow { attribute :>> key="var-predicate"; attribute :>> path="vendor/gambit/gsc/_envadt.scm"; attribute :>> needle="(define (var? x)"; attribute :>> obligation="Matches actual vector/tag"; }
part source5:SourceRow { attribute :>> key="save"; attribute :>> path="vendor/gambit/gsc/_gscdebug.scm"; attribute :>> needle="(let ((save-wr ##wr))"; attribute :>> obligation="Capture current global H per invocation"; }
part source6:SourceRow { attribute :>> key="install"; attribute :>> path="vendor/gambit/gsc/_gscdebug.scm"; attribute :>> needle="(##wr-set! ##default-wr)"; attribute :>> obligation="Set D before output"; }
part source7:SourceRow { attribute :>> key="restore"; attribute :>> path="vendor/gambit/gsc/_gscdebug.scm"; attribute :>> needle="(##wr-set! save-wr)"; attribute :>> obligation="Plain restore retains old lexical save on each resume"; }
part source8:SourceRow { attribute :>> key="var-payload"; attribute :>> path="vendor/gambit/gsc/_gscdebug.scm"; attribute :>> needle="(list 'VAR: (c#var-name obj))"; attribute :>> obligation="No PTREE conversion/eval needed for chosen legal branch"; }
part source9:SourceRow { attribute :>> key="write-simple"; attribute :>> path="vendor/gambit/lib/_io.scm"; attribute :>> needle="(define-prim (write-simple"; attribute :>> obligation="Public checked API reaches raw VAR"; }
part source10:SourceRow { attribute :>> key="write-style"; attribute :>> path="vendor/gambit/lib/_io.scm"; attribute :>> needle="(define-prim (##write-with-style"; attribute :>> obligation="Character port path supplies write environment"; }
part source11:SourceRow { attribute :>> key="make-we"; attribute :>> path="vendor/gambit/lib/_io.scm"; attribute :>> needle="((macro-object-port-write-datum port) port obj we2)"; attribute :>> obligation="Actual output dispatch"; }
part source12:SourceRow { attribute :>> key="string-dispatch"; attribute :>> path="vendor/gambit/lib/_io.scm"; attribute :>> needle="(define (write-datum port obj we)"; attribute :>> obligation="String method dispatch must be disambiguated by source interval"; }
part source13:SourceRow { attribute :>> key="symbol"; attribute :>> path="vendor/gambit/lib/_io.scm"; attribute :>> needle="(define-prim (##wr-symbol we obj)"; attribute :>> obligation="Default symbol writer emits long name"; }
part source14:SourceRow { attribute :>> key="substring"; attribute :>> path="vendor/gambit/lib/_io.scm"; attribute :>> needle="(define-prim (##write-substring str start end port)"; attribute :>> obligation="Fully buffered path fills then drains character buffer"; }
part source15:SourceRow { attribute :>> key="chunk"; attribute :>> path="vendor/gambit/lib/_io.scm"; attribute :>> needle="(define chunk-size 32)"; attribute :>> obligation="String-port chunk size"; }
part source16:SourceRow { attribute :>> key="capacity"; attribute :>> path="vendor/gambit/lib/_io.scm"; attribute :>> needle="(##fx< capacity unread)"; attribute :>> obligation="Strict capacity pressure from published chunk count"; }
part source17:SourceRow { attribute :>> key="timeout-call"; attribute :>> path="vendor/gambit/lib/_io.scm"; attribute :>> needle="((macro-port-wtimeout-thunk port))"; attribute :>> obligation="Actual user callback before relock"; }
part source18:SourceRow { attribute :>> key="relock"; attribute :>> path="vendor/gambit/lib/_io.scm"; attribute :>> needle="(macro-port-mutex-lock! port)"; attribute :>> obligation="Must select relock after timeout, not arbitrary matching occurrence"; }
part source19:SourceRow { attribute :>> key="pipe-constructor"; attribute :>> path="vendor/gambit/lib/_io.scm"; attribute :>> needle="(define-prim (,##make-vect-pipe-port"; attribute :>> obligation="Generated string-pipe peer buffer exchange"; }
part source20:SourceRow { attribute :>> key="pipe-export"; attribute :>> path="vendor/gambit/lib/_io.scm"; attribute :>> needle="(define-prim (,open-vect-pipe"; attribute :>> obligation="Real public constructor generated from string instantiation"; }
part source21:SourceRow { attribute :>> key="timeout-set"; attribute :>> path="vendor/gambit/lib/_io.scm"; attribute :>> needle="(define-prim (output-port-timeout-set!"; attribute :>> obligation="Public accepts procedure and nonpositive timeout"; }
part source22:SourceRow { attribute :>> key="nonpositive"; attribute :>> path="vendor/gambit/lib/_thread.scm"; attribute :>> needle="(define-prim (##absrel-timeout->timeout"; attribute :>> obligation="Integer zero converts to false / immediate wait path"; }
part source23:SourceRow { attribute :>> key="wait-unlock"; attribute :>> path="vendor/gambit/lib/_thread.scm"; attribute :>> needle="(define-prim (##mutex-signal-and-condvar-wait!"; attribute :>> obligation="Both SMP and non-SMP false-timeout arms unlock before returning false"; }
part source24:SourceRow { attribute :>> key="handler-install"; attribute :>> path="vendor/gambit/lib/_thread.scm"; attribute :>> needle="(define-prim (with-exception-handler handler thunk)"; attribute :>> obligation="Dynamic binding uses Gambit original handler"; }
part source25:SourceRow { attribute :>> key="raise"; attribute :>> path="vendor/gambit/lib/_thread#.scm"; attribute :>> needle="(##define-macro (macro-raise obj)"; attribute :>> obligation="Native Gambit handler direct call may return; distinct R7RS wrapper"; }
part source26:SourceRow { attribute :>> key="capture"; attribute :>> path="vendor/gambit/lib/_thread.scm"; attribute :>> needle="(define-prim (call-with-current-continuation"; attribute :>> obligation="Real public capture API"; }
part source27:SourceRow { attribute :>> key="r7rs"; attribute :>> path="vendor/gambit/lib/_thread.scm"; attribute :>> needle="(define (##r7rs-with-exception-handler handler thunk)"; attribute :>> obligation="Do not substitute R7RS noncontinuable semantics"; }
part source28:SourceRow { attribute :>> key="target-begin"; attribute :>> path="vendor/gambit/gsc/_t-c-1.scm"; attribute :>> needle="(define (targ-heap-begin!)"; attribute :>> obligation="Live target registry required for delayed writer"; }
part source29:SourceRow { attribute :>> key="target-end"; attribute :>> path="vendor/gambit/gsc/_t-c-1.scm"; attribute :>> needle="(set! targ-glo-vars #f)"; attribute :>> obligation="Ended registry is not a new usable table"; }
part source30:SourceRow { attribute :>> key="resource-call"; attribute :>> path="vendor/gambit/gsc/_t-c-1.scm"; attribute :>> needle="(define (targ-use-glo glo supply?)"; attribute :>> obligation="Actual callback-callable global lookup and write"; }
part source31:SourceRow { attribute :>> key="canonical"; attribute :>> path="vendor/gambit/gsc/_t-c-1.scm"; attribute :>> needle="(targ-rsrc-demanders-set! (cdr x) '(\"\"))"; attribute :>> obligation="Same entry canonicalization"; }
part source32:SourceRow { attribute :>> key="resource-raw"; attribute :>> path="vendor/gambit/gsc/_t-c-1.scm"; attribute :>> needle="(vector-set! r 1 demanders)"; attribute :>> obligation="Raw alias can erase canonicality"; }
part source33:SourceRow { attribute :>> key="emitter"; attribute :>> path="vendor/gambit/gsc/_t-c-1.scm"; attribute :>> needle="(def-mod-prm-glo \"DEF_MOD_GLO\")"; attribute :>> obligation="Normal scalar emission still does not directly enter VAR branch"; }
part source34:SourceRow { attribute :>> key="doc-pipe"; attribute :>> path="vendor/gambit/doc/gambit.txi"; attribute :>> needle="@deffnx procedure open-string-pipe"; attribute :>> obligation="Documented legal user interface"; }
part source35:SourceRow { attribute :>> key="doc-timeout"; attribute :>> path="vendor/gambit/doc/gambit.txi"; attribute :>> needle="@deffnx procedure output-port-timeout-set!"; attribute :>> obligation="Documentation is not substituted for EAGAIN source behavior"; }
part def WindowRow { attribute key:String; attribute cause:String; attribute effect:String; attribute reachability:String; attribute gap:String; }
part window0:WindowRow { attribute :>> key="legal-witness"; attribute :>> cause="Valid make-temp-var + write-simple + string-pipe capacity 1 + timeout 0"; attribute :>> effect="Callback can occur inside temporary D interval"; attribute :>> reachability="Source-composable legal igsc debug-session capability witness"; attribute :>> gap="No assertion this handler exists in stock compilation; no native run"; }
part window1:WindowRow { attribute :>> key="handler-capture"; attribute :>> cause="User timeout thunk explicitly raises to original Gambit handler"; attribute :>> effect="call/cc captures output stack then escapes; future resumes retain save"; attribute :>> reachability="Legal user-installed extension recipe, not existing stock handler body"; attribute :>> gap="Per-resume mutable writeenv/port frontier and generated roots not fully simulated"; }
part window2:WindowRow { attribute :>> key="metadata"; attribute :>> cause="Delayed callback tail calls targ-use-glo after handler return"; attribute :>> effect="One genuine execution per resume; current target table selected at call time"; attribute :>> reachability="Requires live initialized target and interned symbol capability"; attribute :>> gap="Not proof of callback between the selected emitter calls"; }
part window3:WindowRow { attribute :>> key="timeout-doc"; attribute :>> cause="Timeout thunk returns false"; attribute :>> effect="Some source paths return false/EAGAIN instead of automatically raising"; attribute :>> reachability="Do not use this as exception producer"; attribute :>> gap="Chosen witness explicitly raises; no documentation-only exception edge"; }
part def ClaimRow { attribute key:String; attribute mechanism:String; attribute condition:String; attribute result:String; attribute gap:String; }
part claim0:ClaimRow { attribute :>> key="escape"; attribute :>> mechanism="Capture and escape while D is globally installed"; attribute :>> condition="Valid VAR, actual timeout producer, original Gambit handler"; attribute :>> result="Plain restore is skipped"; attribute :>> gap="Source construction, not native reproduction"; }
part claim1:ClaimRow { attribute :>> key="overwrite"; attribute :>> mechanism="Install N while captured frame is parked; resume without reinstalling D"; attribute :>> condition="Peer releases pressure; remaining output returns and roots survive"; attribute :>> result="Saved H can overwrite N on each completion"; attribute :>> gap="Full mutable I/O multi-shot simulation remains OPEN"; }
part claim2:ClaimRow { attribute :>> key="canonical"; attribute :>> mechanism="Delayed named write preserves canonical demand only within same entry"; attribute :>> condition="Target epoch unchanged; named writer only"; attribute :>> result="No value need for second normalization in qualified profile"; attribute :>> gap="Fault/output and alias closure remain OPEN"; }
part claim3:ClaimRow { attribute :>> key="different-epoch"; attribute :>> mechanism="Callback dynamically resolves current targ-glo-vars"; attribute :>> condition="New heap begin before resume"; attribute :>> result="New registry is canonical, but old plan receipt invalid"; attribute :>> gap="Cannot infer same-entry equivalence from equal field values"; }
part def GainRow { attribute key:String; attribute avoided:String; attribute added:String; attribute condition:String; }
part gain0:GainRow { attribute :>> key="view"; attribute :>> avoided="Two temporary global writes per special invocation"; attribute :>> added="Owned WriterView across 20 recursive applications and multi-shot roots"; attribute :>> condition="All consumers migrated; explicit changed registration interleavings"; }
part gain1:GainRow { attribute :>> key="second"; attribute :>> avoided="At most p*N second normalizations"; attribute :>> added="Qualification Cq and W resolver dispatches at Cv"; attribute :>> condition="p*N*Cn > Cq+W*Cv plus source/observation closure"; }
part gain2:GainRow { attribute :>> key="metadata"; attribute :>> avoided="Repeated validation may share session-level effect policy"; attribute :>> added="Registry epoch identity, callback/capture custody and drain"; attribute :>> condition="No target table retirement while callback can still use targ-use-glo"; }
part gain3:GainRow { attribute :>> key="evidence"; attribute :>> avoided="No longer treat malformed PTREE or OS write error as necessary trigger"; attribute :>> added="Bounded pipe/frontier and handler source refinement"; attribute :>> condition="Legal configurable source witness only; no end-to-end speed claim"; }
part def ContractRow { attribute fromNode:String; attribute toNode:String; attribute custody:String; }
part contract0:ContractRow { attribute :>> fromNode="Valid VAR"; attribute :>> toNode="write-simple"; attribute :>> custody="real constructor"; }
part contract1:ContractRow { attribute :>> fromNode="write-simple"; attribute :>> toNode="Debug hook"; attribute :>> custody="string-port dispatch"; }
part contract2:ContractRow { attribute :>> fromNode="Debug hook"; attribute :>> toNode="Default writer interval"; attribute :>> custody="save H; install D"; }
part contract3:ContractRow { attribute :>> fromNode="Default writer interval"; attribute :>> toNode="Bounded pipe"; attribute :>> custody="32-char chunks"; }
part contract4:ContractRow { attribute :>> fromNode="Bounded pipe"; attribute :>> toNode="Timeout thunk"; attribute :>> custody="pressure; unlock"; }
part contract5:ContractRow { attribute :>> fromNode="Timeout thunk"; attribute :>> toNode="Gambit handler"; attribute :>> custody="explicit raise"; }
part contract6:ContractRow { attribute :>> fromNode="Gambit handler"; attribute :>> toNode="Captured continuation"; attribute :>> custody="capture; escape"; }
part contract7:ContractRow { attribute :>> fromNode="Captured continuation"; attribute :>> toNode="Delayed metadata tail"; attribute :>> custody="resume after peer drain"; }
part contract8:ContractRow { attribute :>> fromNode="Delayed metadata tail"; attribute :>> toNode="Plain restoration"; attribute :>> custody="callback return; relock/unlock"; }
part contract9:ContractRow { attribute :>> fromNode="New formatter N"; attribute :>> toNode="Plain restoration"; attribute :>> custody="H overwrites N"; }
part contract10:ContractRow { attribute :>> fromNode="Delayed metadata tail"; attribute :>> toNode="Registry epoch"; attribute :>> custody="current table lookup"; }
part contract11:ContractRow { attribute :>> fromNode="Registry epoch"; attribute :>> toNode="Retirement gate"; attribute :>> custody="same entry required"; }
part contract12:ContractRow { attribute :>> fromNode="Capture roots"; attribute :>> toNode="Retirement gate"; attribute :>> custody="drain or qualified detach"; }
part contract13:ContractRow { attribute :>> fromNode="Retirement gate"; attribute :>> toNode="Second normalization"; attribute :>> custody="conditional value + observation"; }
part def BindingRow { attribute actionName:String; attribute lemma:String; attribute scope:String; }
part binding0:BindingRow { attribute :>> actionName="formatter_legal_output.prepare"; attribute :>> lemma="FormatterLegal.preparePreserves"; attribute :>> scope="Conditional source witness abstraction; mutable frontier and native refinement external"; }
part binding1:BindingRow { attribute :>> actionName="formatter_legal_output.enter"; attribute :>> lemma="FormatterLegal.enterPreserves"; attribute :>> scope="Conditional source witness abstraction; mutable frontier and native refinement external"; }
part binding2:BindingRow { attribute :>> actionName="formatter_legal_output.fill"; attribute :>> lemma="FormatterLegal.fillPreserves"; attribute :>> scope="Conditional source witness abstraction; mutable frontier and native refinement external"; }
part binding3:BindingRow { attribute :>> actionName="formatter_legal_output.timeout"; attribute :>> lemma="FormatterLegal.timeoutPreserves"; attribute :>> scope="Conditional source witness abstraction; mutable frontier and native refinement external"; }
part binding4:BindingRow { attribute :>> actionName="formatter_legal_output.captureEscape"; attribute :>> lemma="FormatterLegal.captureEscapePreserves"; attribute :>> scope="Conditional source witness abstraction; mutable frontier and native refinement external"; }
part binding5:BindingRow { attribute :>> actionName="formatter_legal_output.publish"; attribute :>> lemma="FormatterLegal.publishPreserves"; attribute :>> scope="Conditional source witness abstraction; mutable frontier and native refinement external"; }
part binding6:BindingRow { attribute :>> actionName="formatter_legal_output.drain"; attribute :>> lemma="FormatterLegal.drainPreserves"; attribute :>> scope="Conditional source witness abstraction; mutable frontier and native refinement external"; }
part binding7:BindingRow { attribute :>> actionName="formatter_legal_output.resume"; attribute :>> lemma="FormatterLegal.resumePreserves"; attribute :>> scope="Conditional source witness abstraction; mutable frontier and native refinement external"; }
part binding8:BindingRow { attribute :>> actionName="formatter_legal_output.returnHandler"; attribute :>> lemma="FormatterLegal.returnHandlerPreserves"; attribute :>> scope="Conditional source witness abstraction; mutable frontier and native refinement external"; }
part binding9:BindingRow { attribute :>> actionName="formatter_legal_output.namedTail"; attribute :>> lemma="FormatterLegal.namedTailPreserves"; attribute :>> scope="Conditional source witness abstraction; mutable frontier and native refinement external"; }
part binding10:BindingRow { attribute :>> actionName="formatter_legal_output.rawTail"; attribute :>> lemma="FormatterLegal.rawTailPreserves"; attribute :>> scope="Conditional source witness abstraction; mutable frontier and native refinement external"; }
part binding11:BindingRow { attribute :>> actionName="formatter_legal_output.rejectDead"; attribute :>> lemma="FormatterLegal.rejectDeadPreserves"; attribute :>> scope="Conditional source witness abstraction; mutable frontier and native refinement external"; }
part binding12:BindingRow { attribute :>> actionName="formatter_legal_output.resetRegistry"; attribute :>> lemma="FormatterLegal.resetRegistryPreserves"; attribute :>> scope="Conditional source witness abstraction; mutable frontier and native refinement external"; }
part binding13:BindingRow { attribute :>> actionName="formatter_legal_output.endRegistry"; attribute :>> lemma="FormatterLegal.endRegistryPreserves"; attribute :>> scope="Conditional source witness abstraction; mutable frontier and native refinement external"; }
part binding14:BindingRow { attribute :>> actionName="formatter_legal_output.callbackReturns"; attribute :>> lemma="FormatterLegal.callbackReturnsPreserves"; attribute :>> scope="Conditional source witness abstraction; mutable frontier and native refinement external"; }
part binding15:BindingRow { attribute :>> actionName="formatter_legal_output.finish"; attribute :>> lemma="FormatterLegal.finishPreserves"; attribute :>> scope="Conditional source witness abstraction; mutable frontier and native refinement external"; }
part binding16:BindingRow { attribute :>> actionName="formatter_legal_output.closeAdmission"; attribute :>> lemma="FormatterLegal.closeAdmissionPreserves"; attribute :>> scope="Conditional source witness abstraction; mutable frontier and native refinement external"; }
part binding17:BindingRow { attribute :>> actionName="formatter_legal_output.detach"; attribute :>> lemma="FormatterLegal.detachPreserves"; attribute :>> scope="Conditional source witness abstraction; mutable frontier and native refinement external"; }
part binding18:BindingRow { attribute :>> actionName="formatter_legal_output.attest"; attribute :>> lemma="FormatterLegal.attestPreserves"; attribute :>> scope="Conditional source witness abstraction; mutable frontier and native refinement external"; }
part binding19:BindingRow { attribute :>> actionName="formatter_legal_output.issue"; attribute :>> lemma="FormatterLegal.issuePreserves"; attribute :>> scope="Conditional source witness abstraction; mutable frontier and native refinement external"; }
part binding20:BindingRow { attribute :>> actionName="formatter_legal_output.attemptStale"; attribute :>> lemma="FormatterLegal.attemptStalePreserves"; attribute :>> scope="Conditional source witness abstraction; mutable frontier and native refinement external"; }
part def ProofRow { attribute key:String; attribute lemma:String; }
part proof0:ProofRow { attribute :>> key="steps"; attribute :>> lemma="FormatterLegal.stepPreserves"; }
part proof1:ProofRow { attribute :>> key="reachable"; attribute :>> lemma="FormatterLegal.reachableSafe"; }
part proof2:ProofRow { attribute :>> key="drain"; attribute :>> lemma="FormatterLegal.permitNeedsDrain"; }
part proof3:ProofRow { attribute :>> key="epoch"; attribute :>> lemma="FormatterLegal.permitNeedsEpoch"; }
part proof4:ProofRow { attribute :>> key="save"; attribute :>> lemma="FormatterLegal.resumeKeepsSaved"; }
part proof5:ProofRow { attribute :>> key="writer"; attribute :>> lemma="FormatterLegal.resumeKeepsWriter"; }
part proof6:ProofRow { attribute :>> key="chunk"; attribute :>> lemma="FormatterLegalAlgebra.stringChunkExceedsCapacity"; }
part proof7:ProofRow { attribute :>> key="drained"; attribute :>> lemma="FormatterLegalAlgebra.fullDrainClearsPressure"; }
part proof8:ProofRow { attribute :>> key="replay"; attribute :>> lemma="FormatterLegalAlgebra.replayRestoresCaptured"; }
part proof9:ProofRow { attribute :>> key="canonical"; attribute :>> lemma="FormatterLegalAlgebra.secondUnderNamedWriters"; }
part def MigrationRow { attribute key:String; attribute producerAnchor:String; attribute consumerAnchor:String; attribute actionName:String; attribute lemma:String; }
part migration0:MigrationRow { attribute :>> key="entry"; attribute :>> producerAnchor="var-constructor"; attribute :>> consumerAnchor="write-simple"; attribute :>> actionName="formatter_legal_output.enter"; attribute :>> lemma="FormatterLegal.enterPreserves"; }
part migration1:MigrationRow { attribute :>> key="pressure"; attribute :>> producerAnchor="substring"; attribute :>> consumerAnchor="capacity"; attribute :>> actionName="formatter_legal_output.timeout"; attribute :>> lemma="FormatterLegalAlgebra.stringChunkExceedsCapacity"; }
part migration2:MigrationRow { attribute :>> key="capture"; attribute :>> producerAnchor="timeout-call"; attribute :>> consumerAnchor="capture"; attribute :>> actionName="formatter_legal_output.captureEscape"; attribute :>> lemma="FormatterLegal.captureEscapePreserves"; }
part migration3:MigrationRow { attribute :>> key="resume"; attribute :>> producerAnchor="capture"; attribute :>> consumerAnchor="restore"; attribute :>> actionName="formatter_legal_output.resume"; attribute :>> lemma="FormatterLegal.resumeKeepsSaved"; }
part migration4:MigrationRow { attribute :>> key="late-write"; attribute :>> producerAnchor="resource-call"; attribute :>> consumerAnchor="canonical"; attribute :>> actionName="formatter_legal_output.namedTail"; attribute :>> lemma="FormatterLegal.namedTailPreserves"; }
part migration5:MigrationRow { attribute :>> key="new-epoch"; attribute :>> producerAnchor="target-begin"; attribute :>> consumerAnchor="resource-call"; attribute :>> actionName="formatter_legal_output.resetRegistry"; attribute :>> lemma="FormatterLegal.permitNeedsEpoch"; }
part migration6:MigrationRow { attribute :>> key="retire"; attribute :>> producerAnchor="resource-call"; attribute :>> consumerAnchor="emitter"; attribute :>> actionName="formatter_legal_output.issue"; attribute :>> lemma="FormatterLegal.permitNeedsDrain"; }
part def InventoryRow { attribute key:String; attribute path:String; attribute pattern:String; attribute count:String; attribute scope:String; }
part inventory0:InventoryRow { attribute :>> key="debug-capture"; attribute :>> path="vendor/gambit/gsc/_gscdebug.scm"; attribute :>> pattern="\\(call-with-current-continuation|\\(dynamic-wind"; attribute :>> count="0"; attribute :>> scope="Lexical only; user callback is supplied externally"; }
part inventory1:InventoryRow { attribute :>> key="debug-direct-resource"; attribute :>> path="vendor/gambit/gsc/_gscdebug.scm"; attribute :>> pattern="targ-use-glo|targ-rsrc-"; attribute :>> count="0"; attribute :>> scope="No direct resource writer in hook; indirect user authority remains open"; }
part inventory2:InventoryRow { attribute :>> key="wait-definitions"; attribute :>> path="vendor/gambit/lib/_thread.scm"; attribute :>> pattern="\\(define-prim \\(##mutex-signal-and-condvar-wait!"; attribute :>> count="2"; attribute :>> scope="SMP/non-SMP branches both inspected"; }
part def PolicyRow { attribute key:String; attribute writerClass:String; attribute assumptions:String; attribute firstExpected:String; attribute secondExpected:String; attribute scope:String; }
part policy0:PolicyRow { attribute :>> key="current"; attribute :>> writerClass="named-only"; attribute :>> assumptions=""; attribute :>> firstExpected="false"; attribute :>> secondExpected="false"; attribute :>> scope="Assumption profile only; not actual source/native permission"; }
part policy1:PolicyRow { attribute :>> key="synthetic-qualified"; attribute :>> writerClass="named-only"; attribute :>> assumptions="first-retained;same-entry;canonical-writers;formatter-profile-current;restore-settled;registration-closed;borrowers-drained;captures-retired;fault-equivalence;legal-entry-qualified;output-equivalence"; attribute :>> firstExpected="false"; attribute :>> secondExpected="true"; attribute :>> scope="Assumption profile only; not actual source/native permission"; }
part policy2:PolicyRow { attribute :>> key="synthetic-live-capture"; attribute :>> writerClass="named-only"; attribute :>> assumptions="first-retained;same-entry;canonical-writers;formatter-profile-current;restore-settled;registration-closed;borrowers-drained;fault-equivalence;legal-entry-qualified;output-equivalence"; attribute :>> firstExpected="false"; attribute :>> secondExpected="false"; attribute :>> scope="Assumption profile only; not actual source/native permission"; }
part policy3:PolicyRow { attribute :>> key="synthetic-new-registry"; attribute :>> writerClass="named-only"; attribute :>> assumptions="first-retained;canonical-writers;formatter-profile-current;restore-settled;registration-closed;borrowers-drained;captures-retired;fault-equivalence;legal-entry-qualified;output-equivalence"; attribute :>> firstExpected="false"; attribute :>> secondExpected="false"; attribute :>> scope="Assumption profile only; not actual source/native permission"; }
part policy4:PolicyRow { attribute :>> key="synthetic-unknown-handler"; attribute :>> writerClass="named-only"; attribute :>> assumptions="first-retained;same-entry;canonical-writers;formatter-profile-current;restore-settled;registration-closed;borrowers-drained;captures-retired;legal-entry-qualified;output-equivalence"; attribute :>> firstExpected="false"; attribute :>> secondExpected="false"; attribute :>> scope="Assumption profile only; not actual source/native permission"; }
part policy5:PolicyRow { attribute :>> key="synthetic-output-gap"; attribute :>> writerClass="named-only"; attribute :>> assumptions="first-retained;same-entry;canonical-writers;formatter-profile-current;restore-settled;registration-closed;borrowers-drained;captures-retired;fault-equivalence;legal-entry-qualified"; attribute :>> firstExpected="false"; attribute :>> secondExpected="false"; attribute :>> scope="Assumption profile only; not actual source/native permission"; }
part policy6:PolicyRow { attribute :>> key="synthetic-no-entry-proof"; attribute :>> writerClass="named-only"; attribute :>> assumptions="first-retained;same-entry;canonical-writers;formatter-profile-current;restore-settled;registration-closed;borrowers-drained;captures-retired;fault-equivalence;output-equivalence"; attribute :>> firstExpected="false"; attribute :>> secondExpected="false"; attribute :>> scope="Assumption profile only; not actual source/native permission"; }
part history:GambitAssuranceRouting::ModelNeed { ref part :>> owner=GambitAssuranceRelations::modelUse2; attribute :>> obligationId="FL-history"; attribute :>> kind="interleaving"; attribute :>> subjectPath="dev/refactoring/modern-c/models/quint/formatter_legal_output.qnt"; attribute :>> subjectScope="16 histories including five negative controls; source-composed witness, not byte-exact execution"; attribute :>> premise="C23 design only; no runtime implementation or native tests"; }
part induction:GambitAssuranceRouting::ModelNeed { ref part :>> owner=GambitAssuranceRelations::modelUse2; attribute :>> obligationId="FL-induction"; attribute :>> kind="induction"; attribute :>> subjectPath="dev/refactoring/modern-c/models/lean/FormatterLegal.lean"; attribute :>> subjectScope="Every projected action preserves conditional custody and certificate invariant"; attribute :>> premise="C23 design only; no runtime implementation or native tests"; }
part algebra:GambitAssuranceRouting::ModelNeed { ref part :>> owner=GambitAssuranceRelations::modelUse2; attribute :>> obligationId="FL-algebra"; attribute :>> kind="induction"; attribute :>> subjectPath="dev/refactoring/modern-c/models/lean/FormatterLegalAlgebra.lean"; attribute :>> subjectScope="Chunk threshold, saved restoration and inherited named-writer value algebra"; attribute :>> premise="C23 design only; no runtime implementation or native tests"; }
part projection:GambitAssuranceRouting::ModelNeed { ref part :>> owner=GambitAssuranceRelations::modelUse2; attribute :>> obligationId="FL-projection"; attribute :>> kind="restricted-projection"; attribute :>> subjectPath="dev/refactoring/modern-c/models/lean/FormatterLegalAst.lean"; attribute :>> subjectScope="Typed IR binding, operator, field and action roster checks; extractor trusted"; attribute :>> premise="C23 design only; no runtime implementation or native tests"; }
part source:GambitAssuranceRouting::ModelNeed { ref part :>> owner=GambitAssuranceRelations::modelUse2; attribute :>> obligationId="FL-source"; attribute :>> kind="source-refinement"; attribute :>> subjectPath="dev/refactoring/modern-c/formatter-legal-output-design.org"; attribute :>> subjectScope="Exact mutable I/O frontiers, application-installed callback closure, selected artifact and resume endpoints OPEN"; attribute :>> premise="C23 design only; no runtime implementation or native tests"; }
part exceptions:GambitAssuranceRouting::ModelNeed { ref part :>> owner=GambitAssuranceRelations::modelUse2; attribute :>> obligationId="FL-exceptions"; attribute :>> kind="exception-equivalence"; attribute :>> subjectPath="dev/refactoring/modern-c/formatter-legal-output-design.org"; attribute :>> subjectScope="Original Gambit handler distinguished from R7RS; all output/fault prefixes OPEN"; attribute :>> premise="C23 design only; no runtime implementation or native tests"; }
part platform:GambitAssuranceRouting::ModelNeed { ref part :>> owner=GambitAssuranceRelations::modelUse2; attribute :>> obligationId="FL-platform"; attribute :>> kind="c23-platform-qualification"; attribute :>> subjectPath="dev/refactoring/modern-c/language-baseline-design.org"; attribute :>> subjectScope="Native ownership, generation publication, GC roots and target support OPEN"; attribute :>> premise="C23 design only; no runtime implementation or native tests"; }
part emission:GambitAssuranceRouting::ModelNeed { ref part :>> owner=GambitAssuranceRelations::modelUse2; attribute :>> obligationId="FL-emission"; attribute :>> kind="emitter-fidelity"; attribute :>> subjectPath="dev/refactoring/modern-c/formatter-legal-output-design.org"; attribute :>> subjectScope="Witness is debug-session capable; selected scalar emission interposition remains OPEN"; attribute :>> premise="C23 design only; no runtime implementation or native tests"; }
part def SliceRow { attribute key:String; attribute path:String; attribute beginNeedle:String; attribute endNeedle:String; attribute callNeedle:String; attribute occurrence:String; attribute actionName:String; attribute lemma:String; }
part slice0:SliceRow { attribute :>> key="concrete-string"; attribute :>> path="vendor/gambit/lib/_io.scm"; attribute :>> beginNeedle="(define-prim (##make-string-port"; attribute :>> endNeedle=";;; Implementation of u8vector ports."; attribute :>> callNeedle="(##wr we obj)"; attribute :>> occurrence="0"; attribute :>> actionName="formatter_legal_output.enter"; attribute :>> lemma="FormatterLegal.enterPreserves"; }
part slice1:SliceRow { attribute :>> key="generic-timeout"; attribute :>> path="vendor/gambit/lib/_io.scm"; attribute :>> beginNeedle="(define (,',vect-wbuf-drain port)"; attribute :>> endNeedle="(define (name port)"; attribute :>> callNeedle="((macro-port-wtimeout-thunk port))"; attribute :>> occurrence="0"; attribute :>> actionName="formatter_legal_output.timeout"; attribute :>> lemma="FormatterLegal.timeoutPreserves"; }
part slice2:SliceRow { attribute :>> key="smp-wait"; attribute :>> path="vendor/gambit/lib/_thread.scm"; attribute :>> beginNeedle="(define-prim (##mutex-signal-and-condvar-wait!"; attribute :>> endNeedle="(define-prim (##wait-for-io!"; attribute :>> callNeedle="(macro-mutex-unlock-no-reschedule! mutex)"; attribute :>> occurrence="0"; attribute :>> actionName="formatter_legal_output.captureEscape"; attribute :>> lemma="FormatterLegal.captureEscapePreserves"; }
part slice3:SliceRow { attribute :>> key="non-smp-wait"; attribute :>> path="vendor/gambit/lib/_thread.scm"; attribute :>> beginNeedle="(define-prim (##mutex-signal-and-condvar-wait!"; attribute :>> endNeedle="(define-prim (##wait-for-io!"; attribute :>> callNeedle="(macro-mutex-unlock-no-reschedule! mutex)"; attribute :>> occurrence="1"; attribute :>> actionName="formatter_legal_output.captureEscape"; attribute :>> lemma="FormatterLegal.captureEscapePreserves"; }
part slice4:SliceRow { attribute :>> key="original-raise"; attribute :>> path="vendor/gambit/lib/_thread#.scm"; attribute :>> beginNeedle="(##define-macro (macro-raise obj)"; attribute :>> endNeedle="(##define-macro (macro-abort obj)"; attribute :>> callNeedle="((macro-current-exception-handler) obj)"; attribute :>> occurrence="0"; attribute :>> actionName="formatter_legal_output.returnHandler"; attribute :>> lemma="FormatterLegal.returnHandlerPreserves"; }
part slice5:SliceRow { attribute :>> key="named-existing"; attribute :>> path="vendor/gambit/gsc/_t-c-1.scm"; attribute :>> beginNeedle="(define (targ-use-glo glo supply?)"; attribute :>> endNeedle="(define (targ-glo-rsrc g)"; attribute :>> callNeedle="(targ-rsrc-demanders-set! (cdr x) '(\"\"))"; attribute :>> occurrence="0"; attribute :>> actionName="formatter_legal_output.namedTail"; attribute :>> lemma="FormatterLegalAlgebra.secondUnderNamedWriters"; }
part slice6:SliceRow { attribute :>> key="debug-restore"; attribute :>> path="vendor/gambit/gsc/_gscdebug.scm"; attribute :>> beginNeedle="(let ((save-wr ##wr))"; attribute :>> endNeedle="(##default-wr we obj))))"; attribute :>> callNeedle="(##wr-set! save-wr)"; attribute :>> occurrence="0"; attribute :>> actionName="formatter_legal_output.finish"; attribute :>> lemma="FormatterLegal.resumeKeepsSaved"; }
part source36:SourceRow { attribute :>> key="doc-native-raise"; attribute :>> path="vendor/gambit/doc/gambit.txi"; attribute :>> needle="continuation of the call to @code{raise} is invoked."; attribute :>> obligation="Gambit manual explicitly permits handler return; source agrees and differs from R7RS raise"; }
}
