package GambitSizeFamilyGuardGc { private import ScalarValues::*;
part def SourceRow { attribute key:String; attribute path:String; attribute needle:String; attribute obligation:String; }
part source0:SourceRow { attribute :>> key="sfun-prolog"; attribute :>> path="vendor/gambit/include/_gambit/foreign_conversion.h.in"; attribute :>> needle="#define ___BEGIN_SFUN_VOID(proc)"; attribute :>> obligation="marker allocated before input conversion; no conversion guard"; }
part source1:SourceRow { attribute :>> key="sfun-input"; attribute :>> path="vendor/gambit/include/_gambit/foreign_conversion.h.in"; attribute :>> needle="#define ___SFUN_ARG(i,arg)___PSSTK"; attribute :>> obligation="stack publication before call; not still-count release"; }
part source2:SourceRow { attribute :>> key="sfun-end"; attribute :>> path="vendor/gambit/include/_gambit/foreign_conversion.h.in"; attribute :>> needle="#define ___END_SFUN_SIZE_T_TO_SCMOBJ(c,s,i)}"; attribute :>> obligation="three family ENDs lack drop"; }
part source3:SourceRow { attribute :>> key="sfun-error"; attribute :>> path="vendor/gambit/include/_gambit/foreign_conversion.h.in"; attribute :>> needle="#define ___SFUN_ERROR_VOID"; attribute :>> obligation="retry calls and error propagation outlive argument scope"; }
part source4:SourceRow { attribute :>> key="sfun-finish"; attribute :>> path="vendor/gambit/include/_gambit/foreign_conversion.h.in"; attribute :>> needle="#define ___END_SFUN_VOID"; attribute :>> obligation="marker invalidation then propagate; not conversion guard"; }
part source5:SourceRow { attribute :>> key="cfun-result"; attribute :>> path="vendor/gambit/include/_gambit/foreign_conversion.h.in"; attribute :>> needle="#define ___CFUN_RESULT ___PSR1"; attribute :>> obligation="actual output root"; }
part source6:SourceRow { attribute :>> key="cfun-end"; attribute :>> path="vendor/gambit/include/_gambit/foreign_conversion.h.in"; attribute :>> needle="#define ___END_CFUN_SIZE_T_TO_SCMOBJ(c,s)"; attribute :>> obligation="three result ENDs lack drop"; }
part source7:SourceRow { attribute :>> key="cfun-context"; attribute :>> path="vendor/gambit/include/_gambit/foreign_conversion.h.in"; attribute :>> needle="#define ___BEGIN_CFUN_CTX"; attribute :>> obligation="spill before out-of-line C; reload after"; }
part source8:SourceRow { attribute :>> key="cfun-cleanup"; attribute :>> path="vendor/gambit/include/_gambit/foreign_conversion.h.in"; attribute :>> needle="#define ___BEGIN_CFUN_BODY_CLEANUP"; attribute :>> obligation="conditional TRY selected by input cleanup flag"; }
part source9:SourceRow { attribute :>> key="catcher"; attribute :>> path="vendor/gambit/include/_gambit/foreign_conversion.h.in"; attribute :>> needle="___ps->catcher = &___jbuf;"; attribute :>> obligation="catcher is automatic activation, restored at END_TRY"; }
part source10:SourceRow { attribute :>> key="throw"; attribute :>> path="vendor/gambit/include/_gambit/foreign_conversion.h.in"; attribute :>> needle="#define ___THROW(e)do { ___ps->longjmp_err"; attribute :>> obligation="nonlocal jump can bypass nested local ENDs"; }
part source11:SourceRow { attribute :>> key="language-c"; attribute :>> path="vendor/gambit/include/_gambit/language.h.in"; attribute :>> needle="#define ___USE_SETJMP"; attribute :>> obligation="C path uses setjmp; no C++ RAII assumption"; }
part source12:SourceRow { attribute :>> key="call-entry"; attribute :>> path="vendor/gambit/lib/setup.c"; attribute :>> needle="___EXP_FUNC(___SCMOBJ,___call)"; attribute :>> obligation="GC phase rejection before frame writes; catcher created later"; }
part source13:SourceRow { attribute :>> key="call-rethrow"; attribute :>> path="vendor/gambit/lib/setup.c"; attribute :>> needle="stack_marker != ___ps->context->fp[___FRAME_SPACE(2)-2]"; attribute :>> obligation="mismatched marker rethrows across wrapper scope"; }
part source14:SourceRow { attribute :>> key="run-landing"; attribute :>> path="vendor/gambit/lib/setup.c"; attribute :>> needle="___VOLATILE ___SCMOBJ marker = ___FAL;"; attribute :>> obligation="run catches its own marker; no per-conversion record"; }
part source15:SourceRow { attribute :>> key="error-propagation"; attribute :>> path="vendor/gambit/lib/setup.c"; attribute :>> needle="___EXP_FUNC(void,___propagate_error)"; attribute :>> obligation="error triggers throw"; }
part source16:SourceRow { attribute :>> key="marker-rooted"; attribute :>> path="vendor/gambit/lib/c_intf.c"; attribute :>> needle="proc_or_false = *proc_root; /* reload after allocating the marker */"; attribute :>> obligation="rooted startup endpoint reloads; generic wrapper local not registry"; }
part source17:SourceRow { attribute :>> key="marker-raw"; attribute :>> path="vendor/gambit/lib/c_intf.c"; attribute :>> needle="Legacy raw SFUN entry is not made a registered-root interface"; attribute :>> obligation="do not infer generic ingress roots"; }
part source18:SourceRow { attribute :>> key="marker-kill"; attribute :>> path="vendor/gambit/lib/c_intf.c"; attribute :>> needle="___still_obj_refcount_dec (marker);"; attribute :>> obligation="different object and native lifetime"; }
part source19:SourceRow { attribute :>> key="size-wrapper"; attribute :>> path="vendor/gambit/lib/c_intf.c"; attribute :>> needle="return ___U64_to_SCMOBJ (___ps, ___U64_from_ULONGLONG"; attribute :>> obligation="delegates allocating converter"; }
part source20:SourceRow { attribute :>> key="signed-wrapper"; attribute :>> path="vendor/gambit/lib/c_intf.c"; attribute :>> needle="return ___S64_to_SCMOBJ (___ps, ___S64_from_LONGLONG"; attribute :>> obligation="signed family"; }
part source21:SourceRow { attribute :>> key="converter-output"; attribute :>> path="vendor/gambit/lib/c_intf.c"; attribute :>> needle="if (___S64_fits_in_width (x, ___FIX_WIDTH))"; attribute :>> obligation="fresh body initialized before output assignment"; }
part source22:SourceRow { attribute :>> key="alloc-init"; attribute :>> path="vendor/gambit/lib/_mem/object-allocation.inc"; attribute :>> needle="still objects this initialization must be done before the next"; attribute :>> obligation="constructor-return handoff has no new allocation"; }
part source23:SourceRow { attribute :>> key="alloc-gc"; attribute :>> path="vendor/gambit/lib/_mem/object-allocation.inc"; attribute :>> needle="if (___garbage_collect (___PSP words))"; attribute :>> obligation="never hold short mutation lease across allocating converter"; }
part source24:SourceRow { attribute :>> key="alloc-count"; attribute :>> path="vendor/gambit/lib/_mem/object-allocation.inc"; attribute :>> needle="base[___STILL_REFCOUNT] = 1;"; attribute :>> obligation="native temporary hold protects fresh still object"; }
part source25:SourceRow { attribute :>> key="release-check"; attribute :>> path="vendor/gambit/lib/_mem/object-allocation.inc"; attribute :>> needle="___EXP_FUNC(___SCMOBJ,___release_scmobj)"; attribute :>> obligation="immediate/permanent no-op; still decrement"; }
part source26:SourceRow { attribute :>> key="count-effect"; attribute :>> path="vendor/gambit/lib/_mem/still-refcount.inc"; attribute :>> needle="___BODY0(obj)[___STILL_REFCOUNT-___STILL_BODY]--;"; attribute :>> obligation="plain effect requires exclusive owner and GC exclusion"; }
part source27:SourceRow { attribute :>> key="scan-still"; attribute :>> path="vendor/gambit/lib/_mem/object-scanning.inc"; attribute :>> needle="if (base[___STILL_REFCOUNT] == 0)"; attribute :>> obligation="nonzero native holds become still roots"; }
part source28:SourceRow { attribute :>> key="scan-context"; attribute :>> path="vendor/gambit/lib/_mem/root-origins.inc"; attribute :>> needle="mark_array (work, context->r, sizeof(context->r)/sizeof(*context->r));"; attribute :>> obligation="includes exact PSR1 slot"; }
part source29:SourceRow { attribute :>> key="scan-saved"; attribute :>> path="vendor/gambit/lib/_mem/root-origins.inc"; attribute :>> needle="mark_array (work, context->saved, sizeof(context->saved)/sizeof(*context->saved));"; attribute :>> obligation="saved roots have current consumers"; }
part source30:SourceRow { attribute :>> key="scan-startup"; attribute :>> path="vendor/gambit/lib/_mem/root-origins.inc"; attribute :>> needle="mark_array (work, &context->entry_marker, 1);"; attribute :>> obligation="startup has dedicated roots, not generic conversion table"; }
part source31:SourceRow { attribute :>> key="root-freeze"; attribute :>> path="vendor/gambit/lib/_mem/collection-round.inc"; attribute :>> needle="participant->phase = ___GC_ROOTS_FROZEN;"; attribute :>> obligation="synchronous context publication cut"; }
part source32:SourceRow { attribute :>> key="root-barrier"; attribute :>> path="vendor/gambit/lib/_mem/collection-round.inc"; attribute :>> needle="BARRIER(); /* actual W and every grant published after complete R freeze */"; attribute :>> obligation="all participants frozen before worker access"; }
part source33:SourceRow { attribute :>> key="owner-cleanup"; attribute :>> path="vendor/gambit/lib/_mem/collection-round.inc"; attribute :>> needle="vm->gc_participants[id].phase = ___GC_OWNER_CLEANUP;"; attribute :>> obligation="restored stacks do not authorize managed reentry"; }
part source34:SourceRow { attribute :>> key="scan-drain"; attribute :>> path="vendor/gambit/lib/_mem/collection-round.inc"; attribute :>> needle="BARRIER(); /* no worker may retain a stopped root view past this cut */"; attribute :>> obligation="scanner view retirement before reuse"; }
part source35:SourceRow { attribute :>> key="context-storage"; attribute :>> path="vendor/gambit/include/_gambit/runtime_roles.h.in"; attribute :>> needle="___WORD saved[3]; /* Scheme objects protected from GC */"; attribute :>> obligation="VM context stable but fixed saved cells cannot hold unbounded nested guards"; }
part source36:SourceRow { attribute :>> key="phase-field"; attribute :>> path="vendor/gambit/include/_gambit/runtime_roles.h.in"; attribute :>> needle="___gc_participant_phase phase;"; attribute :>> obligation="ordinary enum, not an atomic admission pin"; }
part source37:SourceRow { attribute :>> key="cleanup-escrow"; attribute :>> path="vendor/gambit/include/_gambit/runtime_roles.h.in"; attribute :>> needle="typedef struct ___gc_cleanup_escrow_struct"; attribute :>> obligation="dedicated sweep debt, not conversion ownership"; }
part source38:SourceRow { attribute :>> key="psr1"; attribute :>> path="vendor/gambit/include/_gambit/gvm_registers.h.in"; attribute :>> needle="#define ___PSR1 ___ps->context->r[1]"; attribute :>> obligation="slot identity and reload/writeback must agree"; }
part source39:SourceRow { attribute :>> key="spill-select"; attribute :>> path="vendor/gambit/include/_gambit/stack_operations.h.in"; attribute :>> needle="#define ___W_ALL ___SM"; attribute :>> obligation="local and process register coherence"; }
part source40:SourceRow { attribute :>> key="generator-args"; attribute :>> path="vendor/gambit/gsc/_ptree2.scm"; attribute :>> needle="(define (c-convert-argument sfun? numbered-typ body)"; attribute :>> obligation="SFUN args converted before call"; }
part source41:SourceRow { attribute :>> key="generator-result"; attribute :>> path="vendor/gambit/gsc/_ptree2.scm"; attribute :>> needle="(define (c-set-result sfun? result-typ)"; attribute :>> obligation="CFUN native result converted into PSR1"; }
part source42:SourceRow { attribute :>> key="generator-cleanup"; attribute :>> path="vendor/gambit/gsc/_ptree2.scm"; attribute :>> needle="(define (type-needs-cleanup? typ-source)"; attribute :>> obligation="false parameter flags omit cleanup TRY; not result ownership"; }
part source43:SourceRow { attribute :>> key="generator-plan"; attribute :>> path="vendor/gambit/gsc/_ptree2.scm"; attribute :>> needle="(define (c-make-function sfun? name param-typs result-typ make-body)"; attribute :>> obligation="candidate producer of direction-aware guard plan"; }
part source44:SourceRow { attribute :>> key="cfun-backend"; attribute :>> path="vendor/gambit/gsc/_t-c-2.scm"; attribute :>> needle="setjmp interfering with C TCO"; attribute :>> obligation="out-of-line C policy and stack maps; guard must not silently force inline TRY"; }
part source45:SourceRow { attribute :>> key="type-registry"; attribute :>> path="vendor/gambit/gsc/_parms.scm"; attribute :>> needle="(cons size_t-sym"; attribute :>> obligation="three flags false; unchanged ownership omission"; }
part source46:SourceRow { attribute :>> key="darwin-config"; attribute :>> path="vendor/gambit/config.status"; attribute :>> needle="'--disable-smp'"; attribute :>> obligation="configured arm64 GCC16 subset not SMP native qualification"; }
part source47:SourceRow { attribute :>> key="width-config"; attribute :>> path="vendor/gambit/config.log"; attribute :>> needle="ac_cv_sizeof_long=8"; attribute :>> obligation="historical generated profile"; }
part source48:SourceRow { attribute :>> key="build-command"; attribute :>> path="vendor/gambit/bin/gambuild-C"; attribute :>> needle="/opt/homebrew/Cellar/gcc/16.2.0/bin/gcc-16"; attribute :>> obligation="actual recorded toolchain command"; }
part source49:SourceRow { attribute :>> key="generated-header"; attribute :>> path="vendor/gambit/include/gambit.h"; attribute :>> needle="#define ___CFUN_RESULT ___PSR1"; attribute :>> obligation="same macro subset not same full code cohort"; }
part source50:SourceRow { attribute :>> key="parent-design"; attribute :>> path="dev/refactoring/modern-c/size-family-hold-balance-design.org"; attribute :>> needle="A successful out-of-fixnum conversion"; attribute :>> obligation="prior conditional ownership defect; preserve receipt"; }
part source51:SourceRow { attribute :>> key="feeley-paper"; attribute :>> path="evidence/research/sfun-converter-use-closure/feeley-sfp-paper.txt"; attribute :>> needle="return to C frames"; attribute :>> obligation="Scheme continuation extent versus C activation extent"; }
part def IssuerRow { attribute key:String; attribute source:String; attribute existing:String; attribute candidate:String; attribute gap:String; }
part issuer0:IssuerRow { attribute :>> key="SFUN-entry"; attribute :>> source="generator-plan"; attribute :>> existing="C wrapper and stack marker exist"; attribute :>> candidate="generated prolog reserves VM root-domain guard before marker and first converter"; attribute :>> gap="no current per-attempt stable issuer"; }
part issuer1:IssuerRow { attribute :>> key="CFUN-entry"; attribute :>> source="cfun-backend"; attribute :>> existing="context spill / out-of-line wrapper exist"; attribute :>> candidate="generated wrapper reserves before native body; stable root output plus PSR1 handoff"; attribute :>> gap="input cleanup flag cannot stand in for result ownership"; }
part issuer2:IssuerRow { attribute :>> key="landing"; attribute :>> source="catcher"; attribute :>> existing="automatic catcher restores chain"; attribute :>> candidate="outer native return coordinator adopts escaped guard subtree by attempt identity"; attribute :>> gap="landing-to-stable-coordinator composition unresolved"; }
part issuer3:IssuerRow { attribute :>> key="scan"; attribute :>> source="scan-context"; attribute :>> existing="context registers/saved/startup/RC scanned"; attribute :>> candidate="enumerate registered conversion root slots in same frozen root domain"; attribute :>> gap="no generic conversion table in current enumeration"; }
part issuer4:IssuerRow { attribute :>> key="drop"; attribute :>> source="count-effect"; attribute :>> existing="plain decrement exists"; attribute :>> candidate="exclusive owner + short epoch lease from claim through receipt then release"; attribute :>> gap="C23 gate, NoAbandon and all-writer admission unqualified"; }
part issuer5:IssuerRow { attribute :>> key="retire"; attribute :>> source="scan-drain"; attribute :>> existing="collective stopped-view drain exists"; attribute :>> candidate="remove carrier only inside root-update lease after settled receipt and no scan readers"; attribute :>> gap="lookup tombstone and descriptor/code lifetime still separate"; }
part def RouteRow { attribute component:String; attribute actionName:String; attribute lemma:String; attribute producerAnchor:String; attribute obligationId:String; }
part route0:RouteRow { attribute :>> component="ffi-conversion"; attribute :>> actionName="size_family_guard_gc.reserveSfun"; attribute :>> lemma="SizeGuard.reserveSfunPreserves"; attribute :>> producerAnchor="generator-plan"; attribute :>> obligationId="guard-safety"; }
part route1:RouteRow { attribute :>> component="ffi-conversion"; attribute :>> actionName="size_family_guard_gc.reserveCfun"; attribute :>> lemma="SizeGuard.reserveCfunPreserves"; attribute :>> producerAnchor="generator-plan"; attribute :>> obligationId="guard-safety"; }
part route2:RouteRow { attribute :>> component="ffi-conversion"; attribute :>> actionName="size_family_guard_gc.beginConversion"; attribute :>> lemma="SizeGuard.beginConversionPreserves"; attribute :>> producerAnchor="alloc-gc"; attribute :>> obligationId="guard-safety"; }
part route3:RouteRow { attribute :>> component="ffi-conversion"; attribute :>> actionName="size_family_guard_gc.completeBoxed"; attribute :>> lemma="SizeGuard.completeBoxedPreserves"; attribute :>> producerAnchor="converter-output"; attribute :>> obligationId="guard-safety"; }
part route4:RouteRow { attribute :>> component="ffi-conversion"; attribute :>> actionName="size_family_guard_gc.completeImmediate"; attribute :>> lemma="SizeGuard.completeImmediatePreserves"; attribute :>> producerAnchor="converter-output"; attribute :>> obligationId="guard-safety"; }
part route5:RouteRow { attribute :>> component="native-return"; attribute :>> actionName="size_family_guard_gc.abortBeforeConversion"; attribute :>> lemma="SizeGuard.abortBeforeConversionPreserves"; attribute :>> producerAnchor="call-rethrow"; attribute :>> obligationId="guard-safety"; }
part route6:RouteRow { attribute :>> component="ffi-conversion"; attribute :>> actionName="size_family_guard_gc.acquireRootUpdate"; attribute :>> lemma="SizeGuard.acquireRootUpdatePreserves"; attribute :>> producerAnchor="scan-context"; attribute :>> obligationId="guard-safety"; }
part route7:RouteRow { attribute :>> component="ffi-conversion"; attribute :>> actionName="size_family_guard_gc.publishLanguage"; attribute :>> lemma="SizeGuard.publishLanguagePreserves"; attribute :>> producerAnchor="cfun-result"; attribute :>> obligationId="guard-safety"; }
part route8:RouteRow { attribute :>> component="ffi-conversion"; attribute :>> actionName="size_family_guard_gc.releaseRootUpdate"; attribute :>> lemma="SizeGuard.releaseRootUpdatePreserves"; attribute :>> producerAnchor="scan-context"; attribute :>> obligationId="guard-safety"; }
part route9:RouteRow { attribute :>> component="ffi-conversion"; attribute :>> actionName="size_family_guard_gc.captureArgument"; attribute :>> lemma="SizeGuard.captureArgumentPreserves"; attribute :>> producerAnchor="scan-context"; attribute :>> obligationId="guard-safety"; }
part route10:RouteRow { attribute :>> component="ffi-conversion"; attribute :>> actionName="size_family_guard_gc.finishNative"; attribute :>> lemma="SizeGuard.finishNativePreserves"; attribute :>> producerAnchor="scan-context"; attribute :>> obligationId="guard-safety"; }
part route11:RouteRow { attribute :>> component="native-return"; attribute :>> actionName="size_family_guard_gc.escapeNative"; attribute :>> lemma="SizeGuard.escapeNativePreserves"; attribute :>> producerAnchor="call-rethrow"; attribute :>> obligationId="guard-safety"; }
part route12:RouteRow { attribute :>> component="native-return"; attribute :>> actionName="size_family_guard_gc.claimDrop"; attribute :>> lemma="SizeGuard.claimDropPreserves"; attribute :>> producerAnchor="count-effect"; attribute :>> obligationId="guard-safety"; }
part route13:RouteRow { attribute :>> component="ffi-conversion"; attribute :>> actionName="size_family_guard_gc.fuseCfunHandoff"; attribute :>> lemma="SizeGuard.fuseCfunHandoffPreserves"; attribute :>> producerAnchor="cfun-result"; attribute :>> obligationId="guard-safety"; }
part route14:RouteRow { attribute :>> component="native-return"; attribute :>> actionName="size_family_guard_gc.physicalDrop"; attribute :>> lemma="SizeGuard.physicalDropPreserves"; attribute :>> producerAnchor="count-effect"; attribute :>> obligationId="guard-safety"; }
part route15:RouteRow { attribute :>> component="native-return"; attribute :>> actionName="size_family_guard_gc.recordDrop"; attribute :>> lemma="SizeGuard.recordDropPreserves"; attribute :>> producerAnchor="count-effect"; attribute :>> obligationId="guard-safety"; }
part route16:RouteRow { attribute :>> component="native-return"; attribute :>> actionName="size_family_guard_gc.releaseDrop"; attribute :>> lemma="SizeGuard.releaseDropPreserves"; attribute :>> producerAnchor="count-effect"; attribute :>> obligationId="guard-safety"; }
part route17:RouteRow { attribute :>> component="native-return"; attribute :>> actionName="size_family_guard_gc.loseReply"; attribute :>> lemma="SizeGuard.loseReplyPreserves"; attribute :>> producerAnchor="scan-context"; attribute :>> obligationId="guard-safety"; }
part route18:RouteRow { attribute :>> component="native-return"; attribute :>> actionName="size_family_guard_gc.queryReceipt"; attribute :>> lemma="SizeGuard.queryReceiptPreserves"; attribute :>> producerAnchor="scan-context"; attribute :>> obligationId="guard-safety"; }
part route19:RouteRow { attribute :>> component="ffi-conversion"; attribute :>> actionName="size_family_guard_gc.dropCapture"; attribute :>> lemma="SizeGuard.dropCapturePreserves"; attribute :>> producerAnchor="scan-context"; attribute :>> obligationId="guard-safety"; }
part route20:RouteRow { attribute :>> component="ffi-conversion"; attribute :>> actionName="size_family_guard_gc.clearLanguage"; attribute :>> lemma="SizeGuard.clearLanguagePreserves"; attribute :>> producerAnchor="scan-context"; attribute :>> obligationId="guard-safety"; }
part route21:RouteRow { attribute :>> component="native-return"; attribute :>> actionName="size_family_guard_gc.retireGuard"; attribute :>> lemma="SizeGuard.retireGuardPreserves"; attribute :>> producerAnchor="scan-drain"; attribute :>> obligationId="guard-safety"; }
part route22:RouteRow { attribute :>> component="ffi-conversion"; attribute :>> actionName="size_family_guard_gc.reissueSfun"; attribute :>> lemma="SizeGuard.reissueSfunPreserves"; attribute :>> producerAnchor="generator-plan"; attribute :>> obligationId="guard-safety"; }
part route23:RouteRow { attribute :>> component="ffi-conversion"; attribute :>> actionName="size_family_guard_gc.reissueCfun"; attribute :>> lemma="SizeGuard.reissueCfunPreserves"; attribute :>> producerAnchor="generator-plan"; attribute :>> obligationId="guard-safety"; }
part route24:RouteRow { attribute :>> component="gc-root-domain"; attribute :>> actionName="size_family_guard_gc.closeGate"; attribute :>> lemma="SizeGuard.closeGatePreserves"; attribute :>> producerAnchor="root-freeze"; attribute :>> obligationId="guard-safety"; }
part route25:RouteRow { attribute :>> component="gc-root-domain"; attribute :>> actionName="size_family_guard_gc.freezeOwner"; attribute :>> lemma="SizeGuard.freezeOwnerPreserves"; attribute :>> producerAnchor="root-freeze"; attribute :>> obligationId="guard-safety"; }
part route26:RouteRow { attribute :>> component="gc-root-domain"; attribute :>> actionName="size_family_guard_gc.beginScan"; attribute :>> lemma="SizeGuard.beginScanPreserves"; attribute :>> producerAnchor="root-freeze"; attribute :>> obligationId="guard-safety"; }
part route27:RouteRow { attribute :>> component="gc-root-domain"; attribute :>> actionName="size_family_guard_gc.endScan"; attribute :>> lemma="SizeGuard.endScanPreserves"; attribute :>> producerAnchor="scan-drain"; attribute :>> obligationId="guard-safety"; }
part route28:RouteRow { attribute :>> component="gc-root-domain"; attribute :>> actionName="size_family_guard_gc.resumeOwner"; attribute :>> lemma="SizeGuard.resumeOwnerPreserves"; attribute :>> producerAnchor="scan-drain"; attribute :>> obligationId="guard-safety"; }
part def CompositionRow { attribute key:String; attribute lemma:String; attribute source:String; attribute obligation:String; attribute boundary:String; }
part composition0:CompositionRow { attribute :>> key="parent-drop"; attribute :>> lemma="SizeGuardBridge.normalDropBoundary"; attribute :>> source="count-effect"; attribute :>> obligation="normal-parent-bridge"; attribute :>> boundary="normal outcome only; aborted CFUN must not fabricate PSR1"; }
part composition1:CompositionRow { attribute :>> key="parent-effect"; attribute :>> lemma="SizeGuardBridge.dropEffectAgreement"; attribute :>> source="count-effect"; attribute :>> obligation="normal-parent-bridge"; attribute :>> boundary="physical hold/effect fields only; not full state simulation"; }
part composition2:CompositionRow { attribute :>> key="fusion"; attribute :>> lemma="SizeGuard.fusedCfunEqualsSeparate"; attribute :>> source="cfun-result"; attribute :>> obligation="fused-handoff"; attribute :>> boundary="no safepoint/callback/foreign call between root publication and drop claim"; }
part def MemoryRow { attribute key:String; attribute order:String; attribute premise:String; attribute obligation:String; }
part memory0:MemoryRow { attribute :>> key="gate-close"; attribute :>> order="same-word CAS acq_rel closes generation and observes outstanding leases"; attribute :>> premise="ordinary GC_RUNNING load is not admission"; attribute :>> obligation="C23-mutator-gate"; }
part memory1:MemoryRow { attribute :>> key="root-update"; attribute :>> order="acquire short lease before slot write; release on final decrement"; attribute :>> premise="do not block/allocate/call Scheme under the short lease"; attribute :>> obligation="C23-mutator-gate"; }
part memory2:MemoryRow { attribute :>> key="freeze"; attribute :>> order="acquire observe drained lease count then owner publishes frozen roots before worker scan"; attribute :>> premise="all real participants and root producers joined same epoch"; attribute :>> obligation="root-enumeration"; }
part memory3:MemoryRow { attribute :>> key="drop"; attribute :>> order="plain still decrement under sole admitted owner; record completion before release of lease"; attribute :>> premise="no callback/cancel/GC/allocation/longjmp in physical-effect interval"; attribute :>> obligation="constructor-adoption"; }
part memory4:MemoryRow { attribute :>> key="receipt"; attribute :>> order="release completion; acquire lookup matches exact VM/context/attempt/generation"; attribute :>> premise="stale receipt cannot settle fresh attempt"; attribute :>> obligation="retirement"; }
part def GainRow { attribute key:String; attribute benefit:String; attribute cost:String; attribute condition:String; attribute refutation:String; }
part gain0:GainRow { attribute :>> key="balanced-native-holds"; attribute :>> benefit="B native boxed conversion holds can be discharged exactly once"; attribute :>> cost="N release decisions plus B physical decrements; no boxing eliminated"; attribute :>> condition="source holds exclusive and last use established"; attribute :>> refutation="manual old decrements admitted without transfer gives double release"; }
part gain1:GainRow { attribute :>> key="short-leases"; attribute :>> benefit="long-lived guards may cross GC without holding short mutation leases"; attribute :>> cost="one frozen-root enumeration per live carrier per collection"; attribute :>> condition="guard lifetime != GC exclusion lifetime"; attribute :>> refutation="holding lease across ___call or allocating converter can deadlock collector"; }
part gain2:GainRow { attribute :>> key="CFUN-fusion"; attribute :>> benefit="M eligible CFUN handoffs save M acquire/release pairs: 2M successful RMWs in chosen gate design"; attribute :>> cost="fused path retains one pair; retries and metadata accesses still cost"; attribute :>> condition="no callback/allocation/unwind between handoff and drop claim; same root domain"; attribute :>> refutation="SFUN Scheme call allocates or nested callbacks need separate windows"; }
part gain3:GainRow { attribute :>> key="shared-support"; attribute :>> benefit="VM guard pool/root adapter/landing coordinator shared by six size END responsibilities and later converters"; attribute :>> cost="A simultaneous attempts need O(A) live records; T retained receipts need O(T) metadata"; attribute :>> condition="root/receipt storage and key exhaustion policies explicit"; attribute :>> refutation="wrapper-only layer adds runtime without retiring old ownership paths"; }
part gain4:GainRow { attribute :>> key="language-choice"; attribute :>> benefit="C23 contracts directly reuse Gambit GC/context/trampoline and C interface"; attribute :>> cost="Zig would still require the same roots/gate/landing protocol"; attribute :>> condition="modern C mandatory mainline; no extra language needed for this defect"; attribute :>> refutation="no proven Zig-specific reduction of required support here"; }
part def ContractRow { attribute fromNode:String; attribute toNode:String; attribute custody:String; }
part contract0:ContractRow { attribute :>> fromNode="Scheme conversion plan"; attribute :>> toNode="Generated SFUN prolog"; attribute :>> custody="reserve stable rooted guard before marker and input conversion"; }
part contract1:ContractRow { attribute :>> fromNode="Scheme conversion plan"; attribute :>> toNode="Generated CFUN prolog"; attribute :>> custody="reserve before native body; preserve out-of-line/TCO policy"; }
part contract2:ContractRow { attribute :>> fromNode="Generated SFUN prolog"; attribute :>> toNode="VM guard root domain"; attribute :>> custody="AttemptId and source/root/descriptor custody"; }
part contract3:ContractRow { attribute :>> fromNode="Generated CFUN prolog"; attribute :>> toNode="VM guard root domain"; attribute :>> custody="stable result carrier before PSR1 handoff"; }
part contract4:ContractRow { attribute :>> fromNode="VM guard root domain"; attribute :>> toNode="GC frozen root view"; attribute :>> custody="close short-lease gate; owner checkpoint; enumerate carriers"; }
part contract5:ContractRow { attribute :>> fromNode="VM guard root domain"; attribute :>> toNode="Native return coordinator"; attribute :>> custody="outward catcher adopts child guards; no C-stack pointers"; }
part contract6:ContractRow { attribute :>> fromNode="Native return coordinator"; attribute :>> toNode="Drop lease"; attribute :>> custody="close native use; exclude GC and other writers"; }
part contract7:ContractRow { attribute :>> fromNode="Drop lease"; attribute :>> toNode="Physical count decrement"; attribute :>> custody="exact owned object; no callback/allocation/escape"; }
part contract8:ContractRow { attribute :>> fromNode="Physical count decrement"; attribute :>> toNode="Completion receipt"; attribute :>> custody="record before last lease release"; }
part contract9:ContractRow { attribute :>> fromNode="Completion receipt"; attribute :>> toNode="Root and descriptor retirement"; attribute :>> custody="exact attempt lookup; remove carrier after scan drain; tombstone retained"; }
part def NeedRow { attribute key:String; attribute status:String; attribute condition:String; }
part need0:NeedRow { attribute :>> key="guard-safety"; attribute :>> status="formal"; attribute :>> condition="each step preserves guard/carrier/hold/lease invariants"; }
part need1:NeedRow { attribute :>> key="normal-parent-bridge"; attribute :>> status="conditional formal"; attribute :>> condition="normal last-use cut refines parent drop guard and physical effect"; }
part need2:NeedRow { attribute :>> key="fused-handoff"; attribute :>> status="formal"; attribute :>> condition="CFUN normal handoff algebraically matches separate root transfer and claim"; }
part need3:NeedRow { attribute :>> key="native-issuer"; attribute :>> status="unresolved"; attribute :>> condition="stable pool/root-domain/catcher registration before all allocation or callback boundaries"; }
part need4:NeedRow { attribute :>> key="constructor-adoption"; attribute :>> status="unresolved"; attribute :>> condition="initialization and output-slot adoption no-abandon proof; allocator debug/foreign escape remains external"; }
part need5:NeedRow { attribute :>> key="C23-mutator-gate"; attribute :>> status="unresolved"; attribute :>> condition="atomic generation gate + short lease + owner checkpoint mapped to actual collective"; }
part need6:NeedRow { attribute :>> key="root-enumeration"; attribute :>> status="unresolved"; attribute :>> condition="conversion slot census and register/frame maps incl nested callbacks"; }
part need7:NeedRow { attribute :>> key="landing-subtree"; attribute :>> status="unresolved"; attribute :>> condition="outer unwind adopts every inner live attempt without discarded C-stack records"; }
part need8:NeedRow { attribute :>> key="all-writers-cohort"; attribute :>> status="unresolved"; attribute :>> condition="manual decrements/overrides/headers/loaded modules qualified as one cohort"; }
part need9:NeedRow { attribute :>> key="retirement"; attribute :>> status="unresolved"; attribute :>> condition="receipt readers and code/storage lifetime drained; generation exhaustion refuses reuse"; }

part def ComponentRow { attribute componentId:String; attribute role:String; attribute sharedContract:String; attribute boundary:String; }
part component0:ComponentRow { attribute :>> componentId="ffi-conversion"; attribute :>> role="Scheme-generated direction and root transfer plan"; attribute :>> sharedContract="ConversionAttempt/RootSlot/NativeHold"; attribute :>> boundary="no native release inferred from type name or cleanup bit"; }
part component1:ComponentRow { attribute :>> componentId="gc-root-domain"; attribute :>> role="freeze and collector scan-view authority"; attribute :>> sharedContract="ConversionAttempt/RootSlot/NativeHold"; attribute :>> boundary="worker owns scan tasks; root owner owns slot updates"; }
part component2:ComponentRow { attribute :>> componentId="native-return"; attribute :>> role="escaped completion and receipt coordination"; attribute :>> sharedContract="ConversionAttempt/RootSlot/NativeHold"; attribute :>> boundary="native return extent distinct from Scheme multi-shot continuation"; }
}
