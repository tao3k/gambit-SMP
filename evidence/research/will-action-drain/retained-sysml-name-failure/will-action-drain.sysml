package GambitWillActionDrain { private import ScalarValues::*;
part def Owner { attribute componentId:String; }
part construction:Owner { attribute :>> componentId="construction"; }
part execution:Owner { attribute :>> componentId="execution"; }
part restoration:Owner { attribute :>> componentId="restoration"; }
part admission:Owner { attribute :>> componentId="admission"; }
part def SourceRow { attribute key:String; attribute path:String; attribute needle:String; attribute obligation:String; }
part source0:SourceRow { attribute :>> key="public-will"; attribute :>> path="vendor/gambit/lib/_nonstd.scm"; attribute :>> needle="(define-prim (make-will testator action)"; attribute :>> obligation="Actual checked public constructor forwards to primitive"; }
part source1:SourceRow { attribute :>> key="private-ctor"; attribute :>> path="vendor/gambit/lib/_kernel.scm"; attribute :>> needle="(define-prim (##make-final-will testator action)"; attribute :>> obligation="Procedure body creates a will when called; definition is not a default invocation"; }
part source2:SourceRow { attribute :>> key="ctor-macro"; attribute :>> path="vendor/gambit/include/gambit.h"; attribute :>> needle="#define ___MAKEWILL(testator,action)"; attribute :>> obligation="Writes testator/action and links nonexecutable list"; }
part source3:SourceRow { attribute :>> key="ctor-list"; attribute :>> path="vendor/gambit/include/gambit.h"; attribute :>> needle="___ps->mem.nonexecutable_wills_=___TAG(___hp,0)"; attribute :>> obligation="Raw generated allocation publication; no session admission gate"; }
part source4:SourceRow { attribute :>> key="ct-backend"; attribute :>> path="vendor/gambit/gsc/_t-c-2.scm"; attribute :>> needle="(define (targ-apply-make-will)"; attribute :>> obligation="GVM operation emitter, not compile-time action invocation"; }
part source5:SourceRow { attribute :>> key="ct-op"; attribute :>> path="vendor/gambit/gsc/_t-c-2.scm"; attribute :>> needle="(targ-op \"##make-will\""; attribute :>> obligation="Registers target emission recipe"; }
part source6:SourceRow { attribute :>> key="ephemeron-ctor"; attribute :>> path="vendor/gambit/lib/srfi/124/124.scm"; attribute :>> needle="(make-will key (make-ephemeron-finalizer ephemeron))"; attribute :>> obligation="Real library call; optional load and actual compile-session invocation not established"; }
part source7:SourceRow { attribute :>> key="ephemeron-action"; attribute :>> path="vendor/gambit/lib/srfi/124/124.scm"; attribute :>> needle="(define (make-ephemeron-finalizer ephemeron)"; attribute :>> obligation="Captures ephemeron; key formal unused in body"; }
part source8:SourceRow { attribute :>> key="ephemeron-clear"; attribute :>> path="vendor/gambit/lib/srfi/124/124.scm"; attribute :>> needle="(macro-ephemeron-datum-set! ephemeron #f)"; attribute :>> obligation="Clears ephemeron field, does not mutate datum contents"; }
part source9:SourceRow { attribute :>> key="macro-execute"; attribute :>> path="vendor/gambit/gsc/_ptree1.scm"; attribute :>> needle="(apply expander (cdr (source->expression source)))"; attribute :>> obligation="Actual compiler invokes user-defined transformer"; }
part source10:SourceRow { attribute :>> key="macro-eval"; attribute :>> path="vendor/gambit/gsc/_ptree1.scm"; attribute :>> needle="(scheme-global-eval (source->expression proc)"; attribute :>> obligation="Expander construction executes host Scheme expression"; }
part source11:SourceRow { attribute :>> key="host-eval"; attribute :>> path="vendor/gambit/gsc/_host.scm"; attribute :>> needle="(define (scheme-global-eval expr err)"; attribute :>> obligation="Actual Gambit host uses eval; direct calls are not closed-world"; }
part source12:SourceRow { attribute :>> key="finalize-pop"; attribute :>> path="vendor/gambit/lib/_kernel.scm"; attribute :>> needle="___ps->context->mem.executable_wills_ = ___WILL_NEXT_FIELD(will);"; attribute :>> obligation="Dequeued will must remain rooted independently of list"; }
part source13:SourceRow { attribute :>> key="action-load"; attribute :>> path="vendor/gambit/lib/_kernel.scm"; attribute :>> needle="(let ((testator (##will-testator will))"; attribute :>> obligation="Loads operands before field zapping"; }
part source14:SourceRow { attribute :>> key="action-zap"; attribute :>> path="vendor/gambit/lib/_kernel.scm"; attribute :>> needle="(##will-action-set! will #f)"; attribute :>> obligation="Does not clear lexical action or captured continuation roots"; }
part source15:SourceRow { attribute :>> key="action-call"; attribute :>> path="vendor/gambit/lib/_kernel.scm"; attribute :>> needle="(action testator)"; attribute :>> obligation="Interrupts enabled in action body; no completion guard in this source function"; }
part source16:SourceRow { attribute :>> key="final-drain"; attribute :>> path="vendor/gambit/lib/_kernel.scm"; attribute :>> needle="(macro-fifo-remove-all! registry)"; attribute :>> obligation="Detaches list but loop may retain remaining work across exception/capture"; }
part source17:SourceRow { attribute :>> key="strong-action"; attribute :>> path="vendor/gambit/lib/memory/object-scanning.inc"; attribute :>> needle="mark_array (work, body+2, 1);"; attribute :>> obligation="Strong action edge before weak testator processing"; }
part source18:SourceRow { attribute :>> key="weak-transition"; attribute :>> path="vendor/gambit/lib/memory/wills.inc"; attribute :>> needle="determine_will_executability (nonexecutable_wills);"; attribute :>> obligation="Closing creation does not prevent existing weak wills becoming executable"; }
part source19:SourceRow { attribute :>> key="context-list"; attribute :>> path="vendor/gambit/lib/memory/configuration.inc"; attribute :>> needle="#define executable_wills        ___CONTEXT_MEM(executable_wills_)"; attribute :>> obligation="Consumer list uses execution context; current producer header must be qualified separately"; }
part source20:SourceRow { attribute :>> key="generated-load"; attribute :>> path="vendor/gambit/lib/_kernel.c"; attribute :>> needle="___SET_R3(___WILLACTION(___R1))"; attribute :>> obligation="Concrete artifact loads action to R3"; }
part source21:SourceRow { attribute :>> key="generated-poll"; attribute :>> path="vendor/gambit/lib/_kernel.c"; attribute :>> needle="___POLL(1)"; attribute :>> obligation="Selected procedure polls after field clearing with action/testator live"; }
part source22:SourceRow { attribute :>> key="generated-call"; attribute :>> path="vendor/gambit/lib/_kernel.c"; attribute :>> needle="___JUMPGENNOTSAFE(___SET_NARGS(1),___R3)"; attribute :>> obligation="Selected will execution dynamic callee"; }
part source23:SourceRow { attribute :>> key="generated-desc"; attribute :>> path="vendor/gambit/lib/_kernel.c"; attribute :>> needle="___DEF_LBL_RET(___H__23__23_will_2d_execute_21_,___IFD(___RETI,4,0,0x3f1L))"; attribute :>> obligation="Descriptor literal exists; actual generation/configuration correspondence open"; }
part source24:SourceRow { attribute :>> key="frame-scan"; attribute :>> path="vendor/gambit/lib/memory/continuation-roots.inc"; attribute :>> needle="while (___frame_root_next_run (&cursor, &first, &past))"; attribute :>> obligation="Actual frame roots consumer; poll mapping not inferred from lexical liveness"; }
part source25:SourceRow { attribute :>> key="resource"; attribute :>> path="vendor/gambit/gsc/_t-c-1.scm"; attribute :>> needle="(vector-set! r 1 demanders)"; attribute :>> obligation="Raw resource authority remains possible via aliases/globals"; }
part source26:SourceRow { attribute :>> key="first"; attribute :>> path="vendor/gambit/gsc/_t-c-1.scm"; attribute :>> needle="(def-mod-prm-glo \"DEF_MOD_PRM\")"; attribute :>> obligation="First demand remains needed"; }
part source27:SourceRow { attribute :>> key="second"; attribute :>> path="vendor/gambit/gsc/_t-c-1.scm"; attribute :>> needle="(def-mod-prm-glo \"DEF_MOD_GLO\")"; attribute :>> obligation="Actual candidate retirement site"; }
part source28:SourceRow { attribute :>> key="will-contract"; attribute :>> path="vendor/gambit/doc/gambit.txi"; attribute :>> needle="A remarkable feature of wills is that an action procedure can"; attribute :>> obligation="Manual explicitly permits resurrection and creation of a new will"; }
part source29:SourceRow { attribute :>> key="dead-vars"; attribute :>> path="vendor/gambit/doc/gambit.txi"; attribute :>> needle="continuations will contain the dead variables."; attribute :>> obligation="Lexical deadness alone is not physical-root retirement"; }
part def CreatorRow { attribute key:String; attribute producer:String; attribute captures:String; attribute writes:String; attribute reachability:String; attribute retirement:String; }
part creator0:CreatorRow { attribute :>> key="gsc-core"; attribute :>> producer="GSC immediate source files"; attribute :>> captures="Primitive names, specification and emitter closures"; attribute :>> writes="Emission of MAKEWILL does not execute user program constructor"; attribute :>> reachability="No direct compile-time will application found in bounded immediate-file inventory"; attribute :>> retirement="Not evidence of a will-free session"; }
part creator1:CreatorRow { attribute :>> key="public"; attribute :>> producer="make-will -> ##make-will -> target MAKEWILL"; attribute :>> captures="Caller-provided action and weak testator; action strongly rooted"; attribute :>> writes="Arbitrary action, plus internal action/testator setters"; attribute :>> reachability="Exposed API; user macro/eval/native may invoke"; attribute :>> retirement="Must classify actual session producer and operands"; }
part creator2:CreatorRow { attribute :>> key="final-registry"; attribute :>> producer="##make-final-will body"; attribute :>> captures="Action, testator and registry FIFO"; attribute :>> writes="Constructs weak will then inserts strong registry node"; attribute :>> reachability="Definition and generated body found; no core default call established"; attribute :>> retirement="Clear registry does not retire removed list or active action"; }
part creator3:CreatorRow { attribute :>> key="srfi124"; attribute :>> producer="make-ephemeron"; attribute :>> captures="Finalizer captures ephemeron; datum transitively retained"; attribute :>> writes="Exactly will/datum fields cleared by stock closure body"; attribute :>> reachability="Real library creator; not shown loaded/called in default GSC session"; attribute :>> retirement="Write-footprint certificate separate from session reachability"; }
part creator4:CreatorRow { attribute :>> key="macro-eval"; attribute :>> producer="add-macro make-descr -> host eval; macro-expand invokes expander"; attribute :>> captures="User/global environment and arbitrary retained values"; attribute :>> writes="Can invoke constructor, mutate resource or retain raw alias"; attribute :>> reachability="Compiler invocation located; particular effectful macro witness not run"; attribute :>> retirement="Cannot infer closed session from core constructor census"; }
part creator5:CreatorRow { attribute :>> key="test-fixtures"; attribute :>> producer="gsc/tests/35-will"; attribute :>> captures="Identity actions, rotations and printed examples"; attribute :>> writes="Exercises setters/constructors"; attribute :>> reachability="Explicit tests, not default compiler caller"; attribute :>> retirement="Never use fixture as default-session witness"; }
part creator6:CreatorRow { attribute :>> key="native-alias"; attribute :>> producer="MAKEWILL, field macros, FFI and unknown loaded code"; attribute :>> captures="Unregistered root carriers and external references possible"; attribute :>> writes="Raw C write authority not revoked by language choice"; attribute :>> reachability="No complete native producer/borrower inventory"; attribute :>> retirement="Unresolved means keep optimization denied"; }
part def RootRow { attribute key:String; attribute before:String; attribute after:String; attribute condition:String; attribute gap:String; }
part root0:RootRow { attribute :>> key="construct"; attribute :>> before="Action/testator operands in GVM roots"; attribute :>> after="Will strong action plus weak testator and list link"; attribute :>> condition="Allocation checks and generated operand roots must match actual configuration"; attribute :>> gap="Current header/context consumer expressions differ"; }
part root1:RootRow { attribute :>> key="dequeue"; attribute :>> before="Executable list root"; attribute :>> after="Local will then loaded testator/action"; attribute :>> condition="Independent scanned carrier before old list edge removed"; attribute :>> gap="Raw C inline RESULT and per-point roots qualification open"; }
part root2:RootRow { attribute :>> key="zap"; attribute :>> before="Will fields plus lexical operands"; attribute :>> after="Loaded R2/testator and R3/action; then testator moved to R1"; attribute :>> condition="At POLL(1) preserve current registers and RETI frame mapping"; attribute :>> gap="Descriptor 0x3f1 literal is not matched Darwin generation receipt"; }
part root3:RootRow { attribute :>> key="invoke"; attribute :>> before="Runnable strong carrier"; attribute :>> after="Active action frame, dynamic env and return continuation"; attribute :>> condition="GC scanner covers action body and captured caller chain"; attribute :>> gap="Arbitrary action and multi-shot mapping remain open"; }
part root4:RootRow { attribute :>> key="return"; attribute :>> before="Active activation"; attribute :>> after="Possibly retained external capture and native borrower"; attribute :>> condition="Return retires one activation ticket, not every capability"; attribute :>> gap="Need last-capture receipt with stable guard, not empty queue"; }
part root5:RootRow { attribute :>> key="escape"; attribute :>> before="Live action and remaining detached drain list"; attribute :>> after="Unknown owner guard and captured restoration state"; attribute :>> condition="Escaped/unknown completion retains ticket and cannot be retried blindly"; attribute :>> gap="No existing exception completion guard identified in will executor"; }
part root6:RootRow { attribute :>> key="ephemeron"; attribute :>> before="Will -> action -> ephemeron -> datum"; attribute :>> after="Action clears two ephemeron fields"; attribute :>> condition="Referent retention differs from authority to mutate referent"; attribute :>> gap="If datum reaches key, that strong path must be accounted before eligibility"; }
part def MemoryRow { attribute key:String; attribute publication:String; attribute observation:String; attribute obligation:String; attribute overhead:String; }
part memory0:MemoryRow { attribute :>> key="gate"; attribute :>> publication="Normal producer reserve under C23 owner mutex or qualified combined atomic gate"; attribute :>> observation="Close external admission preserves outstanding producer pins"; attribute :>> obligation="Reservation and close must share one linearization domain; no Scheme/GC/FFI while locked"; attribute :>> overhead="At least reserve/settle bookkeeping; cross-worker contention unmeasured"; }
part memory1:MemoryRow { attribute :>> key="roots"; attribute :>> publication="Register scanned carrier before possible GC or list-edge removal"; attribute :>> observation="GC sees operand/current action roots through admitted runtime facility"; attribute :>> obligation="A C atomic pointer or mutex is not a GC root; moving updates need real registry"; attribute :>> overhead="Root slot and generation metadata"; }
part memory2:MemoryRow { attribute :>> key="handoff"; attribute :>> publication="Parent reserves child responsibility before finishing"; attribute :>> observation="Final-empty check sees both parent retirement and child reservation"; attribute :>> obligation="Same ledger critical section or equivalent release/acquire refinement; unknown commit retains ticket"; attribute :>> overhead="No double decrement; one accounting domain"; }
part memory3:MemoryRow { attribute :>> key="reuse"; attribute :>> publication="Validate generation and pin immutable plan before leaving admission critical section"; attribute :>> observation="Output uses the borrowed plan until explicit completion"; attribute :>> obligation="Revoke cannot race unchecked pointer use; C23 atomics alone do not revoke raw aliases"; attribute :>> overhead="Per-borrow pin/return and epoch validation"; }
part memory4:MemoryRow { attribute :>> key="unknown"; attribute :>> publication="Outcome receipt records identity and owner before notifying caller"; attribute :>> observation="Reconcile accepted or absent outcome exactly once"; attribute :>> obligation="No generic retry after lost acknowledgement; source guards still need implementation"; attribute :>> overhead="Stable record retention until result known"; }
part def ClaimRow { attribute key:String; attribute mechanism:String; attribute condition:String; attribute result:String; attribute gap:String; }
part claim0:ClaimRow { attribute :>> key="closure"; attribute :>> mechanism="Separate external creation gate, weak eligibility, invocation and restoration authority"; attribute :>> condition="Already accepted producers and descendants remain accounted"; attribute :>> result="Closing registration neither drains execution nor cancels legal Scheme behavior"; attribute :>> gap="No unconditional global termination claim"; }
part claim1:ClaimRow { attribute :>> key="capture"; attribute :>> mechanism="Action is strongly marked; zapped fields no longer own operands"; attribute :>> condition="Loaded root carrier and captured action/caller frames admitted"; attribute :>> result="Model permits repeated resume after return and close"; attribute :>> gap="Actual root maps and capture enumeration incomplete"; }
part claim2:ClaimRow { attribute :>> key="rights"; attribute :>> mechanism="SRFI124 stock body touches two fields"; attribute :>> condition="Type/primitive identity and no forged native aliases"; attribute :>> result="Holding datum/resource keeps it alive but does not itself mutate resource"; attribute :>> gap="Arbitrary macro action can have broader authority; session inventory open"; }
part claim3:ClaimRow { attribute :>> key="scope"; attribute :>> mechanism="Track only metadata-relevant work for optimization receipt"; attribute :>> condition="Disjoint complete effect closure for excluded wills"; attribute :>> result="Unrelated wills need not die or be forced during compilation"; attribute :>> gap="Effect-disjointness is an external proof, not a name-based rule"; }
part claim4:ClaimRow { attribute :>> key="retire"; attribute :>> mechanism="Quiescent relevant obligations and immutable plan"; attribute :>> condition="Same entry, named-writer law, no post-cut legacy observer divergence"; attribute :>> result="Second helper condition can narrow to write authority rather than global GC shutdown"; attribute :>> gap="Full observable equivalence still required"; }
part def GainRow { attribute key:String; attribute avoided:String; attribute added:String; attribute condition:String; }
part gain0:GainRow { attribute :>> key="helper"; attribute :>> avoided="0..N second helper calls; first N remain"; attribute :>> added="P plan work + V qualification + A activation accounting + K capture/borrow tracking"; attribute :>> condition="Net positive iff sum helper costs > P+V+A+K; admitted N currently zero"; }
part gain1:GainRow { attribute :>> key="global-drain"; attribute :>> avoided="Avoid waiting for unrelated live testators and scanning every will at every binding"; attribute :>> added="Effect scope classification once per admitted closure/generation"; attribute :>> condition="Only valid for fully disjoint effects; weak-pending population may never globally drain"; }
part gain2:GainRow { attribute :>> key="shared-ledger"; attribute :>> avoided="Reuse RootRegistry and completion guard design across callback/job services"; attribute :>> added="Per reservation and handoff ledger transitions; unknown outcomes retained"; attribute :>> condition="Shared design reduces duplicate mechanisms, not proof obligations or measured cycles"; }
part gain3:GainRow { attribute :>> key="captures"; attribute :>> avoided="No eager freeing or forced single-shot conversion"; attribute :>> added="Retained root storage until last real capture/borrower retires"; attribute :>> condition="Unbounded capture lifetime means no guaranteed memory saving or drain latency"; }
part gain4:GainRow { attribute :>> key="parallel"; attribute :>> avoided="Immutable plan can enable independent emission consumers"; attribute :>> added="Per-session context, owner custody and snapshot validity"; attribute :>> condition="Requires separate incremental/session isolation proofs; no speedup measured"; }
part gain5:GainRow { attribute :>> key="language"; attribute :>> avoided="No Zig-only saving established for the same contracts"; attribute :>> added="Modern C23 and Zig both need roots, epochs, unknown-result ownership and GC integration"; attribute :>> condition="Modern C is mandatory mainline; Zig is not needed to establish this protocol"; }
part def ContractRow { attribute fromNode:String; attribute toNode:String; attribute custody:String; }
part contract0:ContractRow { attribute :>> fromNode="SysML"; attribute :>> toNode="ASCENT"; attribute :>> custody="Component-specific action, source and theorem obligations"; }
part contract1:ContractRow { attribute :>> fromNode="ASCENT"; attribute :>> toNode="QNT"; attribute :>> custody="Missing or stale source/route receipts keep actual candidate denied"; }
part contract2:ContractRow { attribute :>> fromNode="QNT"; attribute :>> toNode="Lean"; attribute :>> custody="Restricted typed IR, exact actions and all-step preservation"; }
part contract3:ContractRow { attribute :>> fromNode="macro expander"; attribute :>> toNode="will creation"; attribute :>> custody="Host Scheme execution can create arbitrary action; actual session evidence open"; }
part contract4:ContractRow { attribute :>> fromNode="will creation"; attribute :>> toNode="weak pending"; attribute :>> custody="Action strongly rooted, testator weak; accepted producer obligation"; }
part contract5:ContractRow { attribute :>> fromNode="external gate close"; attribute :>> toNode="weak pending"; attribute :>> custody="No erasure: later GC eligibility still allowed"; }
part contract6:ContractRow { attribute :>> fromNode="weak pending"; attribute :>> toNode="claimed action"; attribute :>> custody="GC queues; executor pops before loading operands"; }
part contract7:ContractRow { attribute :>> fromNode="claimed action"; attribute :>> toNode="runnable action"; attribute :>> custody="Load operands then zap will fields; explicit scanned carrier"; }
part contract8:ContractRow { attribute :>> fromNode="runnable action"; attribute :>> toNode="active action"; attribute :>> custody="POLL and dynamic invocation require matched root maps"; }
part contract9:ContractRow { attribute :>> fromNode="active action"; attribute :>> toNode="captured capability"; attribute :>> custody="Return or escape may retain multi-shot continuation authority"; }
part contract10:ContractRow { attribute :>> fromNode="captured capability"; attribute :>> toNode="active action"; attribute :>> custody="Resume creates a fresh activation ticket after gate closure"; }
part contract11:ContractRow { attribute :>> fromNode="active action"; attribute :>> toNode="child reservation"; attribute :>> custody="Reserve descendant obligation before parent completion"; }
part contract12:ContractRow { attribute :>> fromNode="active action"; attribute :>> toNode="unknown custody"; attribute :>> custody="Exception or unconfirmed completion prevents empty receipt"; }
part contract13:ContractRow { attribute :>> fromNode="scoped closure"; attribute :>> toNode="plan reuse receipt"; attribute :>> custody="No relevant weak/ready/active/unknown/capture/producer debt; admitted roots and aliases"; }
part contract14:ContractRow { attribute :>> fromNode="plan reuse receipt"; attribute :>> toNode="second helper retirement"; attribute :>> custody="Only complete emission-equivalence admission; first demand retained"; }
part def BindingRow { attribute actionName:String; attribute lemma:String; attribute scope:String; }
part binding0:BindingRow { attribute :>> actionName="will_action_drain.reserveExternal"; attribute :>> lemma="WillDrain.reserveExternalPreserves"; attribute :>> scope="Abstract lifecycle; source simulation and external reconciliation/capture receipts open"; }
part binding1:BindingRow { attribute :>> actionName="will_action_drain.reserveChild"; attribute :>> lemma="WillDrain.reserveChildPreserves"; attribute :>> scope="Abstract lifecycle; source simulation and external reconciliation/capture receipts open"; }
part binding2:BindingRow { attribute :>> actionName="will_action_drain.commitWill"; attribute :>> lemma="WillDrain.commitWillPreserves"; attribute :>> scope="Abstract lifecycle; source simulation and external reconciliation/capture receipts open"; }
part binding3:BindingRow { attribute :>> actionName="will_action_drain.abortReservation"; attribute :>> lemma="WillDrain.abortReservationPreserves"; attribute :>> scope="Abstract lifecycle; source simulation and external reconciliation/capture receipts open"; }
part binding4:BindingRow { attribute :>> actionName="will_action_drain.unknownCommit"; attribute :>> lemma="WillDrain.unknownCommitPreserves"; attribute :>> scope="Abstract lifecycle; source simulation and external reconciliation/capture receipts open"; }
part binding5:BindingRow { attribute :>> actionName="will_action_drain.closeExternal"; attribute :>> lemma="WillDrain.closeExternalPreserves"; attribute :>> scope="Abstract lifecycle; source simulation and external reconciliation/capture receipts open"; }
part binding6:BindingRow { attribute :>> actionName="will_action_drain.makeExecutable"; attribute :>> lemma="WillDrain.makeExecutablePreserves"; attribute :>> scope="Abstract lifecycle; source simulation and external reconciliation/capture receipts open"; }
part binding7:BindingRow { attribute :>> actionName="will_action_drain.dequeue"; attribute :>> lemma="WillDrain.dequeuePreserves"; attribute :>> scope="Abstract lifecycle; source simulation and external reconciliation/capture receipts open"; }
part binding8:BindingRow { attribute :>> actionName="will_action_drain.loadOperands"; attribute :>> lemma="WillDrain.loadOperandsPreserves"; attribute :>> scope="Abstract lifecycle; source simulation and external reconciliation/capture receipts open"; }
part binding9:BindingRow { attribute :>> actionName="will_action_drain.zapWillFields"; attribute :>> lemma="WillDrain.zapWillFieldsPreserves"; attribute :>> scope="Abstract lifecycle; source simulation and external reconciliation/capture receipts open"; }
part binding10:BindingRow { attribute :>> actionName="will_action_drain.enterAction"; attribute :>> lemma="WillDrain.enterActionPreserves"; attribute :>> scope="Abstract lifecycle; source simulation and external reconciliation/capture receipts open"; }
part binding11:BindingRow { attribute :>> actionName="will_action_drain.capture"; attribute :>> lemma="WillDrain.capturePreserves"; attribute :>> scope="Abstract lifecycle; source simulation and external reconciliation/capture receipts open"; }
part binding12:BindingRow { attribute :>> actionName="will_action_drain.returnAction"; attribute :>> lemma="WillDrain.returnActionPreserves"; attribute :>> scope="Abstract lifecycle; source simulation and external reconciliation/capture receipts open"; }
part binding13:BindingRow { attribute :>> actionName="will_action_drain.escapeAction"; attribute :>> lemma="WillDrain.escapeActionPreserves"; attribute :>> scope="Abstract lifecycle; source simulation and external reconciliation/capture receipts open"; }
part binding14:BindingRow { attribute :>> actionName="will_action_drain.resumeCapture"; attribute :>> lemma="WillDrain.resumeCapturePreserves"; attribute :>> scope="Abstract lifecycle; source simulation and external reconciliation/capture receipts open"; }
part binding15:BindingRow { attribute :>> actionName="will_action_drain.retireOneCapture"; attribute :>> lemma="WillDrain.retireOneCapturePreserves"; attribute :>> scope="Abstract lifecycle; source simulation and external reconciliation/capture receipts open"; }
part binding16:BindingRow { attribute :>> actionName="will_action_drain.resolveUnknownDone"; attribute :>> lemma="WillDrain.resolveUnknownDonePreserves"; attribute :>> scope="Abstract lifecycle; source simulation and external reconciliation/capture receipts open"; }
part binding17:BindingRow { attribute :>> actionName="will_action_drain.resolveUnknownReady"; attribute :>> lemma="WillDrain.resolveUnknownReadyPreserves"; attribute :>> scope="Abstract lifecycle; source simulation and external reconciliation/capture receipts open"; }
part binding18:BindingRow { attribute :>> actionName="will_action_drain.attestRootMaps"; attribute :>> lemma="WillDrain.attestRootMapsPreserves"; attribute :>> scope="Abstract lifecycle; source simulation and external reconciliation/capture receipts open"; }
part binding19:BindingRow { attribute :>> actionName="will_action_drain.attestAliasClosure"; attribute :>> lemma="WillDrain.attestAliasClosurePreserves"; attribute :>> scope="Abstract lifecycle; source simulation and external reconciliation/capture receipts open"; }
part binding20:BindingRow { attribute :>> actionName="will_action_drain.issue"; attribute :>> lemma="WillDrain.issuePreserves"; attribute :>> scope="Abstract lifecycle; source simulation and external reconciliation/capture receipts open"; }
part binding21:BindingRow { attribute :>> actionName="will_action_drain.reuse"; attribute :>> lemma="WillDrain.reusePreserves"; attribute :>> scope="Abstract lifecycle; source simulation and external reconciliation/capture receipts open"; }
part binding22:BindingRow { attribute :>> actionName="will_action_drain.unmanagedInterference"; attribute :>> lemma="WillDrain.unmanagedInterferencePreserves"; attribute :>> scope="Abstract lifecycle; source simulation and external reconciliation/capture receipts open"; }
part def ProofRow { attribute key:String; attribute lemma:String; }
part proof0:ProofRow { attribute :>> key="stepPreserves"; attribute :>> lemma="WillDrain.stepPreserves"; }
part proof1:ProofRow { attribute :>> key="reachableSafe"; attribute :>> lemma="WillDrain.reachableSafe"; }
part proof2:ProofRow { attribute :>> key="ticketConservation"; attribute :>> lemma="WillDrain.ticketConservation"; }
part proof3:ProofRow { attribute :>> key="issuedHasNoCaptures"; attribute :>> lemma="WillDrain.issuedHasNoCaptures"; }
part proof4:ProofRow { attribute :>> key="issuedHasNoUnknown"; attribute :>> lemma="WillDrain.issuedHasNoUnknown"; }
part proof5:ProofRow { attribute :>> key="issuedHasNoWeak"; attribute :>> lemma="WillDrain.issuedHasNoWeak"; }
part proof6:ProofRow { attribute :>> key="returnRetainsCaptures"; attribute :>> lemma="WillDrain.returnRetainsCaptures"; }
part proof7:ProofRow { attribute :>> key="zapTransfersLoaded"; attribute :>> lemma="WillDrain.zapTransfersLoaded"; }
part proof8:ProofRow { attribute :>> key="childReservationSurvivesReturn"; attribute :>> lemma="WillDrain.childReservationSurvivesReturn"; }
part proof9:ProofRow { attribute :>> key="closeDoesNotEraseWeak"; attribute :>> lemma="WillDrain.closeDoesNotEraseWeak"; }
part proof10:ProofRow { attribute :>> key="closeDoesNotEraseCapture"; attribute :>> lemma="WillDrain.closeDoesNotEraseCapture"; }
part proof11:ProofRow { attribute :>> key="replayCreatesTicket"; attribute :>> lemma="WillDrain.replayCreatesTicket"; }
part proof12:ProofRow { attribute :>> key="resumeNeedsCapability"; attribute :>> lemma="WillDrain.resumeNeedsCapability"; }
part proof13:ProofRow { attribute :>> key="noEarlyPermit"; attribute :>> lemma="WillDrain.noEarlyPermit"; }
part def RouteRow { attribute component:String; attribute actionName:String; attribute lemma:String; attribute producerAnchor:String; attribute obligationId:String; }
part route0:RouteRow { attribute :>> component="construction"; attribute :>> actionName="will_action_drain.reserveExternal"; attribute :>> lemma="WillDrain.reserveExternalPreserves"; attribute :>> producerAnchor="public-will"; attribute :>> obligationId="WD-producers"; }
part route1:RouteRow { attribute :>> component="construction"; attribute :>> actionName="will_action_drain.commitWill"; attribute :>> lemma="WillDrain.commitWillPreserves"; attribute :>> producerAnchor="ctor-list"; attribute :>> obligationId="WD-producers"; }
part route2:RouteRow { attribute :>> component="execution"; attribute :>> actionName="will_action_drain.dequeue"; attribute :>> lemma="WillDrain.dequeuePreserves"; attribute :>> producerAnchor="finalize-pop"; attribute :>> obligationId="WD-roots"; }
part route3:RouteRow { attribute :>> component="execution"; attribute :>> actionName="will_action_drain.loadOperands"; attribute :>> lemma="WillDrain.loadOperandsPreserves"; attribute :>> producerAnchor="action-load"; attribute :>> obligationId="WD-roots"; }
part route4:RouteRow { attribute :>> component="execution"; attribute :>> actionName="will_action_drain.zapWillFields"; attribute :>> lemma="WillDrain.zapWillFieldsPreserves"; attribute :>> producerAnchor="action-zap"; attribute :>> obligationId="WD-roots"; }
part route5:RouteRow { attribute :>> component="execution"; attribute :>> actionName="will_action_drain.enterAction"; attribute :>> lemma="WillDrain.enterActionPreserves"; attribute :>> producerAnchor="generated-poll"; attribute :>> obligationId="WD-roots"; }
part route6:RouteRow { attribute :>> component="restoration"; attribute :>> actionName="will_action_drain.capture"; attribute :>> lemma="WillDrain.capturePreserves"; attribute :>> producerAnchor="action-call"; attribute :>> obligationId="WD-restoration"; }
part route7:RouteRow { attribute :>> component="restoration"; attribute :>> actionName="will_action_drain.resumeCapture"; attribute :>> lemma="WillDrain.resumeCapturePreserves"; attribute :>> producerAnchor="action-call"; attribute :>> obligationId="WD-restoration"; }
part route8:RouteRow { attribute :>> component="restoration"; attribute :>> actionName="will_action_drain.escapeAction"; attribute :>> lemma="WillDrain.escapeActionPreserves"; attribute :>> producerAnchor="final-drain"; attribute :>> obligationId="WD-restoration"; }
part route9:RouteRow { attribute :>> component="admission"; attribute :>> actionName="will_action_drain.issue"; attribute :>> lemma="WillDrain.issuePreserves"; attribute :>> producerAnchor="second"; attribute :>> obligationId="WD-emission"; }
part def Need { attribute obligationId:String; attribute kind:String; attribute subjectPath:String; attribute subjectScope:String; ref owner:Owner; }
part formal:Need { attribute :>> obligationId="WD-formal"; attribute :>> kind="induction"; attribute :>> subjectPath="dev/refactoring/modern-c/models/lean/WillDrain.lean"; attribute :>> subjectScope="unbounded abstract ticket/capability safety under restricted typed IR"; ref :>> owner=execution; }
part producers:Need { attribute :>> obligationId="WD-producers"; attribute :>> kind="source"; attribute :>> subjectPath="dev/refactoring/modern-c/will-action-drain-design.org"; attribute :>> subjectScope="actual compiler session creator/alias/native inventory including macro/eval"; ref :>> owner=construction; }
part roots:Need { attribute :>> obligationId="WD-roots"; attribute :>> kind="source"; attribute :>> subjectPath="vendor/gambit/lib/_kernel.c"; attribute :>> subjectScope="matched generated POLL roots and root-transfer source simulation"; ref :>> owner=execution; }
part restoration:Need { attribute :>> obligationId="WD-restoration"; attribute :>> kind="source"; attribute :>> subjectPath="dev/refactoring/modern-c/will-action-drain-design.org"; attribute :>> subjectScope="last capture, nested/exception exits and unknown completion source refinement"; ref :>> owner=restoration; }
part effects:Need { attribute :>> obligationId="WD-effects"; attribute :>> kind="equivalence"; attribute :>> subjectPath="dev/refactoring/modern-c/will-action-drain-design.org"; attribute :>> subjectScope="actual metadata effect closure and old observer behavior"; ref :>> owner=admission; }
part platform:Need { attribute :>> obligationId="WD-platform"; attribute :>> kind="platform"; attribute :>> subjectPath="dev/refactoring/modern-c/language-baseline-design.org"; attribute :>> subjectScope="C23 memory order and current header/context/generated Darwin correspondence"; ref :>> owner=execution; }
part emission:Need { attribute :>> obligationId="WD-emission"; attribute :>> kind="equivalence"; attribute :>> subjectPath="dev/refactoring/modern-c/callback-carry-closure-design.org"; attribute :>> subjectScope="full previous emission/carry/failure gates still apply"; ref :>> owner=admission; }
part route10:RouteRow { attribute :>> component="execution"; attribute :>> actionName="will_action_drain.makeExecutable"; attribute :>> lemma="WillDrain.makeExecutablePreserves"; attribute :>> producerAnchor="weak-transition"; attribute :>> obligationId="WD-roots"; }
part route11:RouteRow { attribute :>> component="restoration"; attribute :>> actionName="will_action_drain.reserveChild"; attribute :>> lemma="WillDrain.reserveChildPreserves"; attribute :>> producerAnchor="will-contract"; attribute :>> obligationId="WD-restoration"; }
part memory5:MemoryRow { attribute :>> key="finite-fields"; attribute :>> publication="Checked bounded generation and ticket reservation before publication"; attribute :>> observation="Reject optimization admission before wrap or overflow"; attribute :>> obligation="Unbounded QNT/Lean Int proofs do not establish C23 counter ranges or ABA safety; fallback retains custody"; attribute :>> overhead="Range checks and generation retirement policy"; }
}
