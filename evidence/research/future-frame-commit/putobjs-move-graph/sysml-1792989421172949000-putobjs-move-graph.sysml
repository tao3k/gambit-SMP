package GambitPutObjsMoveGraph { private import ScalarValues::*;
part def SourceRow { attribute key:String; attribute path:String; attribute needle:String; attribute limit:String; }
part source0:SourceRow { attribute :>> key="put-unlock"; attribute :>> path="evidence/research/source-references/tcl/cbf86d62348d6b052e1961b4df995960fb21545f/generic/tclThreadAlloc.c"; attribute :>> needle="Tcl_MutexUnlock(objLockPtr);"; attribute :>> limit="known release and unknown release/held branches are distinct"; }
part source1:SourceRow { attribute :>> key="put-last"; attribute :>> path="evidence/research/source-references/tcl/cbf86d62348d6b052e1961b4df995960fb21545f/generic/tclThreadAlloc.c"; attribute :>> needle="fromPtr->lastPtr = lastPtr;"; attribute :>> limit="overwrite owner cache field without dereferencing old tail"; }
part source2:SourceRow { attribute :>> key="put-tail-read"; attribute :>> path="evidence/research/source-references/tcl/cbf86d62348d6b052e1961b4df995960fb21545f/generic/tclThreadAlloc.c"; attribute :>> needle="fromPtr->lastPtr->internalRep.twoPtrValue.ptr1 = sharedPtr->firstObjPtr;"; attribute :>> limit="last PutObjs target access through old tail occurs under shared lock"; }
part source3:SourceRow { attribute :>> key="consumer-lock"; attribute :>> path="evidence/research/source-references/tcl/cbf86d62348d6b052e1961b4df995960fb21545f/generic/tclThreadAlloc.c"; attribute :>> needle="numMove = sharedPtr->numObjects;"; attribute :>> limit="read under consumer objLockPtr, never pre-lock snapshot"; }
part source4:SourceRow { attribute :>> key="move-cap"; attribute :>> path="evidence/research/source-references/tcl/cbf86d62348d6b052e1961b4df995960fb21545f/generic/tclThreadAlloc.c"; attribute :>> needle="if (numMove > NOBJALLOC) {"; attribute :>> limit="801 shared nodes implies selected transfer800"; }
part source5:SourceRow { attribute :>> key="move-head"; attribute :>> path="evidence/research/source-references/tcl/cbf86d62348d6b052e1961b4df995960fb21545f/generic/tclThreadAlloc.c"; attribute :>> needle="Tcl_Obj *objPtr = fromPtr->firstObjPtr;"; attribute :>> limit="capture batch head before count writes"; }
part source6:SourceRow { attribute :>> key="move-dest-count"; attribute :>> path="evidence/research/source-references/tcl/cbf86d62348d6b052e1961b4df995960fb21545f/generic/tclThreadAlloc.c"; attribute :>> needle="toPtr->numObjects += numMove;"; attribute :>> limit="destination credit precedes graph detach"; }
part source7:SourceRow { attribute :>> key="move-src-count"; attribute :>> path="evidence/research/source-references/tcl/cbf86d62348d6b052e1961b4df995960fb21545f/generic/tclThreadAlloc.c"; attribute :>> needle="fromPtr->numObjects -= numMove;"; attribute :>> limit="source debit precedes traversal"; }
part source8:SourceRow { attribute :>> key="move-next"; attribute :>> path="evidence/research/source-references/tcl/cbf86d62348d6b052e1961b4df995960fb21545f/generic/tclThreadAlloc.c"; attribute :>> needle="objPtr = objPtr->internalRep.twoPtrValue.ptr1;"; attribute :>> limit="799 link reads for transfer800"; }
part source9:SourceRow { attribute :>> key="move-detach"; attribute :>> path="evidence/research/source-references/tcl/cbf86d62348d6b052e1961b4df995960fb21545f/generic/tclThreadAlloc.c"; attribute :>> needle="fromPtr->firstObjPtr = objPtr->internalRep.twoPtrValue.ptr1;"; attribute :>> limit="shared head becomes old suffix at node1202"; }
part source10:SourceRow { attribute :>> key="move-tail"; attribute :>> path="evidence/research/source-references/tcl/cbf86d62348d6b052e1961b4df995960fb21545f/generic/tclThreadAlloc.c"; attribute :>> needle="toPtr->lastPtr = objPtr;"; attribute :>> limit="destination takes tail1201"; }
part source11:SourceRow { attribute :>> key="move-cut"; attribute :>> path="evidence/research/source-references/tcl/cbf86d62348d6b052e1961b4df995960fb21545f/generic/tclThreadAlloc.c"; attribute :>> needle="objPtr->internalRep.twoPtrValue.ptr1 = toPtr->firstObjPtr; /* NULL */"; attribute :>> limit="write transferred tail link; original owner must not dereference"; }
part source12:SourceRow { attribute :>> key="move-publish"; attribute :>> path="evidence/research/source-references/tcl/cbf86d62348d6b052e1961b4df995960fb21545f/generic/tclThreadAlloc.c"; attribute :>> needle="toPtr->firstObjPtr = fromFirstObjPtr;"; attribute :>> limit="destination head published under lock"; }
part source13:SourceRow { attribute :>> key="consumer-unlock"; attribute :>> path="evidence/research/source-references/tcl/cbf86d62348d6b052e1961b4df995960fb21545f/generic/tclThreadAlloc.c"; attribute :>> needle="Tcl_MutexUnlock(objLockPtr);"; attribute :>> limit="selected consumer known return; unknown consumer exit not closed"; }
part source14:SourceRow { attribute :>> key="pop-load"; attribute :>> path="evidence/research/source-references/tcl/cbf86d62348d6b052e1961b4df995960fb21545f/generic/tclThreadAlloc.c"; attribute :>> needle="objPtr = cachePtr->firstObjPtr;"; attribute :>> limit="pop current destination head"; }
part source15:SourceRow { attribute :>> key="pop-next"; attribute :>> path="evidence/research/source-references/tcl/cbf86d62348d6b052e1961b4df995960fb21545f/generic/tclThreadAlloc.c"; attribute :>> needle="cachePtr->firstObjPtr = objPtr->internalRep.twoPtrValue.ptr1;"; attribute :>> limit="native next read before object allocation return"; }
part source16:SourceRow { attribute :>> key="pop-count"; attribute :>> path="evidence/research/source-references/tcl/cbf86d62348d6b052e1961b4df995960fb21545f/generic/tclThreadAlloc.c"; attribute :>> needle="cachePtr->numObjects--;"; attribute :>> limit="debit destination after head change"; }
part source17:SourceRow { attribute :>> key="pop-return"; attribute :>> path="evidence/research/source-references/tcl/cbf86d62348d6b052e1961b4df995960fb21545f/generic/tclThreadAlloc.c"; attribute :>> needle="return objPtr;"; attribute :>> limit="returned storage no longer grants old producer a free-link lease"; }
part source18:SourceRow { attribute :>> key="new-object"; attribute :>> path="evidence/research/source-references/tcl/cbf86d62348d6b052e1961b4df995960fb21545f/generic/tclInt.h"; attribute :>> needle="(objPtr)->typePtr  = NULL;"; attribute :>> limit="TclNewObj resets payload after allocation; no claim of C storage lifetime end"; }
part source19:SourceRow { attribute :>> key="cache-free"; attribute :>> path="evidence/research/source-references/tcl/cbf86d62348d6b052e1961b4df995960fb21545f/generic/tclThreadAlloc.c"; attribute :>> needle="TclpSysFree(cachePtr);"; attribute :>> limit="all buckets/keep0/TLS/native borrowers need independent closure"; }
part source20:SourceRow { attribute :>> key="prior"; attribute :>> path="dev/refactoring/modern-c/models/quint/putobjs_custody.qnt"; attribute :>> needle="action takePublishedBatch="; attribute :>> limit="actual previous opaque event is replaced at destination publication"; }
part def ObligationRow { attribute key:String; attribute status:String; attribute condition:String; }
part obligation0:ObligationRow { attribute :>> key="canonical-graph"; attribute :>> status="conditional-model"; attribute :>> condition="injective disjoint node IDs: kept1..401, batch402..1201, old shared1202; destination initially empty"; }
part obligation1:ObligationRow { attribute :>> key="source-order"; attribute :>> status="source-bound"; attribute :>> condition="selected MoveObjs transfer800 walks799 links; PutObjs lastPtr store reads no old tail target"; }
part obligation2:ObligationRow { attribute :>> key="native-encoding"; attribute :>> status="unresolved"; attribute :>> condition="logical IDs to valid distinct native storage/fields, alias closure and complete writer observation"; }
part obligation3:ObligationRow { attribute :>> key="unknown-unlock"; attribute :>> status="unresolved"; attribute :>> condition="retain source C activation/cache/record; consumer success does not restore original native return domain"; }
part obligation4:ObligationRow { attribute :>> key="retirement"; attribute :>> status="unresolved"; attribute :>> condition="all source users/TLS, bucket/keep0 cleanup and shared-lock provider lifetimes; no generation ABA"; }
part obligation5:ObligationRow { attribute :>> key="c23-order"; attribute :>> status="unresolved"; attribute :>> condition="actual Tcl mutex provider synchronization and protected independent completion publication"; }
part obligation6:ObligationRow { attribute :>> key="full-refinement"; attribute :>> status="unresolved"; attribute :>> condition="source CFG, consumer interruption/reentry, arbitrary graphs/competing producers and full parent-product proof"; }
part def RouteRow { attribute actionName:String; attribute lemma:String; attribute source:String; attribute obligation:String; }
part route0:RouteRow { attribute :>> actionName="knownProducerUnlock"; attribute :>> lemma="PutObjsMoveGraph.knownProducerUnlockPreserves"; attribute :>> source="put-unlock"; attribute :>> obligation="canonical-graph"; }
part route1:RouteRow { attribute :>> actionName="unknownReleased"; attribute :>> lemma="PutObjsMoveGraph.unknownReleasedPreserves"; attribute :>> source="put-unlock"; attribute :>> obligation="canonical-graph"; }
part route2:RouteRow { attribute :>> actionName="unknownStillHeld"; attribute :>> lemma="PutObjsMoveGraph.unknownStillHeldPreserves"; attribute :>> source="put-unlock"; attribute :>> obligation="canonical-graph"; }
part route3:RouteRow { attribute :>> actionName="fixProducerLast"; attribute :>> lemma="PutObjsMoveGraph.fixProducerLastPreserves"; attribute :>> source="put-last"; attribute :>> obligation="canonical-graph"; }
part route4:RouteRow { attribute :>> actionName="publishReceipt"; attribute :>> lemma="PutObjsMoveGraph.publishReceiptPreserves"; attribute :>> source="prior"; attribute :>> obligation="canonical-graph"; }
part route5:RouteRow { attribute :>> actionName="closeSourceAdmission"; attribute :>> lemma="PutObjsMoveGraph.closeSourceAdmissionPreserves"; attribute :>> source="cache-free"; attribute :>> obligation="canonical-graph"; }
part route6:RouteRow { attribute :>> actionName="sourceReadersDetached"; attribute :>> lemma="PutObjsMoveGraph.sourceReadersDetachedPreserves"; attribute :>> source="cache-free"; attribute :>> obligation="canonical-graph"; }
part route7:RouteRow { attribute :>> actionName="attestSourceFinalized"; attribute :>> lemma="PutObjsMoveGraph.attestSourceFinalizedPreserves"; attribute :>> source="cache-free"; attribute :>> obligation="canonical-graph"; }
part route8:RouteRow { attribute :>> actionName="reuseSourceCache"; attribute :>> lemma="PutObjsMoveGraph.reuseSourceCachePreserves"; attribute :>> source="cache-free"; attribute :>> obligation="canonical-graph"; }
part route9:RouteRow { attribute :>> actionName="borrowOldTail"; attribute :>> lemma="PutObjsMoveGraph.borrowOldTailPreserves"; attribute :>> source="put-tail-read"; attribute :>> obligation="canonical-graph"; }
part route10:RouteRow { attribute :>> actionName="acquireConsumer"; attribute :>> lemma="PutObjsMoveGraph.acquireConsumerPreserves"; attribute :>> source="consumer-lock"; attribute :>> obligation="canonical-graph"; }
part route11:RouteRow { attribute :>> actionName="selectMove800"; attribute :>> lemma="PutObjsMoveGraph.selectMove800Preserves"; attribute :>> source="move-cap"; attribute :>> obligation="canonical-graph"; }
part route12:RouteRow { attribute :>> actionName="loadMoveHead"; attribute :>> lemma="PutObjsMoveGraph.loadMoveHeadPreserves"; attribute :>> source="move-head"; attribute :>> obligation="canonical-graph"; }
part route13:RouteRow { attribute :>> actionName="creditDestination"; attribute :>> lemma="PutObjsMoveGraph.creditDestinationPreserves"; attribute :>> source="move-dest-count"; attribute :>> obligation="canonical-graph"; }
part route14:RouteRow { attribute :>> actionName="debitShared"; attribute :>> lemma="PutObjsMoveGraph.debitSharedPreserves"; attribute :>> source="move-src-count"; attribute :>> obligation="canonical-graph"; }
part route15:RouteRow { attribute :>> actionName="walkMovedNext"; attribute :>> lemma="PutObjsMoveGraph.walkMovedNextPreserves"; attribute :>> source="move-next"; attribute :>> obligation="canonical-graph"; }
part route16:RouteRow { attribute :>> actionName="detachSharedHead"; attribute :>> lemma="PutObjsMoveGraph.detachSharedHeadPreserves"; attribute :>> source="move-detach"; attribute :>> obligation="canonical-graph"; }
part route17:RouteRow { attribute :>> actionName="assignDestinationTail"; attribute :>> lemma="PutObjsMoveGraph.assignDestinationTailPreserves"; attribute :>> source="move-tail"; attribute :>> obligation="canonical-graph"; }
part route18:RouteRow { attribute :>> actionName="cutMovedTail"; attribute :>> lemma="PutObjsMoveGraph.cutMovedTailPreserves"; attribute :>> source="move-cut"; attribute :>> obligation="canonical-graph"; }
part route19:RouteRow { attribute :>> actionName="publishDestinationHead"; attribute :>> lemma="PutObjsMoveGraph.publishDestinationHeadPreserves"; attribute :>> source="move-publish"; attribute :>> obligation="canonical-graph"; }
part route20:RouteRow { attribute :>> actionName="releaseConsumer"; attribute :>> lemma="PutObjsMoveGraph.releaseConsumerPreserves"; attribute :>> source="consumer-unlock"; attribute :>> obligation="canonical-graph"; }
part route21:RouteRow { attribute :>> actionName="loadPopHead"; attribute :>> lemma="PutObjsMoveGraph.loadPopHeadPreserves"; attribute :>> source="pop-load"; attribute :>> obligation="canonical-graph"; }
part route22:RouteRow { attribute :>> actionName="advanceInteriorHead"; attribute :>> lemma="PutObjsMoveGraph.advanceInteriorHeadPreserves"; attribute :>> source="pop-next"; attribute :>> obligation="canonical-graph"; }
part route23:RouteRow { attribute :>> actionName="advanceLastHead"; attribute :>> lemma="PutObjsMoveGraph.advanceLastHeadPreserves"; attribute :>> source="pop-next"; attribute :>> obligation="canonical-graph"; }
part route24:RouteRow { attribute :>> actionName="decrementDestination"; attribute :>> lemma="PutObjsMoveGraph.decrementDestinationPreserves"; attribute :>> source="pop-count"; attribute :>> obligation="canonical-graph"; }
part route25:RouteRow { attribute :>> actionName="returnInterior"; attribute :>> lemma="PutObjsMoveGraph.returnInteriorPreserves"; attribute :>> source="pop-return"; attribute :>> obligation="canonical-graph"; }
part route26:RouteRow { attribute :>> actionName="returnTail"; attribute :>> lemma="PutObjsMoveGraph.returnTailPreserves"; attribute :>> source="pop-return"; attribute :>> obligation="canonical-graph"; }
part route27:RouteRow { attribute :>> actionName="initializeTailPayload"; attribute :>> lemma="PutObjsMoveGraph.initializeTailPayloadPreserves"; attribute :>> source="new-object"; attribute :>> obligation="canonical-graph"; }
part def GainRow { attribute key:String; attribute saved:String; attribute added:String; attribute condition:String; attribute status:String; }
part gain0:GainRow { attribute :>> key="source-work"; attribute :>> saved="401 kept-prefix reads;799 MoveObjs loop reads plus1 tail-link read advancing shared head;800 pop reads"; attribute :>> added="total2001 selected next-link reads remain; no runtime reduction established"; attribute :>> condition="801 shared nodes,800 transfer, destination empty and no other producer interference"; attribute :>> status="source-bound"; }
part gain1:GainRow { attribute :>> key="independent-last"; attribute :>> saved="original lastPtr overwrite can commute with destination tail cut under disjoint ownership"; attribute :>> added="must preserve original source cache metadata and retained401 pointer; no old-tail dereference"; attribute :>> condition="native storage/field disjointness and correct native owner"; attribute :>> status="conditional-model"; }
part gain2:GainRow { attribute :>> key="opaque-identity"; attribute :>> saved="late query need not pin or inspect a returned/reinitialized tail object"; attribute :>> added="pre-handoff stable NodeId/OperationId record; raw pointer is not a post-handoff lease"; attribute :>> condition="all queries/debug/hooks use metadata rather than stale object fields"; attribute :>> status="conditional"; }
part gain3:GainRow { attribute :>> key="unknown-release"; attribute :>> saved="separate physical mutex states from unknown original completion; avoid unsafe replay/unlock"; attribute :>> added="source cache/return domain may remain retained indefinitely even after destination drains800"; attribute :>> condition="stable supervisor exists before release; actual cancellation/unwind landing still required"; attribute :>> status="conditional-model"; }
part gain4:GainRow { attribute :>> key="retirement"; attribute :>> saved="source cache retirement need not retain transferred nodes once disjointness and all native users are closed"; attribute :>> added="finalization, TLS and shared allocator provider obligations remain; old retired0"; attribute :>> condition="selected consumer shared critical section complete; external finalization attestation"; attribute :>> status="unresolved"; }
part def IssuerRow { attribute key:String; attribute source:String; attribute signature:String; attribute gap:String; }
part issuer0:IssuerRow { attribute :>> key="source-owner"; attribute :>> source="put-last"; attribute :>> signature="known original unlock return, source cache alive and retained last401; overwrite only"; attribute :>> gap="an observed consumer acquire does not restore abandoned source C stack"; }
part issuer1:IssuerRow { attribute :>> key="consumer-owner"; attribute :>> source="move-publish"; attribute :>> signature="correct destination OS thread, objLockPtr held, transfer800 fully linked before unlock"; attribute :>> gap="consumer unknown exit/partial detach and arbitrary additional consumers remain open"; }
part issuer2:IssuerRow { attribute :>> key="record-owner"; attribute :>> source="prior"; attribute :>> signature="stable cache/node/operation incarnations recorded before old-tail handoff"; attribute :>> gap="no reading a stale raw pointer to manufacture identity after reuse"; }
part issuer3:IssuerRow { attribute :>> key="retire-owner"; attribute :>> source="cache-free"; attribute :>> signature="closed source admission, all native borrows detached and complete cache finalization known"; attribute :>> gap="source receipt is independent of shared-lock/provider retirement"; }
part def ConsumerRow { attribute key:String; attribute source:String; attribute access:String; attribute lifetime:String; attribute limit:String; }
part consumer0:ConsumerRow { attribute :>> key="source-last"; attribute :>> source="put-last"; attribute :>> access="write cache.lastPtr with retained last401"; attribute :>> lifetime="source cache metadata and retained prefix; not transferred tail payload"; attribute :>> limit="native field alias disjointness required"; }
part consumer1:ConsumerRow { attribute :>> key="move-cursor"; attribute :>> source="move-next"; attribute :>> access="follow402..1201 with799 next-link reads"; attribute :>> lifetime="objLockPtr and destination-owned transfer"; attribute :>> limit="fixed canonical chain proof only"; }
part consumer2:ConsumerRow { attribute :>> key="move-tail"; attribute :>> source="move-cut"; attribute :>> access="tail1201.next becomes destination previous head0"; attribute :>> lifetime="new consumer owns write while source cache may still store address1201"; attribute :>> limit="old source cannot dereference target despite pointer value remaining"; }
part consumer3:ConsumerRow { attribute :>> key="allocated-tail"; attribute :>> source="new-object"; attribute :>> access="800 allocation returns reach tail1201 and initialize Tcl object payload"; attribute :>> lifetime="destination allocation/returned object ownership"; attribute :>> limit="semantic role change; no physical free or proven C lifetime-end claim"; }
part consumer4:ConsumerRow { attribute :>> key="late-query"; attribute :>> source="prior"; attribute :>> access="read prepublished stable IDs rather than old native tail payload"; attribute :>> lifetime="independent record, source cache lease if needed"; attribute :>> limit="no reinterpretation of stale native pointer as a fresh safe identity"; }
part def EdgeRow { attribute fromNode:String; attribute toNode:String; attribute contract:String; }
part edge0:EdgeRow { attribute :>> fromNode="Shared batch800 plus suffix1"; attribute :>> toNode="Producer unlock"; attribute :>> contract="last target use of old tail already happened under lock"; }
part edge1:EdgeRow { attribute :>> fromNode="Producer unlock"; attribute :>> toNode="Consumer lock"; attribute :>> contract="physical release permits acquire; source may still know outcome only as unknown"; }
part edge2:EdgeRow { attribute :>> fromNode="Consumer lock"; attribute :>> toNode="799 cursor advances"; attribute :>> contract="credit destination, debit shared, follow canonical batch edges"; }
part edge3:EdgeRow { attribute :>> fromNode="799 cursor advances"; attribute :>> toNode="Destination tail cut"; attribute :>> contract="shared head becomes1202; destination tail1201.next becomes0"; }
part edge4:EdgeRow { attribute :>> fromNode="Destination tail cut"; attribute :>> toNode="Consumer unlock and pops"; attribute :>> contract="destination head402;800 returns can allocate old tail1201"; }
part edge5:EdgeRow { attribute :>> fromNode="Producer unlock"; attribute :>> toNode="Source lastPtr overwrite"; attribute :>> contract="use retained401; no read of old target1201; can commute with consumer cut"; }
part edge6:EdgeRow { attribute :>> fromNode="Consumer unlock and pops"; attribute :>> toNode="Opaque old-tail identity"; attribute :>> contract="payload may be reinitialized; queries need pre-handoff IDs"; }
part edge7:EdgeRow { attribute :>> fromNode="Unknown producer unlock"; attribute :>> toNode="Stable source supervisor"; attribute :>> contract="cache/activation retained even if consumer drains batch"; }
part edge8:EdgeRow { attribute :>> fromNode="Source lastPtr overwrite"; attribute :>> toNode="Source receipt and retirement"; attribute :>> contract="known protected publication plus native detachment/finalization"; }
part edge9:EdgeRow { attribute :>> fromNode="Source receipt and retirement"; attribute :>> toNode="Fresh cache generation"; attribute :>> contract="old metadata cannot authorize access to new cache incarnation"; }
part def RefinementRow { attribute key:String; attribute lemma:String; attribute source:String; attribute premise:String; }
part refinement0:RefinementRow { attribute :>> key="edge-encoding"; attribute :>> lemma="PutObjsMoveGraph.encodingUnique"; attribute :>> source="move-next"; attribute :>> premise="only two noncanonical link boundaries,401 and1201; distinct logical node identities"; }
part refinement1:RefinementRow { attribute :>> key="canonical-witness"; attribute :>> lemma="PutObjsMoveGraph.expandedEncodes"; attribute :>> source="move-head"; attribute :>> premise="expanded graph represents exactly the selected canonical family"; }
part refinement2:RefinementRow { attribute :>> key="cursor-read"; attribute :>> lemma="PutObjsMoveGraph.physicalWalk"; attribute :>> source="move-next"; attribute :>> premise="Safe and actual walkMovedNext guard; no moved-node return yet"; }
part refinement3:RefinementRow { attribute :>> key="shared-detach"; attribute :>> lemma="PutObjsMoveGraph.physicalDetach"; attribute :>> source="move-detach"; attribute :>> premise="cursor reaches1201; graph tail edge matches QNT tailNext"; }
part refinement4:RefinementRow { attribute :>> key="tail-cut"; attribute :>> lemma="PutObjsMoveGraph.physicalCut"; attribute :>> source="move-cut"; attribute :>> premise="destination initially empty and native fields do not alias producer metadata"; }
part refinement5:RefinementRow { attribute :>> key="source-no-edge-read"; attribute :>> lemma="PutObjsMoveGraph.producerFixPreservesEdges"; attribute :>> source="put-last"; attribute :>> premise="actual source overwrite uses retained last pointer, never old tail target"; }
part refinement6:RefinementRow { attribute :>> key="commutation"; attribute :>> lemma="PutObjsMoveGraph.fixAndCutCommute"; attribute :>> source="move-cut"; attribute :>> premise="consumer node link and producer cache metadata are separate native locations"; }
part refinement7:RefinementRow { attribute :>> key="returned-no-free-link"; attribute :>> lemma="PutObjsMoveGraph.allocatedTailNoLink"; attribute :>> source="pop-return"; attribute :>> premise="800 allocation returns; free-link role is distinct from C allocation lifetime"; }
part refinement8:RefinementRow { attribute :>> key="opaque-no-borrow"; attribute :>> lemma="PutObjsMoveGraph.opaqueCannotBorrow"; attribute :>> source="prior"; attribute :>> premise="post-unlock source no longer has a target read lease"; }
part refinement9:RefinementRow { attribute :>> key="unknown-no-retire"; attribute :>> lemma="PutObjsMoveGraph.unknownCannotRetire"; attribute :>> source="cache-free"; attribute :>> premise="original unlock knowledge remains unknown regardless of destination progress"; }
}
