package GambitNrAnchorRetirement { private import ScalarValues::*;
part def SourceRow { attribute key:String; attribute path:String; attribute needle:String; attribute limit:String; }
part source0:SourceRow { attribute :>> key="parse-producer"; attribute :>> path="evidence/research/source-references/tcl/cbf86d62348d6b052e1961b4df995960fb21545f/generic/tclParse.c"; attribute :>> needle="*statePtr = Tcl_SaveInterpState(interp, TCL_ERROR);"; attribute :>> limit="only parse error writes state; later prefix reparsing remains in producer"; }
part source1:SourceRow { attribute :>> key="parse-caller"; attribute :>> path="evidence/research/source-references/tcl/cbf86d62348d6b052e1961b4df995960fb21545f/generic/tclCompCmdsSZ.c"; attribute :>> needle="Tcl_InterpState state = NULL;"; attribute :>> limit="caller initializes out slot, conditionally restores before syntax error"; }
part source2:SourceRow { attribute :>> key="nr-add"; attribute :>> path="evidence/research/source-references/tcl/cbf86d62348d6b052e1961b4df995960fb21545f/generic/tclInt.h"; attribute :>> needle="_callbackPtr->data[0] = (ClientData)(data0);"; attribute :>> limit="token copied into allocated callback before TOP_CB publication"; }
part source3:SourceRow { attribute :>> key="nr-pop"; attribute :>> path="evidence/research/source-references/tcl/cbf86d62348d6b052e1961b4df995960fb21545f/generic/tclBasic.c"; attribute :>> needle="TOP_CB(interp) = callbackPtr->nextPtr;"; attribute :>> limit="pop before procPtr; empty chain does not imply no in-flight token"; }
part source4:SourceRow { attribute :>> key="nr-call"; attribute :>> path="evidence/research/source-references/tcl/cbf86d62348d6b052e1961b4df995960fb21545f/generic/tclBasic.c"; attribute :>> needle="result = procPtr(callbackPtr->data, interp, result);"; attribute :>> limit="node free only after callback normally returns"; }
part source5:SourceRow { attribute :>> key="expr-endpoint"; attribute :>> path="evidence/research/source-references/tcl/cbf86d62348d6b052e1961b4df995960fb21545f/generic/tclExecute.c"; attribute :>> needle="Tcl_InterpState state = (Tcl_InterpState)data[0];"; attribute :>> limit="success restores, error discards captured snapshot"; }
part source6:SourceRow { attribute :>> key="rewind"; attribute :>> path="evidence/research/source-references/tcl/cbf86d62348d6b052e1961b4df995960fb21545f/generic/tclBasic.c"; attribute :>> needle="TclNRAddCallback(interp, RewindCoroutineCallback, state,"; attribute :>> limit="Rewind posts saved token into current caller Env before switching"; }
part source7:SourceRow { attribute :>> key="delete-coro"; attribute :>> path="evidence/research/source-references/tcl/cbf86d62348d6b052e1961b4df995960fb21545f/generic/tclBasic.c"; attribute :>> needle="TclNRRunCallbacks(interp, RewindCoroutine(corPtr,TCL_OK), rootPtr);"; attribute :>> limit="suspended deletion drives rewind callbacks; not bare token free"; }
part source8:SourceRow { attribute :>> key="exit-coro"; attribute :>> path="evidence/research/source-references/tcl/cbf86d62348d6b052e1961b4df995960fb21545f/generic/tclBasic.c"; attribute :>> needle="TclDeleteExecEnv(corPtr->eePtr);"; attribute :>> limit="coroutine Env deleted in exit callback; caller snapshot Env is distinct"; }
part source9:SourceRow { attribute :>> key="delete-env"; attribute :>> path="evidence/research/source-references/tcl/cbf86d62348d6b052e1961b4df995960fb21545f/generic/tclExecute.c"; attribute :>> needle="Tcl_Panic(\"Deleting execEnv with pending TEOV callbacks!\");"; attribute :>> limit="normal non-process-exit guard; not arbitrary callback payload destructor"; }
part source10:SourceRow { attribute :>> key="previous-record"; attribute :>> path="dev/refactoring/modern-c/models/quint/saved_result_retirement.qnt"; attribute :>> needle="action retireRecord="; attribute :>> limit="actual prior record guard; no full product simulation"; }
part source11:SourceRow { attribute :>> key="gambit-entry"; attribute :>> path="vendor/gambit/lib/c_intf.c"; attribute :>> needle="call_sfun_with_cleanup"; attribute :>> limit="Gambit landing/root obligations remain outside Tcl callback node alone"; }
part def ObligationRow { attribute key:String; attribute status:String; attribute condition:String; }
part obligation0:ObligationRow { attribute :>> key="anchor-safety"; attribute :>> status="conditional-model"; attribute :>> condition="typed ID resolved through live process anchor; old record pinned under same lookup authority"; }
part obligation1:ObligationRow { attribute :>> key="parse-chain"; attribute :>> status="source-bound"; attribute :>> condition="same immutable Tcl commit/blob now supplies missing producer and initialized caller endpoint"; }
part obligation2:ObligationRow { attribute :>> key="nr-custody"; attribute :>> status="conditional-model"; attribute :>> condition="pop transfers to in-flight duty; known token consumption and node disposal before done"; }
part obligation3:ObligationRow { attribute :>> key="native-abnormal-exit"; attribute :>> status="unresolved"; attribute :>> condition="foreign escape after pop or token consumption needs independent node/token custody and exact receipt"; }
part obligation4:ObligationRow { attribute :>> key="anchor-implementation"; attribute :>> status="unresolved"; attribute :>> condition="live resolver before raw access, generation no-wrap, raw route exclusion and C23 orders"; }
part obligation5:ObligationRow { attribute :>> key="coroutine-product"; attribute :>> status="unresolved"; attribute :>> condition="caller Env versus coroutine Env identity and all nested rewind/delete paths refined"; }
part obligation6:ObligationRow { attribute :>> key="record-detachment"; attribute :>> status="unresolved"; attribute :>> condition="sender closure includes delivery drain; results and external observers detached before retirement"; }
part def RouteRow { attribute actionName:String; attribute lemma:String; attribute source:String; attribute obligation:String; }
part route0:RouteRow { attribute :>> actionName="produceErrorToken"; attribute :>> lemma="NrAnchorRetirement.produceErrorTokenPreserves"; attribute :>> source="parse-producer"; attribute :>> obligation="anchor-safety"; }
part route1:RouteRow { attribute :>> actionName="completeNoToken"; attribute :>> lemma="NrAnchorRetirement.completeNoTokenPreserves"; attribute :>> source="parse-producer"; attribute :>> obligation="anchor-safety"; }
part route2:RouteRow { attribute :>> actionName="enqueueToken"; attribute :>> lemma="NrAnchorRetirement.enqueueTokenPreserves"; attribute :>> source="nr-pop"; attribute :>> obligation="anchor-safety"; }
part route3:RouteRow { attribute :>> actionName="claimPrivateToken"; attribute :>> lemma="NrAnchorRetirement.claimPrivateTokenPreserves"; attribute :>> source="parse-producer"; attribute :>> obligation="anchor-safety"; }
part route4:RouteRow { attribute :>> actionName="popCallback"; attribute :>> lemma="NrAnchorRetirement.popCallbackPreserves"; attribute :>> source="nr-pop"; attribute :>> obligation="anchor-safety"; }
part route5:RouteRow { attribute :>> actionName="knownTokenConsumption"; attribute :>> lemma="NrAnchorRetirement.knownTokenConsumptionPreserves"; attribute :>> source="nr-pop"; attribute :>> obligation="anchor-safety"; }
part route6:RouteRow { attribute :>> actionName="unknownCallbackExit"; attribute :>> lemma="NrAnchorRetirement.unknownCallbackExitPreserves"; attribute :>> source="nr-pop"; attribute :>> obligation="anchor-safety"; }
part route7:RouteRow { attribute :>> actionName="reconcileKnownConsumption"; attribute :>> lemma="NrAnchorRetirement.reconcileKnownConsumptionPreserves"; attribute :>> source="nr-pop"; attribute :>> obligation="anchor-safety"; }
part route8:RouteRow { attribute :>> actionName="finishLanding"; attribute :>> lemma="NrAnchorRetirement.finishLandingPreserves"; attribute :>> source="nr-pop"; attribute :>> obligation="anchor-safety"; }
part route9:RouteRow { attribute :>> actionName="exitOwnerEnv"; attribute :>> lemma="NrAnchorRetirement.exitOwnerEnvPreserves"; attribute :>> source="nr-pop"; attribute :>> obligation="anchor-safety"; }
part route10:RouteRow { attribute :>> actionName="acquireAnchor"; attribute :>> lemma="NrAnchorRetirement.acquireAnchorPreserves"; attribute :>> source="previous-record"; attribute :>> obligation="anchor-safety"; }
part route11:RouteRow { attribute :>> actionName="lookupFirstRecord"; attribute :>> lemma="NrAnchorRetirement.lookupFirstRecordPreserves"; attribute :>> source="previous-record"; attribute :>> obligation="anchor-safety"; }
part route12:RouteRow { attribute :>> actionName="lookupSecondRecord"; attribute :>> lemma="NrAnchorRetirement.lookupSecondRecordPreserves"; attribute :>> source="previous-record"; attribute :>> obligation="anchor-safety"; }
part route13:RouteRow { attribute :>> actionName="releaseRecord"; attribute :>> lemma="NrAnchorRetirement.releaseRecordPreserves"; attribute :>> source="previous-record"; attribute :>> obligation="anchor-safety"; }
part route14:RouteRow { attribute :>> actionName="releaseAnchor"; attribute :>> lemma="NrAnchorRetirement.releaseAnchorPreserves"; attribute :>> source="previous-record"; attribute :>> obligation="anchor-safety"; }
part route15:RouteRow { attribute :>> actionName="closeRecordGate"; attribute :>> lemma="NrAnchorRetirement.closeRecordGatePreserves"; attribute :>> source="previous-record"; attribute :>> obligation="anchor-safety"; }
part route16:RouteRow { attribute :>> actionName="closeSenders"; attribute :>> lemma="NrAnchorRetirement.closeSendersPreserves"; attribute :>> source="previous-record"; attribute :>> obligation="anchor-safety"; }
part route17:RouteRow { attribute :>> actionName="closeRawRoutes"; attribute :>> lemma="NrAnchorRetirement.closeRawRoutesPreserves"; attribute :>> source="previous-record"; attribute :>> obligation="anchor-safety"; }
part route18:RouteRow { attribute :>> actionName="retireRecord"; attribute :>> lemma="NrAnchorRetirement.retireRecordPreserves"; attribute :>> source="previous-record"; attribute :>> obligation="anchor-safety"; }
part route19:RouteRow { attribute :>> actionName="reuseSlot"; attribute :>> lemma="NrAnchorRetirement.reuseSlotPreserves"; attribute :>> source="previous-record"; attribute :>> obligation="anchor-safety"; }
part route20:RouteRow { attribute :>> actionName="acceptFirstAck"; attribute :>> lemma="NrAnchorRetirement.acceptFirstAckPreserves"; attribute :>> source="previous-record"; attribute :>> obligation="anchor-safety"; }
part route21:RouteRow { attribute :>> actionName="rejectFirstAfterReuse"; attribute :>> lemma="NrAnchorRetirement.rejectFirstAfterReusePreserves"; attribute :>> source="previous-record"; attribute :>> obligation="anchor-safety"; }
part def GainRow { attribute key:String; attribute saved:String; attribute added:String; attribute condition:String; attribute status:String; }
part gain0:GainRow { attribute :>> key="parse-closure"; attribute :>> saved="no invented token on successful parse; real conditional producer now known"; attribute :>> added="caller slot and parse-buffer cleanup are separate; post-publication failure still needs escrow"; attribute :>> condition="normal error-token path and initialized caller slot"; attribute :>> status="source-bound"; }
part gain1:GainRow { attribute :>> key="nr-transfer"; attribute :>> saved="reuse existing callback data[0] normal ownership rather than duplicate snapshot"; attribute :>> added="O(I) independent records only for I admitted in-flight/unknown callback scopes"; attribute :>> condition="normal return plus native-abandonment policy"; attribute :>> status="conditional"; }
part gain2:GainRow { attribute :>> key="stable-query"; attribute :>> saved="retire settled heavy records without retaining every complete payload forever"; attribute :>> added="process-lifetime typed-ID resolver/slot generation; outcome history only when promised"; attribute :>> condition="retired-or-unknown API allowed; no permanent successful-result lookup promise"; attribute :>> status="design-only"; }
part gain3:GainRow { attribute :>> key="unknown-pop"; attribute :>> saved="0 queue-empty based owner retirement; 0 blind snapshot/node retry"; attribute :>> added="unknown token/node/provider custody may be indefinite"; attribute :>> condition="proof of native consumption and final node release"; attribute :>> status="conditional-model"; }
part gain4:GainRow { attribute :>> key="runtime-retirement"; attribute :>> saved="0 runtime paths retired; no native speedup measured"; attribute :>> added="resolver, exact-operation adapter and full coroutine product remain"; attribute :>> condition="all native refinement obligations"; attribute :>> status="design-only"; }
part def IssuerRow { attribute key:String; attribute source:String; attribute signature:String; attribute gap:String; }
part issuer0:IssuerRow { attribute :>> key="parser-caller"; attribute :>> source="parse-caller"; attribute :>> signature="initialized stable out slot; receive produced error token after normal producer return"; attribute :>> gap="callee may publish then abandon during reparsing"; }
part issuer1:IssuerRow { attribute :>> key="nr-dispatcher"; attribute :>> source="nr-pop"; attribute :>> signature="queue node custody transfers to in-flight callback before proc invocation"; attribute :>> gap="raw C local alone is not abnormal-exit escrow"; }
part issuer2:IssuerRow { attribute :>> key="snapshot-owner"; attribute :>> source="expr-endpoint"; attribute :>> signature="known Restore/Discard endpoint plus node completion"; attribute :>> gap="token consumption and node free are separate irreversible effects"; }
part issuer3:IssuerRow { attribute :>> key="query-resolver"; attribute :>> source="previous-record"; attribute :>> signature="live typed-ID anchor; validate generation and pin record before returning address"; attribute :>> gap="no code implements proposed InvocationId resolver yet"; }
part issuer4:IssuerRow { attribute :>> key="retirement-owner"; attribute :>> source="delete-env"; attribute :>> signature="combine closed senders/deliveries, lookup gate, old pins and source/result detachment"; attribute :>> gap="normal queue/panic guards are not complete native receipts"; }
part def ConsumerRow { attribute key:String; attribute source:String; attribute access:String; attribute lifetime:String; attribute limit:String; }
part consumer0:ConsumerRow { attribute :>> key="subst-private"; attribute :>> source="parse-producer"; attribute :>> access="error SaveInterpState -> prefix reparse -> caller out slot -> conditional Restore"; attribute :>> lifetime="producer then caller custody; parse allocation independently freed"; attribute :>> limit="normal return source path only"; }
part consumer1:ConsumerRow { attribute :>> key="nr-expression"; attribute :>> source="expr-endpoint"; attribute :>> access="callback data[0] -> Restore on TCL_OK else Discard"; attribute :>> lifetime="queued node then popped in-flight node"; attribute :>> limit="nonlocal escape may bypass generic node free"; }
part consumer2:ConsumerRow { attribute :>> key="suspended-delete"; attribute :>> source="delete-coro"; attribute :>> access="DeleteCoroutine -> RewindCoroutine -> NRRunCallbacks to saved root"; attribute :>> lifetime="token in caller Env callback scope"; attribute :>> limit="root marker and environment identity require product proof"; }
part consumer3:ConsumerRow { attribute :>> key="running-delete"; attribute :>> source="rewind"; attribute :>> access="deleted running command discovered by caller callback then Rewind"; attribute :>> lifetime="post-activation caller environment"; attribute :>> limit="not immediate deletion of all snapshot records"; }
part consumer4:ConsumerRow { attribute :>> key="coroutine-exit"; attribute :>> source="exit-coro"; attribute :>> access="exit callback disables deleteProc, deletes command and coroutine Env then restores caller"; attribute :>> lifetime="coroutine Env may die while caller Env callback remains live"; attribute :>> limit="do not forbid legitimate deletion of a different Env"; }
part consumer5:ConsumerRow { attribute :>> key="record-query"; attribute :>> source="previous-record"; attribute :>> access="typed InvocationId -> resolver -> generation match -> pin record"; attribute :>> lifetime="anchor before lookup; record until final pin return"; attribute :>> limit="raw pointer or late sender aliases remain outside admission"; }
part def EdgeRow { attribute fromNode:String; attribute toNode:String; attribute contract:String; }
part edge0:EdgeRow { attribute :>> fromNode="Parse error producer"; attribute :>> toNode="Caller token slot"; attribute :>> contract="normal handoff after additional prefix reparsing"; }
part edge1:EdgeRow { attribute :>> fromNode="Queued NR node"; attribute :>> toNode="In-flight callback"; attribute :>> contract="pop transfers custody; empty queue is not completion"; }
part edge2:EdgeRow { attribute :>> fromNode="In-flight callback"; attribute :>> toNode="Known token and node disposal"; attribute :>> contract="Restore/Discard endpoint then dispatcher node free"; }
part edge3:EdgeRow { attribute :>> fromNode="Cor Env exit"; attribute :>> toNode="Caller Env snapshot"; attribute :>> contract="distinct environments; rewind snapshot may still be pending"; }
part edge4:EdgeRow { attribute :>> fromNode="Typed InvocationId"; attribute :>> toNode="Process-lifetime resolver"; attribute :>> contract="safe first access through live authority"; }
part edge5:EdgeRow { attribute :>> fromNode="Process-lifetime resolver"; attribute :>> toNode="Pinned record"; attribute :>> contract="validate generation before address exposure"; }
part edge6:EdgeRow { attribute :>> fromNode="Closed record admission"; attribute :>> toNode="Prior record-pin drain"; attribute :>> contract="reject new lookups; keep existing readers"; }
part edge7:EdgeRow { attribute :>> fromNode="Record retired"; attribute :>> toNode="Late old-ID rejection"; attribute :>> contract="stable anchor survives; reject before raw record load"; }
}
