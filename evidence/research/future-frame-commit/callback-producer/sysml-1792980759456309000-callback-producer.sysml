package GambitCallbackProducer { private import ScalarValues::*;
part def SourceRow { attribute key:String; attribute path:String; attribute needle:String; attribute limit:String; }
part source0:SourceRow { attribute :>> key="eval-entry"; attribute :>> path="vendor/gambit/examples/tcltk/tcltk.scm"; attribute :>> needle="else if (Tcl_Eval (tcl_interp, cmd) != TCL_OK)"; attribute :>> limit="existing admitted caller candidate; no native producer receipt"; }
part source1:SourceRow { attribute :>> key="event-entry"; attribute :>> path="vendor/gambit/examples/tcltk/tcltk.scm"; attribute :>> needle="Tcl_DoOneEvent (TCL_DONT_WAIT)"; attribute :>> limit="event pump is a separate producer; not necessarily nested under tcltk_eval"; }
part source2:SourceRow { attribute :>> key="command-registration"; attribute :>> path="vendor/gambit/examples/tcltk/tcltk.scm"; attribute :>> needle="___result = ___BOOLEAN (Tcl_CreateCommand"; attribute :>> limit="defines proc/ClientData/delete hook; not per-eval authorization"; }
part source3:SourceRow { attribute :>> key="dispatch"; attribute :>> path="evidence/research/source-references/tcl/cbf86d62348d6b052e1961b4df995960fb21545f/generic/tclBasic.c"; attribute :>> needle="result = cmdPtr->proc(cmdPtr->clientData, interp, objc, argv);"; attribute :>> limit="actual string-command callback selection; argv freed on return"; }
part source4:SourceRow { attribute :>> key="marker-decrement"; attribute :>> path="vendor/gambit/lib/c_intf.c"; attribute :>> needle="___still_obj_refcount_dec (marker);"; attribute :>> limit="marker false does not make repeated decrement idempotent"; }
part source5:SourceRow { attribute :>> key="sfun-end"; attribute :>> path="vendor/gambit/lib/c_intf.c"; attribute :>> needle="if (bank) { ___return_rc_root(bank); ___release_rc(bank); }"; attribute :>> limit="cleanup uses actual bank; no per-TicketId stable receipt"; }
part source6:SourceRow { attribute :>> key="sfun-landing"; attribute :>> path="vendor/gambit/lib/c_intf.c"; attribute :>> needle="call_sfun_with_cleanup"; attribute :>> limit="known throw landing versus arbitrary foreign escape"; }
part source7:SourceRow { attribute :>> key="result-publish"; attribute :>> path="vendor/gambit/examples/tcltk/tcltk.scm"; attribute :>> needle="___CAST(Tcl_FreeProc*,___EXT(___release_string))"; attribute :>> limit="native result storage owner crosses callback return"; }
part source8:SourceRow { attribute :>> key="set-result"; attribute :>> path="evidence/research/source-references/tcl/cbf86d62348d6b052e1961b4df995960fb21545f/generic/tclResult.c"; attribute :>> needle="oldFreeProc(oldResult);"; attribute :>> limit="new result installed before old custom callback executes"; }
part source9:SourceRow { attribute :>> key="free-result"; attribute :>> path="evidence/research/source-references/tcl/cbf86d62348d6b052e1961b4df995960fb21545f/generic/tclResult.c"; attribute :>> needle="Tcl_FreeResult("; attribute :>> limit="custom free callback precedes freeProc clear"; }
part source10:SourceRow { attribute :>> key="reset-result"; attribute :>> path="evidence/research/source-references/tcl/cbf86d62348d6b052e1961b4df995960fb21545f/generic/tclResult.c"; attribute :>> needle="Tcl_ResetResult("; attribute :>> limit="custom free callback precedes final reset assignments"; }
part source11:SourceRow { attribute :>> key="delete-interp"; attribute :>> path="evidence/research/source-references/tcl/cbf86d62348d6b052e1961b4df995960fb21545f/generic/tclBasic.c"; attribute :>> needle="Tcl_EventuallyFree(interp, DeleteInterpProc);"; attribute :>> limit="deletion request is not necessarily immediate reclamation"; }
part source12:SourceRow { attribute :>> key="delete-result"; attribute :>> path="evidence/research/source-references/tcl/cbf86d62348d6b052e1961b4df995960fb21545f/generic/tclBasic.c"; attribute :>> needle="Tcl_FreeResult(interp);"; attribute :>> limit="after namespace/variable cleanup in DeleteInterpProc"; }
part source13:SourceRow { attribute :>> key="release-string"; attribute :>> path="vendor/gambit/lib/c_intf.c"; attribute :>> needle="___release_rc (x);"; attribute :>> limit="selected result hook is RC storage release; Scheme reentry not shown"; }
part source14:SourceRow { attribute :>> key="parent-model"; attribute :>> path="dev/refactoring/modern-c/models/quint/cleanup_ingress.qnt"; attribute :>> needle="action reserveChild="; attribute :>> limit="earlier bounded pre-close child policy is sufficient only for finite declared child work"; }
part def ObligationRow { attribute key:String; attribute status:String; attribute condition:String; }
part obligation0:ObligationRow { attribute :>> key="producer-safety"; attribute :>> status="conditional-model"; attribute :>> condition="pre-admitted eval/event-pump remains producer until no child or unknown cleanup"; }
part obligation1:ObligationRow { attribute :>> key="tcl-ordering"; attribute :>> status="source-bound"; attribute :>> condition="pinned local Tcl source; not loaded Darwin library identity"; }
part obligation2:ObligationRow { attribute :>> key="producer-issuer"; attribute :>> status="unresolved"; attribute :>> condition="stable owner/interpreter generation plus eval/pump entry and source command permit"; }
part obligation3:ObligationRow { attribute :>> key="exact-landing"; attribute :>> status="unresolved"; attribute :>> condition="per-invocation receipt outside captured Scheme frames; cleanup result known before done"; }
part obligation4:ObligationRow { attribute :>> key="native-result"; attribute :>> status="unresolved"; attribute :>> condition="old free hook reentry/escape, provider/source lifetime and same-operation disposal receipt"; }
part obligation5:ObligationRow { attribute :>> key="c23-refinement"; attribute :>> status="unresolved"; attribute :>> condition="native close/producer/dispatch synchronization and actual loaded ABI"; }
part def RouteRow { attribute actionName:String; attribute lemma:String; attribute source:String; attribute obligation:String; }
part route0:RouteRow { attribute :>> actionName="closeRoots"; attribute :>> lemma="CallbackProducer.closeRootsPreserves"; attribute :>> source="dispatch"; attribute :>> obligation="producer-safety"; }
part route1:RouteRow { attribute :>> actionName="dispatchChild"; attribute :>> lemma="CallbackProducer.dispatchChildPreserves"; attribute :>> source="dispatch"; attribute :>> obligation="producer-safety"; }
part route2:RouteRow { attribute :>> actionName="landingFirst"; attribute :>> lemma="CallbackProducer.landingFirstPreserves"; attribute :>> source="dispatch"; attribute :>> obligation="producer-safety"; }
part route3:RouteRow { attribute :>> actionName="landingSecond"; attribute :>> lemma="CallbackProducer.landingSecondPreserves"; attribute :>> source="dispatch"; attribute :>> obligation="producer-safety"; }
part route4:RouteRow { attribute :>> actionName="beginCleanup"; attribute :>> lemma="CallbackProducer.beginCleanupPreserves"; attribute :>> source="marker-decrement"; attribute :>> obligation="producer-safety"; }
part route5:RouteRow { attribute :>> actionName="loseCleanup"; attribute :>> lemma="CallbackProducer.loseCleanupPreserves"; attribute :>> source="marker-decrement"; attribute :>> obligation="producer-safety"; }
part route6:RouteRow { attribute :>> actionName="cleanupReceiptFirst"; attribute :>> lemma="CallbackProducer.cleanupReceiptFirstPreserves"; attribute :>> source="marker-decrement"; attribute :>> obligation="producer-safety"; }
part route7:RouteRow { attribute :>> actionName="settleFirst"; attribute :>> lemma="CallbackProducer.settleFirstPreserves"; attribute :>> source="marker-decrement"; attribute :>> obligation="producer-safety"; }
part route8:RouteRow { attribute :>> actionName="settleSecond"; attribute :>> lemma="CallbackProducer.settleSecondPreserves"; attribute :>> source="marker-decrement"; attribute :>> obligation="producer-safety"; }
part route9:RouteRow { attribute :>> actionName="sealProducer"; attribute :>> lemma="CallbackProducer.sealProducerPreserves"; attribute :>> source="dispatch"; attribute :>> obligation="producer-safety"; }
part route10:RouteRow { attribute :>> actionName="publishResult"; attribute :>> lemma="CallbackProducer.publishResultPreserves"; attribute :>> source="set-result"; attribute :>> obligation="producer-safety"; }
part route11:RouteRow { attribute :>> actionName="beginResultRelease"; attribute :>> lemma="CallbackProducer.beginResultReleasePreserves"; attribute :>> source="set-result"; attribute :>> obligation="producer-safety"; }
part route12:RouteRow { attribute :>> actionName="loseResultRelease"; attribute :>> lemma="CallbackProducer.loseResultReleasePreserves"; attribute :>> source="set-result"; attribute :>> obligation="producer-safety"; }
part route13:RouteRow { attribute :>> actionName="resultReleaseReceipt"; attribute :>> lemma="CallbackProducer.resultReleaseReceiptPreserves"; attribute :>> source="set-result"; attribute :>> obligation="producer-safety"; }
part route14:RouteRow { attribute :>> actionName="settleResultRelease"; attribute :>> lemma="CallbackProducer.settleResultReleasePreserves"; attribute :>> source="set-result"; attribute :>> obligation="producer-safety"; }
part route15:RouteRow { attribute :>> actionName="retireDomain"; attribute :>> lemma="CallbackProducer.retireDomainPreserves"; attribute :>> source="dispatch"; attribute :>> obligation="producer-safety"; }
part def GainRow { attribute key:String; attribute saved:String; attribute added:String; attribute condition:String; attribute status:String; }
part gain0:GainRow { attribute :>> key="eval-producer"; attribute :>> saved="no pre-enumeration of all callbacks from arbitrary Scheme/Tcl scripts"; attribute :>> added="one retained producer plus O(C) active child records"; attribute :>> condition="fresh root ingress closed; authorized existing eval/pump continues until it returns"; attribute :>> status="conditional"; }
part gain1:GainRow { attribute :>> key="landing-once"; attribute :>> saved="0 admitted stale-ticket or duplicate cleanup replays"; attribute :>> added="stable identity ledger and explicit cleanup-inflight/unknown custody"; attribute :>> condition="known cleanup receipt; marker false is not completion receipt"; attribute :>> status="conditional-model"; }
part gain2:GainRow { attribute :>> key="result-lifetime"; attribute :>> saved="0 premature provider/storage releases solely on callback return"; attribute :>> added="O(R) outstanding results and unknown operation records"; attribute :>> condition="Tcl disposal route and original free provider remain live"; attribute :>> status="unresolved-native"; }
part gain3:GainRow { attribute :>> key="existing-hook"; attribute :>> saved="reuse ordinary release_string -> release_rc"; attribute :>> added="no assumed Scheme reentry for this selected hook; other free hooks classified separately"; attribute :>> condition="effective target and origin binding qualified"; attribute :>> status="source-bound"; }
part gain4:GainRow { attribute :>> key="closure"; attribute :>> saved="0 current runtime paths retired; no measured speedup"; attribute :>> added="admission wrapper, identity mapping and cleanup/result receipt adapters"; attribute :>> condition="native caller and exception closure required"; attribute :>> status="design-only"; }
part def IssuerRow { attribute key:String; attribute source:String; attribute signature:String; attribute gap:String; }
part issuer0:IssuerRow { attribute :>> key="eval-owner"; attribute :>> source="eval-entry"; attribute :>> signature="VM entry plus interpreter generation and owner-thread scope before Tcl_Eval"; attribute :>> gap="existing adapter provides no stable receipt"; }
part issuer1:IssuerRow { attribute :>> key="pump-owner"; attribute :>> source="event-entry"; attribute :>> signature="separate admitted event-pump producer and dispatch scope"; attribute :>> gap="Scheme event mutex alone does not prove Tcl OS-thread ownership"; }
part issuer2:IssuerRow { attribute :>> key="command-owner"; attribute :>> source="command-registration"; attribute :>> signature="command/source identity lease before ClientData snapshot"; attribute :>> gap="registration itself is not dynamic invocation authority"; }
part issuer3:IssuerRow { attribute :>> key="landing-owner"; attribute :>> source="sfun-landing"; attribute :>> signature="exact InvocationId and cleanup completion, independent of multishot Scheme frame"; attribute :>> gap="end_sfun and marker kill have no idempotence token"; }
part issuer4:IssuerRow { attribute :>> key="result-owner"; attribute :>> source="result-publish"; attribute :>> signature="ResultId and original provider/storage hold until authoritative release"; attribute :>> gap="delete/reset return and raw freeProc fields are not durable receipts"; }
part def ConsumerRow { attribute key:String; attribute source:String; attribute access:String; attribute lifetime:String; attribute limit:String; }
part consumer0:ConsumerRow { attribute :>> key="admitted-eval"; attribute :>> source="eval-entry"; attribute :>> access="arbitrary command sequence may enter multiple callbacks"; attribute :>> lifetime="retained eval producer across root close"; attribute :>> limit="no proof all scripts terminate; forced bounded fuel changes semantics"; }
part consumer1:ConsumerRow { attribute :>> key="event-pump"; attribute :>> source="event-entry"; attribute :>> access="DoOneEvent can dispatch independent or nested event callbacks"; attribute :>> lifetime="separate owner-affine pump permit"; attribute :>> limit="cannot inherit authority from unrelated eval automatically"; }
part consumer2:ConsumerRow { attribute :>> key="command-dispatch"; attribute :>> source="dispatch"; attribute :>> access="proc/clientData called then argv freed"; attribute :>> lifetime="Tcl active invocation plus managed source and VM permit"; attribute :>> limit="Command refcount is not RC payload root ownership"; }
part consumer3:ConsumerRow { attribute :>> key="common-landing"; attribute :>> source="sfun-end"; attribute :>> access="return RC borrow, owner release, kill marker"; attribute :>> lifetime="exact active native invocation until cleanup acknowledged"; attribute :>> limit="repeated native cleanup can double release; no idempotence inferred"; }
part consumer4:ConsumerRow { attribute :>> key="replace-result"; attribute :>> source="set-result"; attribute :>> access="new result installed, old callback then object reset"; attribute :>> lifetime="both old disposal and new result ownership across callout"; attribute :>> limit="old hook can reenter/escape; publication is not old cleanup completion"; }
part consumer5:ConsumerRow { attribute :>> key="free-reset"; attribute :>> source="free-result"; attribute :>> access="custom callback before freeProc zero"; attribute :>> lifetime="owner-affine interpreter plus result disposal record"; attribute :>> limit="escaping callback may leave stale raw freeProc"; }
part consumer6:ConsumerRow { attribute :>> key="interpreter-delete"; attribute :>> source="delete-result"; attribute :>> access="eventual delete then namespace/variable cleanup then result free"; attribute :>> lifetime="native preservation and owner thread until actual deletion"; attribute :>> limit="DeleteInterp request return is not blanket all-resource receipt"; }
part def EdgeRow { attribute fromNode:String; attribute toNode:String; attribute contract:String; }
part edge0:EdgeRow { attribute :>> fromNode="Stable VM and interpreter owner"; attribute :>> toNode="Admitted eval / event pump"; attribute :>> contract="issue producer before native entry"; }
part edge1:EdgeRow { attribute :>> fromNode="Admitted eval / event pump"; attribute :>> toNode="Dynamic child InvocationId"; attribute :>> contract="allowed after fresh-root close while producer remains live"; }
part edge2:EdgeRow { attribute :>> fromNode="Dynamic child InvocationId"; attribute :>> toNode="Exact landing"; attribute :>> contract="session identity outside captured Scheme frames"; }
part edge3:EdgeRow { attribute :>> fromNode="Exact landing"; attribute :>> toNode="Cleanup in flight"; attribute :>> contract="single authorized attempt; not marker-based idempotence"; }
part edge4:EdgeRow { attribute :>> fromNode="Cleanup in flight"; attribute :>> toNode="Settled / retained unknown"; attribute :>> contract="receipt before settlement; no blind retry"; }
part edge5:EdgeRow { attribute :>> fromNode="New Tcl result"; attribute :>> toNode="Old free callback"; attribute :>> contract="publish new before freeing old; track both lifetimes"; }
part edge6:EdgeRow { attribute :>> fromNode="Old free callback"; attribute :>> toNode="Result release custody"; attribute :>> contract="normal known completion or retained OperationId"; }
part edge7:EdgeRow { attribute :>> fromNode="Producer sealed and results settled"; attribute :>> toNode="Prior retirement obligations"; attribute :>> contract="still require collective, join, roots and descriptor grace"; }
part route16:RouteRow { attribute :>> actionName="cleanupReceiptSecond"; attribute :>> lemma="CallbackProducer.cleanupReceiptSecondPreserves"; attribute :>> source="marker-decrement"; attribute :>> obligation="producer-safety"; }
}
