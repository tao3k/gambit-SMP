package GambitEscrowCriticalTail { private import ScalarValues::*;
part def SourceRow { attribute key:String; attribute path:String; attribute needle:String; attribute limit:String; }
part source0:SourceRow { attribute :>> key="queued-allocation"; attribute :>> path="evidence/research/source-references/tcl/cbf86d62348d6b052e1961b4df995960fb21545f/generic/tclInt.h"; attribute :>> needle="TCLNR_ALLOC((interp), (_callbackPtr));"; attribute :>> limit="TclNRAddCallback allocates before publication; not a nonallocating escrow registry"; }
part source1:SourceRow { attribute :>> key="pop"; attribute :>> path="evidence/research/source-references/tcl/cbf86d62348d6b052e1961b4df995960fb21545f/generic/tclBasic.c"; attribute :>> needle="TOP_CB(interp) = callbackPtr->nextPtr;"; attribute :>> limit="register independent custody before dequeue"; }
part source2:SourceRow { attribute :>> key="expr-issuer"; attribute :>> path="evidence/research/source-references/tcl/cbf86d62348d6b052e1961b4df995960fb21545f/generic/tclExecute.c"; attribute :>> needle="Tcl_InterpState state = (Tcl_InterpState)data[0];"; attribute :>> limit="normal endpoint observer for exact token; no persistent receipt emitted today"; }
part source3:SourceRow { attribute :>> key="token-discard"; attribute :>> path="evidence/research/source-references/tcl/cbf86d62348d6b052e1961b4df995960fb21545f/generic/tclResult.c"; attribute :>> needle="ckfree(statePtr);"; attribute :>> limit="object decrements precede final free; no general nonabandoning consumer"; }
part source4:SourceRow { attribute :>> key="node-tail"; attribute :>> path="evidence/research/source-references/tcl/cbf86d62348d6b052e1961b4df995960fb21545f/generic/tclInt.h"; attribute :>> needle="cachePtr->firstObjPtr = objPtr;"; attribute :>> limit="narrow cache put candidate; helper/debug/threshold branches differ"; }
part source5:SourceRow { attribute :>> key="node-stats"; attribute :>> path="evidence/research/source-references/tcl/cbf86d62348d6b052e1961b4df995960fb21545f/generic/tclInt.h"; attribute :>> needle="tclObjsFreed++"; attribute :>> limit="optional stats add observable writes after pool put; qualify selected full expansion"; }
part source6:SourceRow { attribute :>> key="global-pool"; attribute :>> path="evidence/research/source-references/tcl/cbf86d62348d6b052e1961b4df995960fb21545f/generic/tclInt.h"; attribute :>> needle="Tcl_MutexLock(&tclObjMutex);"; attribute :>> limit="global pool branch has lock/unlock rather than simple thread-local stores"; }
part source7:SourceRow { attribute :>> key="debug-free"; attribute :>> path="evidence/research/source-references/tcl/cbf86d62348d6b052e1961b4df995960fb21545f/generic/tclInt.h"; attribute :>> needle="_objPtr->typePtr = NULL;"; attribute :>> limit="debug node release uses a separate object teardown path"; }
part source8:SourceRow { attribute :>> key="cancel-disable"; attribute :>> path="vendor/gambit/lib/setup.c"; attribute :>> needle="pthread_setcancelstate(PTHREAD_CANCEL_DISABLE, &cancel_state)"; attribute :>> limit="actual resize-source protocol; not installed NR mask/guard"; }
part source9:SourceRow { attribute :>> key="cancel-restore"; attribute :>> path="vendor/gambit/lib/setup.c"; attribute :>> needle="pthread_setcancelstate(cancel_state, NULL);"; attribute :>> limit="source restores after stable request custody processing; may not provide NR receipt"; }
part source10:SourceRow { attribute :>> key="catcher"; attribute :>> path="vendor/gambit/include/_gambit/foreign_conversion.h.in"; attribute :>> needle="___LONGJMP1(___ps->catcher->buf);"; attribute :>> limit="POSIX cancellation mask does not exclude Scheme nonlocal transfer"; }
part source11:SourceRow { attribute :>> key="c-cleanup"; attribute :>> path="vendor/gambit/include/_gambit/foreign_conversion.h.in"; attribute :>> needle="cleanup; }"; attribute :>> limit="plain C cleanup block is lexical; not arbitrary longjmp finalization"; }
part source12:SourceRow { attribute :>> key="parent-model"; attribute :>> path="dev/refactoring/modern-c/models/quint/nr_inflight_handoff.qnt"; attribute :>> needle="action receiveNodeReceipt="; attribute :>> limit="actual prior token/node receipt distinction; full product remains open"; }
part def ObligationRow { attribute key:String; attribute status:String; attribute condition:String; }
part obligation0:ObligationRow { attribute :>> key="critical-safety"; attribute :>> status="conditional-model"; attribute :>> condition="preallocated slot and stable owner; known registration before pop; no unknown force-release"; }
part obligation1:ObligationRow { attribute :>> key="source-classification"; attribute :>> status="source-bound"; attribute :>> condition="Tcl callback endpoints, pool variants and Gambit cancellation/catcher source boundaries"; }
part obligation2:ObligationRow { attribute :>> key="slot-service"; attribute :>> status="unresolved"; attribute :>> condition="pool created before entry; exact NativeThreadDomain/root identity and allocation-free stores qualified"; }
part obligation3:ObligationRow { attribute :>> key="tail-qualification"; attribute :>> status="unresolved"; attribute :>> condition="selected expansion has no allocation/callout/abandonment; cancellation suppression alone insufficient"; }
part obligation4:ObligationRow { attribute :>> key="receipt-issuers"; attribute :>> status="unresolved"; attribute :>> condition="token observer, native pool owner and landing supervisor sign exact OperationId"; }
part obligation5:ObligationRow { attribute :>> key="resolver-landing"; attribute :>> status="unresolved"; attribute :>> condition="lock owner/phase and pin-return state recover before reuse; unknown retains debt"; }
part obligation6:ObligationRow { attribute :>> key="c23-refinement"; attribute :>> status="unresolved"; attribute :>> condition="mask failure/restore semantics, thread affinity, root coverage, memory orders and no-wrap"; }
part def RouteRow { attribute actionName:String; attribute lemma:String; attribute source:String; attribute obligation:String; }
part route0:RouteRow { attribute :>> actionName="disableCancel"; attribute :>> lemma="EscrowCriticalTail.disableCancelPreserves"; attribute :>> source="pop"; attribute :>> obligation="critical-safety"; }
part route1:RouteRow { attribute :>> actionName="exhaustPool"; attribute :>> lemma="EscrowCriticalTail.exhaustPoolPreserves"; attribute :>> source="pop"; attribute :>> obligation="critical-safety"; }
part route2:RouteRow { attribute :>> actionName="returnExternalSlot"; attribute :>> lemma="EscrowCriticalTail.returnExternalSlotPreserves"; attribute :>> source="pop"; attribute :>> obligation="critical-safety"; }
part route3:RouteRow { attribute :>> actionName="claimSlot"; attribute :>> lemma="EscrowCriticalTail.claimSlotPreserves"; attribute :>> source="pop"; attribute :>> obligation="critical-safety"; }
part route4:RouteRow { attribute :>> actionName="releaseUnpublishedSlot"; attribute :>> lemma="EscrowCriticalTail.releaseUnpublishedSlotPreserves"; attribute :>> source="pop"; attribute :>> obligation="critical-safety"; }
part route5:RouteRow { attribute :>> actionName="registerKnown"; attribute :>> lemma="EscrowCriticalTail.registerKnownPreserves"; attribute :>> source="pop"; attribute :>> obligation="critical-safety"; }
part route6:RouteRow { attribute :>> actionName="registerUnknown"; attribute :>> lemma="EscrowCriticalTail.registerUnknownPreserves"; attribute :>> source="pop"; attribute :>> obligation="critical-safety"; }
part route7:RouteRow { attribute :>> actionName="reconcileRegistration"; attribute :>> lemma="EscrowCriticalTail.reconcileRegistrationPreserves"; attribute :>> source="pop"; attribute :>> obligation="critical-safety"; }
part route8:RouteRow { attribute :>> actionName="popKnownEscrow"; attribute :>> lemma="EscrowCriticalTail.popKnownEscrowPreserves"; attribute :>> source="pop"; attribute :>> obligation="critical-safety"; }
part route9:RouteRow { attribute :>> actionName="escapeToken"; attribute :>> lemma="EscrowCriticalTail.escapeTokenPreserves"; attribute :>> source="pop"; attribute :>> obligation="critical-safety"; }
part route10:RouteRow { attribute :>> actionName="knownTokenEndpoint"; attribute :>> lemma="EscrowCriticalTail.knownTokenEndpointPreserves"; attribute :>> source="pop"; attribute :>> obligation="critical-safety"; }
part route11:RouteRow { attribute :>> actionName="qualifyNodeTail"; attribute :>> lemma="EscrowCriticalTail.qualifyNodeTailPreserves"; attribute :>> source="node-tail"; attribute :>> obligation="critical-safety"; }
part route12:RouteRow { attribute :>> actionName="completeQualifiedNodeTail"; attribute :>> lemma="EscrowCriticalTail.completeQualifiedNodeTailPreserves"; attribute :>> source="node-tail"; attribute :>> obligation="critical-safety"; }
part route13:RouteRow { attribute :>> actionName="unknownNodeCompletion"; attribute :>> lemma="EscrowCriticalTail.unknownNodeCompletionPreserves"; attribute :>> source="node-tail"; attribute :>> obligation="critical-safety"; }
part route14:RouteRow { attribute :>> actionName="knownNodeBackendReceipt"; attribute :>> lemma="EscrowCriticalTail.knownNodeBackendReceiptPreserves"; attribute :>> source="node-tail"; attribute :>> obligation="critical-safety"; }
part route15:RouteRow { attribute :>> actionName="publishDone"; attribute :>> lemma="EscrowCriticalTail.publishDonePreserves"; attribute :>> source="node-tail"; attribute :>> obligation="critical-safety"; }
part route16:RouteRow { attribute :>> actionName="acquireMap"; attribute :>> lemma="EscrowCriticalTail.acquireMapPreserves"; attribute :>> source="pop"; attribute :>> obligation="critical-safety"; }
part route17:RouteRow { attribute :>> actionName="issuePin"; attribute :>> lemma="EscrowCriticalTail.issuePinPreserves"; attribute :>> source="pop"; attribute :>> obligation="critical-safety"; }
part route18:RouteRow { attribute :>> actionName="unlockMap"; attribute :>> lemma="EscrowCriticalTail.unlockMapPreserves"; attribute :>> source="pop"; attribute :>> obligation="critical-safety"; }
part route19:RouteRow { attribute :>> actionName="escapeHoldingMap"; attribute :>> lemma="EscrowCriticalTail.escapeHoldingMapPreserves"; attribute :>> source="catcher"; attribute :>> obligation="critical-safety"; }
part route20:RouteRow { attribute :>> actionName="knownOwnerLanding"; attribute :>> lemma="EscrowCriticalTail.knownOwnerLandingPreserves"; attribute :>> source="catcher"; attribute :>> obligation="critical-safety"; }
part route21:RouteRow { attribute :>> actionName="returnPinKnown"; attribute :>> lemma="EscrowCriticalTail.returnPinKnownPreserves"; attribute :>> source="pop"; attribute :>> obligation="critical-safety"; }
part route22:RouteRow { attribute :>> actionName="returnPinUnknown"; attribute :>> lemma="EscrowCriticalTail.returnPinUnknownPreserves"; attribute :>> source="catcher"; attribute :>> obligation="critical-safety"; }
part route23:RouteRow { attribute :>> actionName="knownPinReturnLanding"; attribute :>> lemma="EscrowCriticalTail.knownPinReturnLandingPreserves"; attribute :>> source="catcher"; attribute :>> obligation="critical-safety"; }
part route24:RouteRow { attribute :>> actionName="handoffSupervisor"; attribute :>> lemma="EscrowCriticalTail.handoffSupervisorPreserves"; attribute :>> source="cancel-restore"; attribute :>> obligation="critical-safety"; }
part route25:RouteRow { attribute :>> actionName="beginRestoreCancel"; attribute :>> lemma="EscrowCriticalTail.beginRestoreCancelPreserves"; attribute :>> source="cancel-restore"; attribute :>> obligation="critical-safety"; }
part route26:RouteRow { attribute :>> actionName="knownRestoreReturn"; attribute :>> lemma="EscrowCriticalTail.knownRestoreReturnPreserves"; attribute :>> source="cancel-restore"; attribute :>> obligation="critical-safety"; }
part route27:RouteRow { attribute :>> actionName="retireSlot"; attribute :>> lemma="EscrowCriticalTail.retireSlotPreserves"; attribute :>> source="cancel-restore"; attribute :>> obligation="critical-safety"; }
part def GainRow { attribute key:String; attribute saved:String; attribute added:String; attribute condition:String; attribute status:String; }
part gain0:GainRow { attribute :>> key="prepop-reserve"; attribute :>> saved="0 required allocator calls during admitted claim/register/pop itself"; attribute :>> added="P preinitialized descriptors; memory P*S bytes before allocator overhead"; attribute :>> condition="capacity and root/native-owner setup occur before critical registration"; attribute :>> status="conditional"; }
part gain1:GainRow { attribute :>> key="exhaustion"; attribute :>> saved="0 pop with missing/unknown escrow; no waiting on own nested slot"; attribute :>> added="bounded profiles may refuse/pause before pop; unbounded nesting needs safe growth policy"; attribute :>> condition="P covers maximum active + retained debt or admission fails"; attribute :>> status="conditional-model"; }
part gain2:GainRow { attribute :>> key="narrow-tail"; attribute :>> saved="one qualified no-callout pool-put plus completion publication may fuse"; attribute :>> added="variant/effects proof and cancellation/nonlocal-exit policy"; attribute :>> condition="ordinary token cleanup remains callout-capable; no generic transaction"; attribute :>> status="unresolved-native"; }
part gain3:GainRow { attribute :>> key="resolver-return"; attribute :>> saved="reuse common mapping authority and existing exact guard ownership"; attribute :>> added="unknown lock/pin debts retain owner; no speculative decrement or forced unlock"; attribute :>> condition="known owner landing and coherent pin accounting"; attribute :>> status="conditional-model"; }
part gain4:GainRow { attribute :>> key="runtime-value"; attribute :>> saved="0 runtime paths retired; no measured speedup"; attribute :>> added="stable pool service, receipts and entry/landing adaptation remain"; attribute :>> condition="net benefit depends on avoided allocation, duplicate wrappers and bounded retention"; attribute :>> status="design-only"; }
part def IssuerRow { attribute key:String; attribute source:String; attribute signature:String; attribute gap:String; }
part issuer0:IssuerRow { attribute :>> key="preallocated-service"; attribute :>> source="queued-allocation"; attribute :>> signature="stable slot index/incarnation, NativeThreadDomain and source refs before pop"; attribute :>> gap="current Tcl allocation/node local is not this registry"; }
part issuer1:IssuerRow { attribute :>> key="token-observer"; attribute :>> source="expr-issuer"; attribute :>> signature="Restore/Discard normal return for exact token OperationId"; attribute :>> gap="no completion receipt on partial/escaped destructor path"; }
part issuer2:IssuerRow { attribute :>> key="pool-owner"; attribute :>> source="node-tail"; attribute :>> signature="qualified node last-use, actual owner-thread pool put and published receipt"; attribute :>> gap="all selected macro branches/debug/statistics must be covered"; }
part issuer3:IssuerRow { attribute :>> key="landing-supervisor"; attribute :>> source="cancel-restore"; attribute :>> signature="independent ownership of remaining debt before restoring cancellation"; attribute :>> gap="restoration can fail/not return; local statement after restore insufficient"; }
part issuer4:IssuerRow { attribute :>> key="resolver-owner"; attribute :>> source="catcher"; attribute :>> signature="map operation phase, lock identity and pin credit reconciled at exact native landing"; attribute :>> gap="mutex return code or missing ACK alone cannot recover consistency"; }
part def ConsumerRow { attribute key:String; attribute source:String; attribute access:String; attribute lifetime:String; attribute limit:String; }
part consumer0:ConsumerRow { attribute :>> key="prepop-dispatch"; attribute :>> source="pop"; attribute :>> access="queued node survives reserve/register then commits pop"; attribute :>> lifetime="stable slot and original native owner/source"; attribute :>> limit="claim failure retains queued payload"; }
part consumer1:ConsumerRow { attribute :>> key="token-endpoint"; attribute :>> source="expr-issuer"; attribute :>> access="exact expression success Restore/error Discard; rewind Restore as prior study"; attribute :>> lifetime="callback/native return domain until endpoint known"; attribute :>> limit="not every generic NR callback has this payload"; }
part consumer2:ConsumerRow { attribute :>> key="cache-return"; attribute :>> source="node-tail"; attribute :>> access="qualified local cache stores or unqualified helper/debug/global branch"; attribute :>> lifetime="original Tcl native thread and selected allocator"; attribute :>> limit="metadata handoff does not migrate node release"; }
part consumer3:ConsumerRow { attribute :>> key="cancel-restore-owner"; attribute :>> source="cancel-restore"; attribute :>> access="publish stable ownership before unmask; finish only on known landing"; attribute :>> lifetime="supervisor outlives abandoned C activation"; attribute :>> limit="does not make arbitrary Scheme longjmp cancellation-safe"; }
part consumer4:ConsumerRow { attribute :>> key="map-reader"; attribute :>> source="parent-model"; attribute :>> access="pin stays after lookup lock release; return under matching authority"; attribute :>> lifetime="stable guard/lease operation through last payload access"; attribute :>> limit="unknown return is a debt, not a zero pin count"; }
part def EdgeRow { attribute fromNode:String; attribute toNode:String; attribute contract:String; }
part edge0:EdgeRow { attribute :>> fromNode="Initialized slot service"; attribute :>> toNode="Known escrow registration"; attribute :>> contract="no allocation/callout in qualified claim/register prefix"; }
part edge1:EdgeRow { attribute :>> fromNode="Known escrow registration"; attribute :>> toNode="Queue pop"; attribute :>> contract="unknown/exhausted reservation leaves node queued"; }
part edge2:EdgeRow { attribute :>> fromNode="Token endpoint"; attribute :>> toNode="Known or retained custody"; attribute :>> contract="normal return observer or exact backend evidence"; }
part edge3:EdgeRow { attribute :>> fromNode="Qualified node tail"; attribute :>> toNode="Done receipt"; attribute :>> contract="no-callout pool put and publication on native owner"; }
part edge4:EdgeRow { attribute :>> fromNode="Done receipt"; attribute :>> toNode="Stable supervisor"; attribute :>> contract="transfer debt before restoring cancellation"; }
part edge5:EdgeRow { attribute :>> fromNode="Map lock and pin owner"; attribute :>> toNode="Exact landing or retained unknown"; attribute :>> contract="no forced unlock or blind pin decrement"; }
part edge6:EdgeRow { attribute :>> fromNode="Stable supervisor"; attribute :>> toNode="Slot reuse"; attribute :>> contract="only known restoration, no locks/pins and detached users"; }
}
