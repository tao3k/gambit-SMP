package GambitNrInflightHandoff { private import ScalarValues::*;
part def SourceRow { attribute key:String; attribute path:String; attribute needle:String; attribute limit:String; }
part source0:SourceRow { attribute :>> key="pop"; attribute :>> path="evidence/research/source-references/tcl/cbf86d62348d6b052e1961b4df995960fb21545f/generic/tclBasic.c"; attribute :>> needle="TOP_CB(interp) = callbackPtr->nextPtr;"; attribute :>> limit="last queued custody must hand off before callback callout"; }
part source1:SourceRow { attribute :>> key="invoke"; attribute :>> path="evidence/research/source-references/tcl/cbf86d62348d6b052e1961b4df995960fb21545f/generic/tclBasic.c"; attribute :>> needle="result = procPtr(callbackPtr->data, interp, result);"; attribute :>> limit="callback data pointer into node remains valid through call"; }
part source2:SourceRow { attribute :>> key="node-free"; attribute :>> path="evidence/research/source-references/tcl/cbf86d62348d6b052e1961b4df995960fb21545f/generic/tclBasic.c"; attribute :>> needle="TCLNR_FREE(interp, callbackPtr);"; attribute :>> limit="only reached after proc returns normally; not token destructor"; }
part source3:SourceRow { attribute :>> key="expr"; attribute :>> path="evidence/research/source-references/tcl/cbf86d62348d6b052e1961b4df995960fb21545f/generic/tclExecute.c"; attribute :>> needle="Tcl_InterpState state = (Tcl_InterpState)data[0];"; attribute :>> limit="known callback kind provides token-specific Restore/Discard endpoint"; }
part source4:SourceRow { attribute :>> key="restore"; attribute :>> path="evidence/research/source-references/tcl/cbf86d62348d6b052e1961b4df995960fb21545f/generic/tclResult.c"; attribute :>> needle="Tcl_DiscardInterpState(state);"; attribute :>> limit="Restore may already mutate interp fields before final discard"; }
part source5:SourceRow { attribute :>> key="discard"; attribute :>> path="evidence/research/source-references/tcl/cbf86d62348d6b052e1961b4df995960fb21545f/generic/tclResult.c"; attribute :>> needle="ckfree(statePtr);"; attribute :>> limit="multiple object decrements precede state allocation free"; }
part source6:SourceRow { attribute :>> key="pool"; attribute :>> path="evidence/research/source-references/tcl/cbf86d62348d6b052e1961b4df995960fb21545f/generic/tclInt.h"; attribute :>> needle="DO NOT LET THEM CROSS THREAD BOUNDARIES"; attribute :>> limit="small node allocator is owner/thread sensitive"; }
part source7:SourceRow { attribute :>> key="pool-put"; attribute :>> path="evidence/research/source-references/tcl/cbf86d62348d6b052e1961b4df995960fb21545f/generic/tclInt.h"; attribute :>> needle="cachePtr->firstObjPtr = objPtr;"; attribute :>> limit="pool return makes address reusable; not necessarily libc free"; }
part source8:SourceRow { attribute :>> key="decr"; attribute :>> path="evidence/research/source-references/tcl/cbf86d62348d6b052e1961b4df995960fb21545f/generic/tclInt.h"; attribute :>> needle="TclFreeObj(objPtr);"; attribute :>> limit="internal-representation destruction slow path; selected effects need qualification"; }
part source9:SourceRow { attribute :>> key="rewind"; attribute :>> path="evidence/research/source-references/tcl/cbf86d62348d6b052e1961b4df995960fb21545f/generic/tclBasic.c"; attribute :>> needle="return Tcl_RestoreInterpState(interp, (Tcl_InterpState)data[0]);"; attribute :>> limit="actual rewind token callback; different caller and coroutine Env lifetimes"; }
part source10:SourceRow { attribute :>> key="parent-model"; attribute :>> path="dev/refactoring/modern-c/models/quint/nr_anchor_retirement.qnt"; attribute :>> needle="action finishLanding="; attribute :>> limit="earlier collapsed node-release/done action is refined here"; }
part source11:SourceRow { attribute :>> key="gambit-landing"; attribute :>> path="vendor/gambit/lib/c_intf.c"; attribute :>> needle="call_sfun_with_cleanup"; attribute :>> limit="Tcl token completion does not discharge Scheme native-frame/RC roots"; }
part def ObligationRow { attribute key:String; attribute status:String; attribute condition:String; }
part obligation0:ObligationRow { attribute :>> key="handoff-safety"; attribute :>> status="conditional-model"; attribute :>> condition="independent escrow before pop; token and node receipts distinct from effects"; }
part obligation1:ObligationRow { attribute :>> key="source-cuts"; attribute :>> status="source-bound"; attribute :>> condition="pop/call/Restore/Discard/pool-free last-use boundaries in fixed local source"; }
part obligation2:ObligationRow { attribute :>> key="native-escrow"; attribute :>> status="unresolved"; attribute :>> condition="record prepared without unsafe callout; owner-thread and exact callback/source identity retained"; }
part obligation3:ObligationRow { attribute :>> key="unknown-completion"; attribute :>> status="unresolved"; attribute :>> condition="no retry after effect unknown; same-operation backend receipt or non-abandoning tail required"; }
part obligation4:ObligationRow { attribute :>> key="resolver-native"; attribute :>> status="unresolved"; attribute :>> condition="live process resolver lock really covers mapping check and pin; abnormal lock holder custody"; }
part obligation5:ObligationRow { attribute :>> key="native-generation"; attribute :>> status="unresolved"; attribute :>> condition="all raw readers/senders excluded or drained; no-wrap and identity tuple validated before pointer exposure"; }
part obligation6:ObligationRow { attribute :>> key="c23-refinement"; attribute :>> status="unresolved"; attribute :>> condition="effective mutex/atomics, Tcl thread owner and loaded ABI; full product with Gambit roots"; }
part def RouteRow { attribute actionName:String; attribute lemma:String; attribute source:String; attribute obligation:String; }
part route0:RouteRow { attribute :>> actionName="prepareEscrow"; attribute :>> lemma="NrInflightHandoff.prepareEscrowPreserves"; attribute :>> source="pop"; attribute :>> obligation="handoff-safety"; }
part route1:RouteRow { attribute :>> actionName="popNode"; attribute :>> lemma="NrInflightHandoff.popNodePreserves"; attribute :>> source="pop"; attribute :>> obligation="handoff-safety"; }
part route2:RouteRow { attribute :>> actionName="beginToken"; attribute :>> lemma="NrInflightHandoff.beginTokenPreserves"; attribute :>> source="discard"; attribute :>> obligation="handoff-safety"; }
part route3:RouteRow { attribute :>> actionName="applyTokenEffect"; attribute :>> lemma="NrInflightHandoff.applyTokenEffectPreserves"; attribute :>> source="discard"; attribute :>> obligation="handoff-safety"; }
part route4:RouteRow { attribute :>> actionName="loseTokenReturn"; attribute :>> lemma="NrInflightHandoff.loseTokenReturnPreserves"; attribute :>> source="discard"; attribute :>> obligation="handoff-safety"; }
part route5:RouteRow { attribute :>> actionName="receiveTokenReceipt"; attribute :>> lemma="NrInflightHandoff.receiveTokenReceiptPreserves"; attribute :>> source="discard"; attribute :>> obligation="handoff-safety"; }
part route6:RouteRow { attribute :>> actionName="confirmToken"; attribute :>> lemma="NrInflightHandoff.confirmTokenPreserves"; attribute :>> source="discard"; attribute :>> obligation="handoff-safety"; }
part route7:RouteRow { attribute :>> actionName="beginNodeRelease"; attribute :>> lemma="NrInflightHandoff.beginNodeReleasePreserves"; attribute :>> source="node-free"; attribute :>> obligation="handoff-safety"; }
part route8:RouteRow { attribute :>> actionName="applyNodeEffect"; attribute :>> lemma="NrInflightHandoff.applyNodeEffectPreserves"; attribute :>> source="node-free"; attribute :>> obligation="handoff-safety"; }
part route9:RouteRow { attribute :>> actionName="loseNodeReturn"; attribute :>> lemma="NrInflightHandoff.loseNodeReturnPreserves"; attribute :>> source="node-free"; attribute :>> obligation="handoff-safety"; }
part route10:RouteRow { attribute :>> actionName="receiveNodeReceipt"; attribute :>> lemma="NrInflightHandoff.receiveNodeReceiptPreserves"; attribute :>> source="node-free"; attribute :>> obligation="handoff-safety"; }
part route11:RouteRow { attribute :>> actionName="confirmNode"; attribute :>> lemma="NrInflightHandoff.confirmNodePreserves"; attribute :>> source="node-free"; attribute :>> obligation="handoff-safety"; }
part route12:RouteRow { attribute :>> actionName="publishDone"; attribute :>> lemma="NrInflightHandoff.publishDonePreserves"; attribute :>> source="node-free"; attribute :>> obligation="handoff-safety"; }
part route13:RouteRow { attribute :>> actionName="releaseEscrow"; attribute :>> lemma="NrInflightHandoff.releaseEscrowPreserves"; attribute :>> source="node-free"; attribute :>> obligation="handoff-safety"; }
part route14:RouteRow { attribute :>> actionName="beginLookup"; attribute :>> lemma="NrInflightHandoff.beginLookupPreserves"; attribute :>> source="parent-model"; attribute :>> obligation="handoff-safety"; }
part route15:RouteRow { attribute :>> actionName="validateFirst"; attribute :>> lemma="NrInflightHandoff.validateFirstPreserves"; attribute :>> source="parent-model"; attribute :>> obligation="handoff-safety"; }
part route16:RouteRow { attribute :>> actionName="validateSecond"; attribute :>> lemma="NrInflightHandoff.validateSecondPreserves"; attribute :>> source="parent-model"; attribute :>> obligation="handoff-safety"; }
part route17:RouteRow { attribute :>> actionName="installPin"; attribute :>> lemma="NrInflightHandoff.installPinPreserves"; attribute :>> source="parent-model"; attribute :>> obligation="handoff-safety"; }
part route18:RouteRow { attribute :>> actionName="unlockLookup"; attribute :>> lemma="NrInflightHandoff.unlockLookupPreserves"; attribute :>> source="parent-model"; attribute :>> obligation="handoff-safety"; }
part route19:RouteRow { attribute :>> actionName="releasePin"; attribute :>> lemma="NrInflightHandoff.releasePinPreserves"; attribute :>> source="parent-model"; attribute :>> obligation="handoff-safety"; }
part route20:RouteRow { attribute :>> actionName="rejectClosedLookup"; attribute :>> lemma="NrInflightHandoff.rejectClosedLookupPreserves"; attribute :>> source="parent-model"; attribute :>> obligation="handoff-safety"; }
part route21:RouteRow { attribute :>> actionName="rejectOldFirst"; attribute :>> lemma="NrInflightHandoff.rejectOldFirstPreserves"; attribute :>> source="parent-model"; attribute :>> obligation="handoff-safety"; }
part route22:RouteRow { attribute :>> actionName="acquireClose"; attribute :>> lemma="NrInflightHandoff.acquireClosePreserves"; attribute :>> source="parent-model"; attribute :>> obligation="handoff-safety"; }
part route23:RouteRow { attribute :>> actionName="closeGate"; attribute :>> lemma="NrInflightHandoff.closeGatePreserves"; attribute :>> source="parent-model"; attribute :>> obligation="handoff-safety"; }
part route24:RouteRow { attribute :>> actionName="closeSenders"; attribute :>> lemma="NrInflightHandoff.closeSendersPreserves"; attribute :>> source="parent-model"; attribute :>> obligation="handoff-safety"; }
part route25:RouteRow { attribute :>> actionName="closeRawRoutes"; attribute :>> lemma="NrInflightHandoff.closeRawRoutesPreserves"; attribute :>> source="parent-model"; attribute :>> obligation="handoff-safety"; }
part route26:RouteRow { attribute :>> actionName="retireRecord"; attribute :>> lemma="NrInflightHandoff.retireRecordPreserves"; attribute :>> source="parent-model"; attribute :>> obligation="handoff-safety"; }
part route27:RouteRow { attribute :>> actionName="unlockClose"; attribute :>> lemma="NrInflightHandoff.unlockClosePreserves"; attribute :>> source="parent-model"; attribute :>> obligation="handoff-safety"; }
part route28:RouteRow { attribute :>> actionName="acquireReuse"; attribute :>> lemma="NrInflightHandoff.acquireReusePreserves"; attribute :>> source="parent-model"; attribute :>> obligation="handoff-safety"; }
part route29:RouteRow { attribute :>> actionName="commitReuse"; attribute :>> lemma="NrInflightHandoff.commitReusePreserves"; attribute :>> source="parent-model"; attribute :>> obligation="handoff-safety"; }
part route30:RouteRow { attribute :>> actionName="unlockReuse"; attribute :>> lemma="NrInflightHandoff.unlockReusePreserves"; attribute :>> source="parent-model"; attribute :>> obligation="handoff-safety"; }
part def GainRow { attribute key:String; attribute saved:String; attribute added:String; attribute condition:String; attribute status:String; }
part gain0:GainRow { attribute :>> key="escrow"; attribute :>> saved="reuse existing node/token payload; no blanket deep snapshot copy"; attribute :>> added="one independent in-flight record across pop and abnormal exit"; attribute :>> condition="stable record prepared before ownership gap; exact source identity"; attribute :>> status="conditional"; }
part gain1:GainRow { attribute :>> key="split-receipts"; attribute :>> saved="0 effect-as-completion inference; 0 blind token/node retries"; attribute :>> added="two operation identities/receipts or one qualified non-abandoning completion chain"; attribute :>> condition="native consumption and pool return can be irreversible separately"; attribute :>> status="conditional-model"; }
part gain2:GainRow { attribute :>> key="same-thread-release"; attribute :>> saved="reuse ordinary Tcl pool on its qualified native owner"; attribute :>> added="unknown owners keep affinity; handoff metadata does not move allocator obligations"; attribute :>> condition="no cross-thread node pool return without explicit allocator migration proof"; attribute :>> status="source-bound"; }
part gain3:GainRow { attribute :>> key="resolver-fusion"; attribute :>> saved="one mapping critical section can fuse validation and record pin"; attribute :>> added="existing pin lifetime beyond lock; stable resolver and closed admission still needed"; attribute :>> condition="all mapping readers/close/reuse obey same authority"; attribute :>> status="conditional"; }
part gain4:GainRow { attribute :>> key="record-reuse"; attribute :>> saved="drop heavy done record after pins/producers/raw routes drain"; attribute :>> added="generation identity and resolver grace; long-lived resolver state and unknown records"; attribute :>> condition="no-wrap refusal and no permanent arbitrary history promise"; attribute :>> status="design-only"; }
part def IssuerRow { attribute key:String; attribute source:String; attribute signature:String; attribute gap:String; }
part issuer0:IssuerRow { attribute :>> key="dispatch-owner"; attribute :>> source="pop"; attribute :>> signature="pre-pop registered stable escrow and original Env/thread/source identity"; attribute :>> gap="current callbackPtr local is not durable abandonment custody"; }
part issuer1:IssuerRow { attribute :>> key="token-endpoint"; attribute :>> source="expr"; attribute :>> signature="exact callback Restore/Discard normal return or backend receipt"; attribute :>> gap="partial object decrements/state free may have happened on unknown return"; }
part issuer2:IssuerRow { attribute :>> key="node-owner"; attribute :>> source="pool"; attribute :>> signature="known last callback data use and owner-affine pool return"; attribute :>> gap="pool mutation/ACK and node address reuse need independent control"; }
part issuer3:IssuerRow { attribute :>> key="resolver-owner"; attribute :>> source="parent-model"; attribute :>> signature="live lock authority joins generation check with pin acquisition"; attribute :>> gap="not implemented by atomic pointer load then refcount increment"; }
part issuer4:IssuerRow { attribute :>> key="retirement-owner"; attribute :>> source="parent-model"; attribute :>> signature="closed record entry, final pins, exact completion and sender/raw-route receipts"; attribute :>> gap="unknown lock/callback/delivery cannot be erased to produce zero"; }
part def ConsumerRow { attribute key:String; attribute source:String; attribute access:String; attribute lifetime:String; attribute limit:String; }
part consumer0:ConsumerRow { attribute :>> key="expression-node"; attribute :>> source="expr"; attribute :>> access="TclNRRunCallbacks -> ExprObjCallback data[0]/data[1] -> Restore or Discard -> return -> node free"; attribute :>> lifetime="data points inside node; token and result objects have separate endpoints"; attribute :>> limit="foreign escape before generic free has no normal receipt"; }
part consumer1:ConsumerRow { attribute :>> key="rewind-node"; attribute :>> source="rewind"; attribute :>> access="RewindCoroutineCallback restores snapshot then returns to dispatcher"; attribute :>> lifetime="caller Env snapshot scope and node survive until last use"; attribute :>> limit="full coroutine exit product remains unresolved"; }
part consumer2:ConsumerRow { attribute :>> key="state-cleanup"; attribute :>> source="discard"; attribute :>> access="decrement error/result object refs before freeing snapshot state"; attribute :>> lifetime="exact original token operation"; attribute :>> limit="unknown may be partial or already freed; pointer is not recovery handle"; }
part consumer3:ConsumerRow { attribute :>> key="small-pool-free"; attribute :>> source="pool-put"; attribute :>> access="TCLNR_FREE -> TclSmallFreeEx -> selected object storage service"; attribute :>> lifetime="owner thread/allocator until put and node last use"; attribute :>> limit="not every compile configuration uses this pool branch"; }
part consumer4:ConsumerRow { attribute :>> key="typed-query"; attribute :>> source="parent-model"; attribute :>> access="borrow live resolver -> validate generation -> pin record before unlock"; attribute :>> lifetime="pin outlives map lock until reader last use"; attribute :>> limit="no record exposure while candidate only validated"; }
part consumer5:ConsumerRow { attribute :>> key="mapping-reuse"; attribute :>> source="parent-model"; attribute :>> access="close under same authority; wait record pins; retire; wait anchor readers; publish new generation"; attribute :>> lifetime="record and map/identity graces are separate"; attribute :>> limit="process resolver still lives; lock-free alternatives not proved"; }
part def EdgeRow { attribute fromNode:String; attribute toNode:String; attribute contract:String; }
part edge0:EdgeRow { attribute :>> fromNode="Queued node"; attribute :>> toNode="Pre-pop stable escrow"; attribute :>> contract="prepare/register before queue ownership disappears"; }
part edge1:EdgeRow { attribute :>> fromNode="Pre-pop stable escrow"; attribute :>> toNode="Token operation"; attribute :>> contract="one invocation-bound attempt; unknown retains opaque responsibility"; }
part edge2:EdgeRow { attribute :>> fromNode="Token operation"; attribute :>> toNode="Node release operation"; attribute :>> contract="token completion receipt before last-use pool return"; }
part edge3:EdgeRow { attribute :>> fromNode="Node release operation"; attribute :>> toNode="Done publication"; attribute :>> contract="known node receipt then release escrow; not a free-effect guess"; }
part edge4:EdgeRow { attribute :>> fromNode="Live resolver lock"; attribute :>> toNode="Validated candidate"; attribute :>> contract="generation/mapping check while exclusive authority held"; }
part edge5:EdgeRow { attribute :>> fromNode="Validated candidate"; attribute :>> toNode="Pinned record"; attribute :>> contract="acquire pin before unlock/address exposure"; }
part edge6:EdgeRow { attribute :>> fromNode="Close/reclaim lock"; attribute :>> toNode="Closed record gate"; attribute :>> contract="existing pins survive; new lookups denied"; }
part edge7:EdgeRow { attribute :>> fromNode="No record pins"; attribute :>> toNode="Record retirement"; attribute :>> contract="also exact completion/sender/raw route closure"; }
part edge8:EdgeRow { attribute :>> fromNode="No anchor readers"; attribute :>> toNode="Generation reuse"; attribute :>> contract="exclusive update; old typed ID refused before record access"; }
}
