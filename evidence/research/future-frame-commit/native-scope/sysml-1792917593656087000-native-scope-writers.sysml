package GambitNativeScopeWriters { private import ScalarValues::*;
part def SourceRow { attribute key:String; attribute path:String; attribute needle:String; attribute limit:String; }
part source0:SourceRow { attribute :>> key="call"; attribute :>> path="vendor/gambit/lib/setup.c"; attribute :>> needle="___EXP_FUNC(___SCMOBJ,___call)"; attribute :>> limit="candidate issuer before argument loads; current phase check is not a scope"; }
part source1:SourceRow { attribute :>> key="run"; attribute :>> path="vendor/gambit/lib/setup.c"; attribute :>> needle="___EXP_FUNC(___SCMOBJ,___run)"; attribute :>> limit="entry-local writes precede call; must admit before them"; }
part source2:SourceRow { attribute :>> key="sfun"; attribute :>> path="vendor/gambit/lib/c_intf.c"; attribute :>> needle="___EXP_FUNC(___SCMOBJ,___begin_sfun)"; attribute :>> limit="existing source borrow and bank are context-bound"; }
part source3:SourceRow { attribute :>> key="catcher"; attribute :>> path="vendor/gambit/include/_gambit/foreign_conversion.h.in"; attribute :>> needle="#define ___BEGIN_TRY"; attribute :>> limit="live jmpbuf extent; stable landing issuer still proposed"; }
part source4:SourceRow { attribute :>> key="sfun-exit"; attribute :>> path="vendor/gambit/include/_gambit/foreign_conversion.h.in"; attribute :>> needle="#define ___END_SFUN "; attribute :>> limit="candidate completion adapter; not exception-proof stable guard"; }
part source5:SourceRow { attribute :>> key="rc-write"; attribute :>> path="vendor/gambit/lib/_mem/rc-allocation.inc"; attribute :>> needle="___EXP_FUNC(___BOOL,___set_data_rc)"; attribute :>> limit="payload writer, not a future control-word writer"; }
part source6:SourceRow { attribute :>> key="rc-root"; attribute :>> path="vendor/gambit/lib/_mem/rc-roots.inc"; attribute :>> needle="mark_array (work, &h->data, 1);"; attribute :>> limit="root slot is updated by GC under closed domain"; }
part source7:SourceRow { attribute :>> key="thread"; attribute :>> path="vendor/gambit/lib/os_thread.c"; attribute :>> needle="void ___thread_set_pstate"; attribute :>> limit="TLS and affinity only; no ticket or extent identity"; }
part source8:SourceRow { attribute :>> key="tcl"; attribute :>> path="vendor/gambit/examples/tcltk/tcltk.scm"; attribute :>> needle="___HIDDEN int scheme_call_cmd"; attribute :>> limit="snapshot before SFUN entry; source borrowing gap"; }
part source9:SourceRow { attribute :>> key="steal"; attribute :>> path="vendor/gambit/lib/_thread.scm"; attribute :>> needle="(macro-thread-pinned stolen-thread)"; attribute :>> limit="existing migration restriction; no C stack migration"; }
part source10:SourceRow { attribute :>> key="atomic"; attribute :>> path="vendor/gambit/include/_gambit/activity_log.h.in"; attribute :>> needle="#define ___WORD_CAS_ACQUIRE"; attribute :>> limit="generic public pointer API does not close managed writers"; }
part source11:SourceRow { attribute :>> key="hooks"; attribute :>> path="vendor/gambit/include/_gambit/module_generation.h.in"; attribute :>> needle="#define ___TASK_PUSH(i)"; attribute :>> limit="task hooks empty; no implemented NativeScope"; }
part source12:SourceRow { attribute :>> key="extent-paper"; attribute :>> path="evidence/research/source-references/feeley-sfp/8bb2fae8ae4b54d3a86206596f90e9cf73da39846af0f39244a476074cf81ed4.txt"; attribute :>> needle="5       Pra"; attribute :>> limit="paper proposes native segment lifetime; not C23 scope protocol"; }
part source13:SourceRow { attribute :>> key="parent-owner"; attribute :>> path="dev/refactoring/modern-c/models/lean/AtomicOwnerAst.lean"; attribute :>> needle="def activateA0Guard"; attribute :>> limit="private owner view and generation; not native issuance proof"; }
part def RouteRow { attribute actionName:String; attribute lemma:String; attribute source:String; attribute contract:String; }
part route0:RouteRow { attribute :>> actionName="issue"; attribute :>> lemma="NativeScope.issuePreserves"; attribute :>> source="sfun"; attribute :>> contract="writer-custody"; }
part route1:RouteRow { attribute :>> actionName="beginWrite"; attribute :>> lemma="NativeScope.beginWritePreserves"; attribute :>> source="sfun"; attribute :>> contract="writer-custody"; }
part route2:RouteRow { attribute :>> actionName="publishRelease"; attribute :>> lemma="NativeScope.publishReleasePreserves"; attribute :>> source="atomic"; attribute :>> contract="writer-custody"; }
part route3:RouteRow { attribute :>> actionName="recordOutcome"; attribute :>> lemma="NativeScope.recordOutcomePreserves"; attribute :>> source="sfun"; attribute :>> contract="writer-custody"; }
part route4:RouteRow { attribute :>> actionName="deliverOutcome"; attribute :>> lemma="NativeScope.deliverOutcomePreserves"; attribute :>> source="sfun"; attribute :>> contract="writer-custody"; }
part route5:RouteRow { attribute :>> actionName="loseResponse"; attribute :>> lemma="NativeScope.loseResponsePreserves"; attribute :>> source="catcher"; attribute :>> contract="writer-custody"; }
part route6:RouteRow { attribute :>> actionName="recoverRecorded"; attribute :>> lemma="NativeScope.recoverRecordedPreserves"; attribute :>> source="catcher"; attribute :>> contract="writer-custody"; }
part route7:RouteRow { attribute :>> actionName="enterNested"; attribute :>> lemma="NativeScope.enterNestedPreserves"; attribute :>> source="sfun"; attribute :>> contract="writer-custody"; }
part route8:RouteRow { attribute :>> actionName="leaveNested"; attribute :>> lemma="NativeScope.leaveNestedPreserves"; attribute :>> source="sfun"; attribute :>> contract="writer-custody"; }
part route9:RouteRow { attribute :>> actionName="catcherSubtree"; attribute :>> lemma="NativeScope.catcherSubtreePreserves"; attribute :>> source="catcher"; attribute :>> contract="writer-custody"; }
part route10:RouteRow { attribute :>> actionName="acquire0"; attribute :>> lemma="NativeScope.acquire0Preserves"; attribute :>> source="atomic"; attribute :>> contract="rf-witness"; }
part route11:RouteRow { attribute :>> actionName="acquire1"; attribute :>> lemma="NativeScope.acquire1Preserves"; attribute :>> source="atomic"; attribute :>> contract="rf-witness"; }
part route12:RouteRow { attribute :>> actionName="closeAdmission"; attribute :>> lemma="NativeScope.closeAdmissionPreserves"; attribute :>> source="sfun"; attribute :>> contract="writer-custody"; }
part route13:RouteRow { attribute :>> actionName="renewSameThread"; attribute :>> lemma="NativeScope.renewSameThreadPreserves"; attribute :>> source="sfun"; attribute :>> contract="writer-custody"; }
part route14:RouteRow { attribute :>> actionName="prepareMigration"; attribute :>> lemma="NativeScope.prepareMigrationPreserves"; attribute :>> source="thread"; attribute :>> contract="writer-custody"; }
part route15:RouteRow { attribute :>> actionName="targetAcquire"; attribute :>> lemma="NativeScope.targetAcquirePreserves"; attribute :>> source="thread"; attribute :>> contract="writer-custody"; }
part route16:RouteRow { attribute :>> actionName="issueTarget"; attribute :>> lemma="NativeScope.issueTargetPreserves"; attribute :>> source="thread"; attribute :>> contract="writer-custody"; }
part route17:RouteRow { attribute :>> actionName="rejectStaleDelivery"; attribute :>> lemma="NativeScope.rejectStaleDeliveryPreserves"; attribute :>> source="sfun"; attribute :>> contract="writer-custody"; }
part route18:RouteRow { attribute :>> actionName="rawInterference"; attribute :>> lemma="NativeScope.rawInterferencePreserves"; attribute :>> source="tcl"; attribute :>> contract="writer-custody"; }
part route19:RouteRow { attribute :>> actionName="retire"; attribute :>> lemma="NativeScope.retirePreserves"; attribute :>> source="sfun"; attribute :>> contract="writer-custody"; }
part def IssuerRow { attribute key:String; attribute source:String; attribute existing:String; attribute proposed:String; attribute gap:String; }
part issuer0:IssuerRow { attribute :>> key="entry"; attribute :>> source="run"; attribute :>> existing="GC phase rejection before local writes"; attribute :>> proposed="entry adapter plus VM stable registry before mutation"; attribute :>> gap="preallocated slot/root producer not implemented"; }
part issuer1:IssuerRow { attribute :>> key="sfun"; attribute :>> source="sfun"; attribute :>> existing="borrowed closure root and registered RC bank"; attribute :>> proposed="joint source owner plus VM domain admission"; attribute :>> gap="Tcl pre-dispatch lifetime not covered by bank"; }
part issuer2:IssuerRow { attribute :>> key="nested"; attribute :>> source="catcher"; attribute :>> existing="local catcher chaining and restoration"; attribute :>> proposed="parent-linked scope per callback entry"; attribute :>> gap="outer landing subtree settlement not implemented"; }
part issuer3:IssuerRow { attribute :>> key="migration"; attribute :>> source="thread"; attribute :>> existing="PSTATE binding and pinned-thread skip"; attribute :>> proposed="scheduler closes source activation; target admits fresh scope"; attribute :>> gap="never move live C return extent; handoff RF adapter missing"; }
part issuer4:IssuerRow { attribute :>> key="unknown"; attribute :>> source="sfun-exit"; attribute :>> existing="end_sfun normal cleanup"; attribute :>> proposed="stable completion recipient with immutable operation identity"; attribute :>> gap="no response is not proof of failed operation"; }
part def WriterRow { attribute key:String; attribute source:String; attribute storage:String; attribute rule:String; attribute status:String; }
part writer0:WriterRow { attribute :>> key="generated-entry"; attribute :>> source="sfun"; attribute :>> storage="roots and PSTATE"; attribute :>> rule="register before mutation; no collecting gap"; attribute :>> status="bounded source fact; future adapter missing"; }
part writer1:WriterRow { attribute :>> key="generated-error-retry"; attribute :>> source="sfun-exit"; attribute :>> storage="marker and root bank"; attribute :>> rule="new call identity per actual call; delivery retains identity"; attribute :>> status="whole generated caller closure unresolved"; }
part writer2:WriterRow { attribute :>> key="collector"; attribute :>> source="rc-root"; attribute :>> storage="relocatable root slots"; attribute :>> rule="closed RC domain scan updates canonical slots; no task control reset"; attribute :>> status="existing gated scan; registry integration unresolved"; }
part writer3:WriterRow { attribute :>> key="payload-setter"; attribute :>> source="rc-write"; attribute :>> storage="RC payload"; attribute :>> rule="source lease and same domain; freeze excludes setter"; attribute :>> status="existing domain guard; external alias census unresolved"; }
part writer4:WriterRow { attribute :>> key="tcl-delete"; attribute :>> source="tcl"; attribute :>> storage="ClientData RC lifetime"; attribute :>> rule="close callback admission and drain before release"; attribute :>> status="Tcl example lacks new joint scope admission"; }
part writer5:WriterRow { attribute :>> key="thread-binding"; attribute :>> source="thread"; attribute :>> storage="PSTATE TLS"; attribute :>> rule="fresh target admission; do not copy source capability"; attribute :>> status="existing setter not authority issuer"; }
part writer6:WriterRow { attribute :>> key="task-control"; attribute :>> source="hooks"; attribute :>> storage="new managed control word"; attribute :>> rule="private opaque AtomicRef; only named transitions and init before publication"; attribute :>> status="not implemented; old empty hooks retire only after qualification"; }
part writer7:WriterRow { attribute :>> key="generic-atomic-ffi"; attribute :>> source="atomic"; attribute :>> storage="raw pointer supplied by caller"; attribute :>> rule="no alias to managed word; reject unmediated native escape"; attribute :>> status="cannot prove all foreign binaries closed"; }
part writer8:WriterRow { attribute :>> key="retire-reinit"; attribute :>> source="parent-owner"; attribute :>> storage="storage generation and receipt"; attribute :>> rule="drain writers/readers and GC before reuse; pin generation"; attribute :>> status="full object reuse refinement unresolved"; }
part def ObligationRow { attribute key:String; attribute status:String; attribute condition:String; }
part obligation0:ObligationRow { attribute :>> key="writer-custody"; attribute :>> status="conditional-model"; attribute :>> condition="complete action roster; stable roots and issuer premise"; }
part obligation1:ObligationRow { attribute :>> key="rf-witness"; attribute :>> status="conditional-model"; attribute :>> condition="actual acquire reads from matching release or its qualified sequence"; }
part obligation2:ObligationRow { attribute :>> key="native-issuer"; attribute :>> status="unresolved"; attribute :>> condition="generated entry plus VM registry identity and live thread/extent"; }
part obligation3:ObligationRow { attribute :>> key="writer-closure"; attribute :>> status="unresolved"; attribute :>> condition="all generated C callouts and external aliases admitted or rejected"; }
part obligation4:ObligationRow { attribute :>> key="native-rf"; attribute :>> status="unresolved"; attribute :>> condition="C23 event graph refinement; ghost event not runtime observation"; }
part obligation5:ObligationRow { attribute :>> key="landing"; attribute :>> status="unresolved"; attribute :>> condition="stable catcher landing reconciles all nested guards"; }
part obligation6:ObligationRow { attribute :>> key="gc-grace"; attribute :>> status="unresolved"; attribute :>> condition="registered slots updated each round; descriptors live until grace"; }
part obligation7:ObligationRow { attribute :>> key="product"; attribute :>> status="unresolved"; attribute :>> condition="NativeScope and AtomicOwner step synchronization; interface bridge alone insufficient"; }
part def GainRow { attribute key:String; attribute benefit:String; attribute overhead:String; attribute condition:String; attribute refutation:String; }
part gain0:GainRow { attribute :>> key="same-thread"; attribute :>> benefit="one retained coherence floor per thread and atomic object; no reset on nested callback"; attribute :>> overhead="scope identity plus parent link per callback"; attribute :>> condition="all same-thread roles join the floor"; attribute :>> refutation="independent per-role floors forget prior acquire"; }
part gain1:GainRow { attribute :>> key="migration"; attribute :>> benefit="Scheme work can move; immutable result payload need not be copied again"; attribute :>> overhead="one source release publication plus one target acquire minimum"; attribute :>> condition="source roots retained until target acceptance"; attribute :>> refutation="moving return permission or source view alone is unsound"; }
part gain2:GainRow { attribute :>> key="unknown"; attribute :>> benefit="zero blind operation replays after lost response"; attribute :>> overhead="one stable pending record per outstanding operation; retention can be unbounded"; attribute :>> condition="recover using same operation identity"; attribute :>> refutation="no recovery witness means retained resources, not claimed progress"; }
part gain3:GainRow { attribute :>> key="writer-module"; attribute :>> benefit="one private control-word API replaces duplicate ad-hoc wrappers for that word"; attribute :>> overhead="closed writer roster and generated entry adapter"; attribute :>> condition="no raw pointer escape to unqualified writers"; attribute :>> refutation="public raw aliases prevent closed-world admission"; }
part gain4:GainRow { attribute :>> key="runtime-speed"; attribute :>> benefit="no measured speedup claimed; control-state CAS bound remains prior conditional bound"; attribute :>> overhead="scope admission and root registration are additional costs"; attribute :>> condition="saved retry/rebuild work exceeds added admission cost"; attribute :>> refutation="frequent nested FFI may cost more than work saved"; }
part gain5:GainRow { attribute :>> key="zig"; attribute :>> benefit="C23 expresses the same ownership and publication contracts"; attribute :>> overhead="second backend qualification if Zig introduced"; attribute :>> condition="incremental benefit beyond mandatory modern C must be separately proved"; attribute :>> refutation="language choice does not remove root or native extent proof"; }
part def EdgeRow { attribute fromNode:String; attribute toNode:String; attribute contract:String; }
part edge0:EdgeRow { attribute :>> fromNode="source_root"; attribute :>> toNode="stable_registry"; attribute :>> contract="pin roots before allocating marker"; }
part edge1:EdgeRow { attribute :>> fromNode="stable_registry"; attribute :>> toNode="outer_scope"; attribute :>> contract="entry admission plus live native extent"; }
part edge2:EdgeRow { attribute :>> fromNode="outer_scope"; attribute :>> toNode="nested_scope"; attribute :>> contract="new callback identity; same physical thread history"; }
part edge3:EdgeRow { attribute :>> fromNode="nested_scope"; attribute :>> toNode="catcher_landing"; attribute :>> contract="subtree settlement retains unknown operations"; }
part edge4:EdgeRow { attribute :>> fromNode="outer_scope"; attribute :>> toNode="atomic_event"; attribute :>> contract="opaque storage generation; closed writer API"; }
part edge5:EdgeRow { attribute :>> fromNode="atomic_event"; attribute :>> toNode="acquire_view"; attribute :>> contract="RF release witness is a proof ghost"; }
part edge6:EdgeRow { attribute :>> fromNode="outer_scope"; attribute :>> toNode="handoff"; attribute :>> contract="close old activation; retain root custody"; }
part edge7:EdgeRow { attribute :>> fromNode="handoff"; attribute :>> toNode="target_scope"; attribute :>> contract="target acquire and fresh identity; no C return transfer"; }
part edge8:EdgeRow { attribute :>> fromNode="catcher_landing"; attribute :>> toNode="recovery"; attribute :>> contract="same operation identity; no blind replay"; }
part edge9:EdgeRow { attribute :>> fromNode="recovery"; attribute :>> toNode="gc_grace"; attribute :>> contract="only resolved operations may release last pin"; }
part edge10:EdgeRow { attribute :>> fromNode="gc_grace"; attribute :>> toNode="retire"; attribute :>> contract="no writers or readers; descriptor retirement separate"; }
}
