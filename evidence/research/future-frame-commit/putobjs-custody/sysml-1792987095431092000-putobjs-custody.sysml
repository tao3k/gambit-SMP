package GambitPutObjsCustody { private import ScalarValues::*;
part def SourceRow { attribute key:String; attribute path:String; attribute needle:String; attribute limit:String; }
part source0:SourceRow { attribute :>> key="trim"; attribute :>> path="evidence/research/source-references/tcl/cbf86d62348d6b052e1961b4df995960fb21545f/generic/tclThreadAlloc.c"; attribute :>> needle="fromPtr->numObjects = keep;"; attribute :>> limit="counter changes before the local chain is cut"; }
part source1:SourceRow { attribute :>> key="head-load"; attribute :>> path="evidence/research/source-references/tcl/cbf86d62348d6b052e1961b4df995960fb21545f/generic/tclThreadAlloc.c"; attribute :>> needle="firstPtr = fromPtr->firstObjPtr;"; attribute :>> limit="owner-protected local head snapshot"; }
part source2:SourceRow { attribute :>> key="walk-last"; attribute :>> path="evidence/research/source-references/tcl/cbf86d62348d6b052e1961b4df995960fb21545f/generic/tclThreadAlloc.c"; attribute :>> needle="lastPtr = firstPtr;"; attribute :>> limit="loop last pointer assignment precedes next-link read"; }
part source3:SourceRow { attribute :>> key="walk-next"; attribute :>> path="evidence/research/source-references/tcl/cbf86d62348d6b052e1961b4df995960fb21545f/generic/tclThreadAlloc.c"; attribute :>> needle="firstPtr = firstPtr->internalRep.twoPtrValue.ptr1;"; attribute :>> limit="one physical link read per loop"; }
part source4:SourceRow { attribute :>> key="walk-condition"; attribute :>> path="evidence/research/source-references/tcl/cbf86d62348d6b052e1961b4df995960fb21545f/generic/tclThreadAlloc.c"; attribute :>> needle="} while (--keep > 0);"; attribute :>> limit="401 iterations for selected 1201/800 transfer"; }
part source5:SourceRow { attribute :>> key="split"; attribute :>> path="evidence/research/source-references/tcl/cbf86d62348d6b052e1961b4df995960fb21545f/generic/tclThreadAlloc.c"; attribute :>> needle="lastPtr->internalRep.twoPtrValue.ptr1 = NULL;"; attribute :>> limit="local retained prefix detached from batch"; }
part source6:SourceRow { attribute :>> key="lock"; attribute :>> path="evidence/research/source-references/tcl/cbf86d62348d6b052e1961b4df995960fb21545f/generic/tclThreadAlloc.c"; attribute :>> needle="Tcl_MutexLock(objLockPtr);"; attribute :>> limit="lock result must be known; not a recovery receipt"; }
part source7:SourceRow { attribute :>> key="suffix-link"; attribute :>> path="evidence/research/source-references/tcl/cbf86d62348d6b052e1961b4df995960fb21545f/generic/tclThreadAlloc.c"; attribute :>> needle="fromPtr->lastPtr->internalRep.twoPtrValue.ptr1 = sharedPtr->firstObjPtr;"; attribute :>> limit="uses old local tail while shared lock held"; }
part source8:SourceRow { attribute :>> key="shared-head"; attribute :>> path="evidence/research/source-references/tcl/cbf86d62348d6b052e1961b4df995960fb21545f/generic/tclThreadAlloc.c"; attribute :>> needle="sharedPtr->firstObjPtr = firstPtr;"; attribute :>> limit="shared reachability precedes shared count"; }
part source9:SourceRow { attribute :>> key="tail-condition"; attribute :>> path="evidence/research/source-references/tcl/cbf86d62348d6b052e1961b4df995960fb21545f/generic/tclThreadAlloc.c"; attribute :>> needle="if (sharedPtr->numObjects == 0) {"; attribute :>> limit="branch observes shared count while locked"; }
part source10:SourceRow { attribute :>> key="shared-tail"; attribute :>> path="evidence/research/source-references/tcl/cbf86d62348d6b052e1961b4df995960fb21545f/generic/tclThreadAlloc.c"; attribute :>> needle="sharedPtr->lastPtr = fromPtr->lastPtr;"; attribute :>> limit="only empty shared list replaces tail"; }
part source11:SourceRow { attribute :>> key="shared-count"; attribute :>> path="evidence/research/source-references/tcl/cbf86d62348d6b052e1961b4df995960fb21545f/generic/tclThreadAlloc.c"; attribute :>> needle="sharedPtr->numObjects += numMove;"; attribute :>> limit="shared count increment after splice"; }
part source12:SourceRow { attribute :>> key="unlock"; attribute :>> path="evidence/research/source-references/tcl/cbf86d62348d6b052e1961b4df995960fb21545f/generic/tclThreadAlloc.c"; attribute :>> needle="Tcl_MutexUnlock(objLockPtr);"; attribute :>> limit="normal unlock return precedes local tail update"; }
part source13:SourceRow { attribute :>> key="local-last"; attribute :>> path="evidence/research/source-references/tcl/cbf86d62348d6b052e1961b4df995960fb21545f/generic/tclThreadAlloc.c"; attribute :>> needle="fromPtr->lastPtr = lastPtr;"; attribute :>> limit="final PutObjs cache store; not whole TCLNR_FREE receipt"; }
part source14:SourceRow { attribute :>> key="cache-free"; attribute :>> path="evidence/research/source-references/tcl/cbf86d62348d6b052e1961b4df995960fb21545f/generic/tclThreadAlloc.c"; attribute :>> needle="TclpSysFree(cachePtr);"; attribute :>> limit="cache address can be reused only after full teardown qualification"; }
part source15:SourceRow { attribute :>> key="thread-finalize"; attribute :>> path="evidence/research/source-references/tcl/cbf86d62348d6b052e1961b4df995960fb21545f/generic/tclThreadAlloc.c"; attribute :>> needle="TclpFreeAllocCache(cachePtr);"; attribute :>> limit="thread finalization delegates platform TLS/free adapter"; }
part source16:SourceRow { attribute :>> key="high-helper"; attribute :>> path="evidence/research/source-references/tcl/cbf86d62348d6b052e1961b4df995960fb21545f/generic/tclThreadAlloc.c"; attribute :>> needle="PutObjs(cachePtr, NOBJALLOC);"; attribute :>> limit="selected n=1200 route"; }
part source17:SourceRow { attribute :>> key="free-all"; attribute :>> path="evidence/research/source-references/tcl/cbf86d62348d6b052e1961b4df995960fb21545f/generic/tclThreadAlloc.c"; attribute :>> needle="PutObjs(cachePtr, cachePtr->numObjects);"; attribute :>> limit="different keep=0 cleanup caller; excluded from selected ordinal model"; }
part source18:SourceRow { attribute :>> key="global-finalize"; attribute :>> path="evidence/research/source-references/tcl/cbf86d62348d6b052e1961b4df995960fb21545f/generic/tclThreadAlloc.c"; attribute :>> needle="TclpFreeAllocMutex(objLockPtr);"; attribute :>> limit="shared lock itself has finalization lifetime"; }
part source19:SourceRow { attribute :>> key="prior"; attribute :>> path="dev/refactoring/modern-c/models/quint/thread_cache_tail.qnt"; attribute :>> needle="action helperFlush800="; attribute :>> limit="actual coarse parent effect; helperKnownReturn remains independent"; }
part def ObligationRow { attribute key:String; attribute status:String; attribute condition:String; }
part obligation0:ObligationRow { attribute :>> key="scalar-safety"; attribute :>> status="conditional-model"; attribute :>> condition="valid 1201-node chain, same native owner, protected shared cache and stable independent record"; }
part obligation1:ObligationRow { attribute :>> key="source-order"; attribute :>> status="source-bound"; attribute :>> condition="401-link walk, split, locked splice/count, unlock then local lastPtr"; }
part obligation2:ObligationRow { attribute :>> key="pointer-refinement"; attribute :>> status="unresolved"; attribute :>> condition="ordinal-to-address chain, no cycles/aliases, all cache consumers and actual interruption cuts"; }
part obligation3:ObligationRow { attribute :>> key="unknown-lock"; attribute :>> status="unresolved"; attribute :>> condition="unknown lock/unlock owner must retain batch/cache and cannot be unlocked by arbitrary worker"; }
part obligation4:ObligationRow { attribute :>> key="cache-retirement"; attribute :>> status="unresolved"; attribute :>> condition="close all native/TLS/interp borrowers, finish bucket/keep=0 cleanup, drain pins and forbid generation wrap"; }
part obligation5:ObligationRow { attribute :>> key="c23-publication"; attribute :>> status="unresolved"; attribute :>> condition="actual Tcl mutex provider semantics and complete non-abandon receipt tail; C23 source mapping"; }
part obligation6:ObligationRow { attribute :>> key="composition"; attribute :>> status="unresolved"; attribute :>> condition="observation exclusion for coarse parent join; full trace/product and outer free/statistics completion not supplied"; }
part def RouteRow { attribute actionName:String; attribute lemma:String; attribute source:String; attribute obligation:String; }
part route0:RouteRow { attribute :>> actionName="admitOwner"; attribute :>> lemma="PutObjsCustody.admitOwnerPreserves"; attribute :>> source="prior"; attribute :>> obligation="scalar-safety"; }
part route1:RouteRow { attribute :>> actionName="chooseEmpty"; attribute :>> lemma="PutObjsCustody.chooseEmptyPreserves"; attribute :>> source="tail-condition"; attribute :>> obligation="scalar-safety"; }
part route2:RouteRow { attribute :>> actionName="chooseNonempty"; attribute :>> lemma="PutObjsCustody.chooseNonemptyPreserves"; attribute :>> source="tail-condition"; attribute :>> obligation="scalar-safety"; }
part route3:RouteRow { attribute :>> actionName="trimLocal"; attribute :>> lemma="PutObjsCustody.trimLocalPreserves"; attribute :>> source="trim"; attribute :>> obligation="scalar-safety"; }
part route4:RouteRow { attribute :>> actionName="loadLocalHead"; attribute :>> lemma="PutObjsCustody.loadLocalHeadPreserves"; attribute :>> source="head-load"; attribute :>> obligation="scalar-safety"; }
part route5:RouteRow { attribute :>> actionName="assignLast"; attribute :>> lemma="PutObjsCustody.assignLastPreserves"; attribute :>> source="walk-last"; attribute :>> obligation="scalar-safety"; }
part route6:RouteRow { attribute :>> actionName="advanceCursor"; attribute :>> lemma="PutObjsCustody.advanceCursorPreserves"; attribute :>> source="walk-next"; attribute :>> obligation="scalar-safety"; }
part route7:RouteRow { attribute :>> actionName="loopAgain"; attribute :>> lemma="PutObjsCustody.loopAgainPreserves"; attribute :>> source="walk-condition"; attribute :>> obligation="scalar-safety"; }
part route8:RouteRow { attribute :>> actionName="cutLocal"; attribute :>> lemma="PutObjsCustody.cutLocalPreserves"; attribute :>> source="split"; attribute :>> obligation="scalar-safety"; }
part route9:RouteRow { attribute :>> actionName="lockKnown"; attribute :>> lemma="PutObjsCustody.lockKnownPreserves"; attribute :>> source="lock"; attribute :>> obligation="scalar-safety"; }
part route10:RouteRow { attribute :>> actionName="lockUnknown"; attribute :>> lemma="PutObjsCustody.lockUnknownPreserves"; attribute :>> source="lock"; attribute :>> obligation="scalar-safety"; }
part route11:RouteRow { attribute :>> actionName="linkOldTail"; attribute :>> lemma="PutObjsCustody.linkOldTailPreserves"; attribute :>> source="suffix-link"; attribute :>> obligation="scalar-safety"; }
part route12:RouteRow { attribute :>> actionName="publishSharedHead"; attribute :>> lemma="PutObjsCustody.publishSharedHeadPreserves"; attribute :>> source="shared-head"; attribute :>> obligation="scalar-safety"; }
part route13:RouteRow { attribute :>> actionName="updateEmptySharedTail"; attribute :>> lemma="PutObjsCustody.updateEmptySharedTailPreserves"; attribute :>> source="shared-tail"; attribute :>> obligation="scalar-safety"; }
part route14:RouteRow { attribute :>> actionName="keepSharedTail"; attribute :>> lemma="PutObjsCustody.keepSharedTailPreserves"; attribute :>> source="tail-condition"; attribute :>> obligation="scalar-safety"; }
part route15:RouteRow { attribute :>> actionName="addSharedCount"; attribute :>> lemma="PutObjsCustody.addSharedCountPreserves"; attribute :>> source="shared-count"; attribute :>> obligation="scalar-safety"; }
part route16:RouteRow { attribute :>> actionName="unlockKnown"; attribute :>> lemma="PutObjsCustody.unlockKnownPreserves"; attribute :>> source="unlock"; attribute :>> obligation="scalar-safety"; }
part route17:RouteRow { attribute :>> actionName="unlockUnknown"; attribute :>> lemma="PutObjsCustody.unlockUnknownPreserves"; attribute :>> source="unlock"; attribute :>> obligation="scalar-safety"; }
part route18:RouteRow { attribute :>> actionName="fixLocalLast"; attribute :>> lemma="PutObjsCustody.fixLocalLastPreserves"; attribute :>> source="localCount-last"; attribute :>> obligation="scalar-safety"; }
part route19:RouteRow { attribute :>> actionName="publishReceipt"; attribute :>> lemma="PutObjsCustody.publishReceiptPreserves"; attribute :>> source="localCount-last"; attribute :>> obligation="scalar-safety"; }
part route20:RouteRow { attribute :>> actionName="escape"; attribute :>> lemma="PutObjsCustody.escapePreserves"; attribute :>> source="prior"; attribute :>> obligation="scalar-safety"; }
part route21:RouteRow { attribute :>> actionName="loseReceiptAck"; attribute :>> lemma="PutObjsCustody.loseReceiptAckPreserves"; attribute :>> source="prior"; attribute :>> obligation="scalar-safety"; }
part route22:RouteRow { attribute :>> actionName="acceptReceipt"; attribute :>> lemma="PutObjsCustody.acceptReceiptPreserves"; attribute :>> source="prior"; attribute :>> obligation="scalar-safety"; }
part route23:RouteRow { attribute :>> actionName="closeAdmission"; attribute :>> lemma="PutObjsCustody.closeAdmissionPreserves"; attribute :>> source="cache-free"; attribute :>> obligation="scalar-safety"; }
part route24:RouteRow { attribute :>> actionName="readersDetached"; attribute :>> lemma="PutObjsCustody.readersDetachedPreserves"; attribute :>> source="cache-free"; attribute :>> obligation="scalar-safety"; }
part route25:RouteRow { attribute :>> actionName="attestFinalization"; attribute :>> lemma="PutObjsCustody.attestFinalizationPreserves"; attribute :>> source="thread-finalize"; attribute :>> obligation="scalar-safety"; }
part route26:RouteRow { attribute :>> actionName="reuseAddress"; attribute :>> lemma="PutObjsCustody.reuseAddressPreserves"; attribute :>> source="cache-free"; attribute :>> obligation="scalar-safety"; }
part def GainRow { attribute key:String; attribute saved:String; attribute added:String; attribute condition:String; attribute status:String; }
part gain0:GainRow { attribute :>> key="walk"; attribute :>> saved="reuse original prefix walk; exactly 401 next-link reads in selected source case"; attribute :>> added="no reduction of those 401 reads or O(keep) complexity"; attribute :>> condition="valid source chain and count1201 transfer800"; attribute :>> status="source-bound"; }
part gain1:GainRow { attribute :>> key="receipt"; attribute :>> saved="exact PutObjs receipt can avoid replay or generic reconciliation on qualified known normal path"; attribute :>> added="at least one independent logical publication plus owner/incarnation record"; attribute :>> condition="lastPtr updated, lock known released and full publication tail qualified"; attribute :>> status="conditional"; }
part gain2:GainRow { attribute :>> key="unknown"; attribute :>> saved="prevents duplicate batch splice, wrong-thread unlock and premature cache free"; attribute :>> added="unknown cache/batch/lock custody may block shared allocator indefinitely"; attribute :>> condition="stable record exists before first irreversible count write"; attribute :>> status="conditional-model"; }
part gain3:GainRow { attribute :>> key="address"; attribute :>> saved="reject old receipt after same address obtains a new incarnation"; attribute :>> added="gate/readers and stable generation identity; cleanup evidence independent of address"; attribute :>> condition="bounded witness models1->2 only; global ABA/wrap proof still required"; attribute :>> status="conditional-model"; }
part gain4:GainRow { attribute :>> key="retirement"; attribute :>> saved="potentially retire only coarse high-water unknown-handling branch after full qualification"; attribute :>> added="all bucket, TLS, interp and keep=0 caller closure remains; old retired now0"; attribute :>> condition="native refinement and full caller proof; no timing ratio or Zig-specific gain"; attribute :>> status="unresolved"; }
part def IssuerRow { attribute key:String; attribute source:String; attribute signature:String; attribute gap:String; }
part issuer0:IssuerRow { attribute :>> key="source-owner"; attribute :>> source="trim"; attribute :>> signature="same thread cache and valid split representation before count mutation"; attribute :>> gap="current code has no persistent operation/cursor record"; }
part issuer1:IssuerRow { attribute :>> key="shared-owner"; attribute :>> source="shared-count"; attribute :>> signature="matching native lock acquisition, shared splice/tail/count stores and known unlock"; attribute :>> gap="mutex provider, abandonment and integer overflow bounds unqualified"; }
part issuer2:IssuerRow { attribute :>> key="putobjs-owner"; attribute :>> source="local-last"; attribute :>> signature="known local lastPtr store and protected independent PutObjs completion publication"; attribute :>> gap="unlock alone is insufficient; whole TclSmallFreeEx effects remain separate"; }
part issuer3:IssuerRow { attribute :>> key="supervisor"; attribute :>> source="prior"; attribute :>> signature="retains original operation, phase, batch, local cursor and uncertain lock duty after abandonment"; attribute :>> gap="metadata survival is not arbitrary same-operation recovery or C-stack resurrection"; }
part issuer4:IssuerRow { attribute :>> key="retire-owner"; attribute :>> source="cache-free"; attribute :>> signature="generation-bound closed admission, native borrowers detached, all finalization effects known"; attribute :>> gap="Tcl cache has no installed incarnation field or global detachment receipt"; }
part def ConsumerRow { attribute key:String; attribute source:String; attribute access:String; attribute lifetime:String; attribute limit:String; }
part consumer0:ConsumerRow { attribute :>> key="local-cursor"; attribute :>> source="walk-next"; attribute :>> access="load next link after assigning last ordinal"; attribute :>> lifetime="whole original thread cache and chain"; attribute :>> limit="ordinal equation is not a native alias/GC pointer proof"; }
part consumer1:ConsumerRow { attribute :>> key="batch"; attribute :>> source="suffix-link"; attribute :>> access="old tail connects batch to previous shared head"; attribute :>> lifetime="exclusive local source plus shared lock"; attribute :>> limit="partial splice/count states cannot be replayed as absent"; }
part consumer2:ConsumerRow { attribute :>> key="shared-reader"; attribute :>> source="shared-head"; attribute :>> access="may observe new batch only after matching shared mutex synchronization"; attribute :>> lifetime="shared cache and objLockPtr"; attribute :>> limit="native out-of-lock readers or escapes invalidate observation hiding"; }
part consumer3:ConsumerRow { attribute :>> key="local-tail"; attribute :>> source="local-last"; attribute :>> access="lastPtr remains old through unlock; then becomes retained-prefix end"; attribute :>> lifetime="original owner excludes cache reentry through final store"; attribute :>> limit="shared visibility is earlier than PutObjs completion"; }
part consumer4:ConsumerRow { attribute :>> key="late-receipt"; attribute :>> source="cache-free"; attribute :>> access="resolve full owner/storage generation and operation identity before reuse"; attribute :>> lifetime="stable receipt record; cache lease separate"; attribute :>> limit="same raw address is not same storage incarnation"; }
part consumer5:ConsumerRow { attribute :>> key="cache-finalizer"; attribute :>> source="free-all"; attribute :>> access="bucket flush plus PutObjs all objects, list unlink, native free and TLS cleanup"; attribute :>> lifetime="all native borrowers and allocator locks"; attribute :>> limit="keep=0 and all platform TLS writers remain outside selected high-water model"; }
part def EdgeRow { attribute fromNode:String; attribute toNode:String; attribute contract:String; }
part edge0:EdgeRow { attribute :>> fromNode="Post-push 1201"; attribute :>> toNode="Local count401"; attribute :>> contract="stable owner record exists; reserve800 uncredited responsibility"; }
part edge1:EdgeRow { attribute :>> fromNode="Local count401"; attribute :>> toNode="Walk 401 links"; attribute :>> contract="load head; assign last then read next; preserve phase and cursor"; }
part edge2:EdgeRow { attribute :>> fromNode="Walk 401 links"; attribute :>> toNode="Cut local prefix"; attribute :>> contract="only walk==401; retained401 and batch800"; }
part edge3:EdgeRow { attribute :>> fromNode="Cut local prefix"; attribute :>> toNode="Shared mutex known"; attribute :>> contract="unknown acquisition retains lock/cache custody"; }
part edge4:EdgeRow { attribute :>> fromNode="Shared mutex known"; attribute :>> toNode="Batch head visible"; attribute :>> contract="old tail link then shared head; count still old"; }
part edge5:EdgeRow { attribute :>> fromNode="Batch head visible"; attribute :>> toNode="Shared count800 credited"; attribute :>> contract="empty-list tail branch then count increment"; }
part edge6:EdgeRow { attribute :>> fromNode="Shared count800 credited"; attribute :>> toNode="Mutex released"; attribute :>> contract="unknown release retains duty; never guess unlocked"; }
part edge7:EdgeRow { attribute :>> fromNode="Mutex released"; attribute :>> toNode="Local lastPtr fixed"; attribute :>> contract="same native owner; reentry still excluded"; }
part edge8:EdgeRow { attribute :>> fromNode="Local lastPtr fixed"; attribute :>> toNode="PutObjs receipt"; attribute :>> contract="independent protected release publication; not entire free receipt"; }
part edge9:EdgeRow { attribute :>> fromNode="Any uncertain cut"; attribute :>> toNode="Stable supervisor"; attribute :>> contract="no replay; preserve phase/cursor/batch/lock/source lease"; }
part edge10:EdgeRow { attribute :>> fromNode="PutObjs receipt"; attribute :>> toNode="Closed cache admission"; attribute :>> contract="drain readers and qualify all finalization callers"; }
part edge11:EdgeRow { attribute :>> fromNode="Closed cache admission"; attribute :>> toNode="New generation"; attribute :>> contract="cache address may be reused; old opaque receipt stays stale"; }
}
