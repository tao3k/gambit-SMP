package GambitNativeEntryAdmission { private import ScalarValues::*;
part def SourceRow { attribute key:String; attribute path:String; attribute needle:String; attribute limit:String; }
part source0:SourceRow { attribute :>> key="call"; attribute :>> path="vendor/gambit/lib/setup.c"; attribute :>> needle="___EXP_FUNC(___SCMOBJ,___call)"; attribute :>> limit="candidate issuer before argument loads; current phase check is not a scope"; }
part source1:SourceRow { attribute :>> key="run"; attribute :>> path="vendor/gambit/lib/setup.c"; attribute :>> needle="___EXP_FUNC(___SCMOBJ,___run)"; attribute :>> limit="entry-local writes precede call; must admit before them"; }
part source2:SourceRow { attribute :>> key="sfun"; attribute :>> path="vendor/gambit/lib/c_intf.c"; attribute :>> needle="___EXP_FUNC(___SCMOBJ,___begin_sfun)"; attribute :>> limit="existing source borrow and bank are context-bound"; }
part source3:SourceRow { attribute :>> key="catcher"; attribute :>> path="vendor/gambit/include/_gambit/foreign_conversion.h.in"; attribute :>> needle="#define ___BEGIN_TRY"; attribute :>> limit="live jmpbuf extent; stable landing issuer still proposed"; }
part source4:SourceRow { attribute :>> key="sfun-exit"; attribute :>> path="vendor/gambit/include/_gambit/foreign_conversion.h.in"; attribute :>> needle="#define ___END_SFUN "; attribute :>> limit="candidate completion adapter; not exception-proof stable guard"; }
part source5:SourceRow { attribute :>> key="rc-write"; attribute :>> path="vendor/gambit/lib/_mem/rc-allocation.inc"; attribute :>> needle="___EXP_FUNC(___BOOL,___set_data_rc)"; attribute :>> limit="payload writer, not a future control-word writer"; }
part source6:SourceRow { attribute :>> key="rc-root"; attribute :>> path="vendor/gambit/lib/_mem/rc-roots.inc"; attribute :>> needle="mark_array (work, &h->data, 1);"; attribute :>> limit="root slot is updated by GC under closed domain"; }
part source7:SourceRow { attribute :>> key="thread"; attribute :>> path="vendor/gambit/lib/os_thread.c"; attribute :>> needle="void ___thread_set_pstate"; attribute :>> limit="TLS and affinity only; no ticket or extent identity"; }
part source8:SourceRow { attribute :>> key="tcl"; attribute :>> path="vendor/gambit/examples/tcltk/tcltk.scm"; attribute :>> needle="___HIDDEN int scheme_call_cmd"; attribute :>> limit="snapshot before SFUN entry; source borrowing gap"; }
part source9:SourceRow { attribute :>> key="extent-paper"; attribute :>> path="evidence/research/source-references/feeley-sfp/8bb2fae8ae4b54d3a86206596f90e9cf73da39846af0f39244a476074cf81ed4.txt"; attribute :>> needle="5       Pra"; attribute :>> limit="paper proposes native segment lifetime; not C23 scope protocol"; }
part source10:SourceRow { attribute :>> key="rc-freeze"; attribute :>> path="vendor/gambit/lib/_mem/rc-allocation.inc"; attribute :>> needle="Closing writers must never"; attribute :>> limit="GC closes writers without draining root borrows"; }
part source11:SourceRow { attribute :>> key="rc-register"; attribute :>> path="vendor/gambit/lib/_mem/rc-allocation.inc"; attribute :>> needle="Unregistered allocation remains caller-owned."; attribute :>> limit="registration rejection returns private allocation ownership"; }
part source12:SourceRow { attribute :>> key="rc-borrow"; attribute :>> path="vendor/gambit/lib/_mem/rc-allocation.inc"; attribute :>> needle="___SCMOBJ *___borrow_rc_root"; attribute :>> limit="cell pin and context root are distinct from GC participation"; }
part source13:SourceRow { attribute :>> key="root-origin"; attribute :>> path="vendor/gambit/lib/_mem/root-origins.inc"; attribute :>> needle="mark_array (work, &context->startup_thunk, 1);"; attribute :>> limit="startup source slot already enumerated"; }
part source14:SourceRow { attribute :>> key="gc-round"; attribute :>> path="vendor/gambit/lib/_mem/collection-round.inc"; attribute :>> needle="BARRIER(); /* no worker may retain a stopped root view past this cut */"; attribute :>> limit="actual context thaw and reopen path"; }
part source15:SourceRow { attribute :>> key="argument-order"; attribute :>> path="vendor/gambit/gsc/_ptree2.scm"; attribute :>> needle="(append (keep scmobj-typ? numbered-param-typs)"; attribute :>> limit="SCMOBJ arguments are converted before collecting converters"; }
part source16:SourceRow { attribute :>> key="tcl-dispatch"; attribute :>> path="evidence/research/source-references/tcl/cbf86d62348d6b052e1961b4df995960fb21545f/generic/tclBasic.c"; attribute :>> needle="result = cmdPtr->proc(cmdPtr->clientData, interp, objc, argv);"; attribute :>> limit="pinned captured source only; not installed Tcl qualification"; }
part source17:SourceRow { attribute :>> key="tcl-delete"; attribute :>> path="evidence/research/source-references/tcl/cbf86d62348d6b052e1961b4df995960fb21545f/generic/tclBasic.c"; attribute :>> needle="cmdPtr->deleteProc(cmdPtr->deleteData);"; attribute :>> limit="application cleanup runs before final command cleanup"; }
part def CutRow { attribute key:String; attribute source:String; attribute cutBefore:String; attribute existing:String; attribute needed:String; attribute classification:String; }
part cut0:CutRow { attribute :>> key="run-startup"; attribute :>> source="run"; attribute :>> cutBefore="context r[0], catcher and marker allocation"; attribute :>> existing="startup_thunk and entry_marker are scanned context roots"; attribute :>> needed="validate startup generation; publish rooted stable guard before entry writes"; attribute :>> classification="reuse rooted source; new joint issuer"; }
part cut1:CutRow { attribute :>> key="run-program"; attribute :>> source="run"; attribute :>> cutBefore="legacy by-value marker helper"; attribute :>> existing="initial program thunk comes from program_descr; helper uses noncollecting RC bridge"; attribute :>> needed="retain program/module descriptor and prove noncollecting interval or use registered source slot"; attribute :>> classification="bounded call path; arbitrary raw thunk provenance unresolved"; }
part cut2:CutRow { attribute :>> key="sfun-closure"; attribute :>> source="sfun"; attribute :>> cutBefore="root bank allocation and marker construction"; attribute :>> existing="closure self root borrow, noncollecting bank allocation and registered bank"; attribute :>> needed="pre-reserve stable completion slot; retain source until registered target acknowledged"; attribute :>> classification="reuse RC source and bank; no duplicate root bank"; }
part cut3:CutRow { attribute :>> key="sfun-raw-args"; attribute :>> source="argument-order"; attribute :>> cutBefore="first collecting representation converter"; attribute :>> existing="SCMOBJ argument prefix is registered through BEGIN_SFUN_ARG_SCMOBJ"; attribute :>> needed="seal generated raw-input prefix and reject unknown pre-prefix callbacks"; attribute :>> classification="existing ordering reusable; complete converter closure unresolved"; }
part cut4:CutRow { attribute :>> key="tcl-pre-dispatch"; attribute :>> source="tcl"; attribute :>> cutBefore="___data_rc snapshot"; attribute :>> existing="same-owner callback can reach bank through a noncollecting path"; attribute :>> needed="joint Tcl owner lease and Gambit root eligibility; stable owner before raw RC dereference"; attribute :>> classification="no demonstrated ordinary same-owner race; new asynchronous profile needs qualification"; }
part cut5:CutRow { attribute :>> key="nested-return"; attribute :>> source="catcher"; attribute :>> cutBefore="outer catcher landing and marker invalidation"; attribute :>> existing="local catcher restores old catcher; marker detects invalid return"; attribute :>> needed="stable parent-linked guard settles or retains entire affected subtree"; attribute :>> classification="proposed adapter; no cross-Tcl nonlocal jump assumed"; }
part cut6:CutRow { attribute :>> key="sfun-error"; attribute :>> source="sfun-exit"; attribute :>> cutBefore="conversion-error Scheme callback"; attribute :>> existing="check_sfun prevents entry after current domain rejection"; attribute :>> needed="AdmissionRejected and UnknownCompletion are transport outcomes, not conversion errors"; attribute :>> classification="new checked status adapter; marker reuse is not operation identity"; }
part cut7:CutRow { attribute :>> key="sfun-end"; attribute :>> source="sfun-exit"; attribute :>> cutBefore="end_sfun returns bank borrow and releases RC"; attribute :>> existing="normal cleanup endpoint exists"; attribute :>> needed="last use, known completion, closed scanner admission and grace before root retirement"; attribute :>> classification="reuse cleanup operations after new ordering proof"; }
part def IssuerRow { attribute key:String; attribute source:String; attribute fact:String; attribute signs:String; attribute limit:String; }
part issuer0:IssuerRow { attribute :>> key="source-owner"; attribute :>> source="rc-borrow"; attribute :>> fact="live storage, canonical registered source slot, same-owner eligibility"; attribute :>> signs="source lease or qualified noncollecting owner interval"; attribute :>> limit="cannot sign VM admission or rely on raw SCMOBJ address"; }
part issuer1:IssuerRow { attribute :>> key="vm-domain"; attribute :>> source="gc-round"; attribute :>> fact="current context in frozen manifest and participant execution state"; attribute :>> signs="current execution or parked-scannable-root handoff"; attribute :>> limit="no waiting for borrower count during GC freeze"; }
part issuer2:IssuerRow { attribute :>> key="native-thread"; attribute :>> source="thread"; attribute :>> fact="actual native binding and live C return extent"; attribute :>> signs="thread and return identity for this activation"; attribute :>> limit="TLS alone insufficient; no C stack migration"; }
part issuer3:IssuerRow { attribute :>> key="guard-registry"; attribute :>> source="sfun"; attribute :>> fact="pre-reserved stable record and acknowledged canonical root bundle"; attribute :>> signs="same EntryId registration; accepted or unknown custody"; attribute :>> limit="no registration retry with new identity after lost response"; }
part issuer4:IssuerRow { attribute :>> key="scanner"; attribute :>> source="rc-root"; attribute :>> fact="root slot updated and old scan admission drained"; attribute :>> signs="local registry detachment and round grace"; attribute :>> limit="new registry-to-current-manifest adapter unresolved"; }
part def RouteRow { attribute actionName:String; attribute lemma:String; attribute source:String; attribute obligationId:String; }
part route0:RouteRow { attribute :>> actionName="pinSource"; attribute :>> lemma="NativeEntry.pinSourcePreserves"; attribute :>> source="rc-borrow"; attribute :>> obligationId="entry-safety"; }
part route1:RouteRow { attribute :>> actionName="reserveCarrier"; attribute :>> lemma="NativeEntry.reserveCarrierPreserves"; attribute :>> source="sfun"; attribute :>> obligationId="entry-safety"; }
part route2:RouteRow { attribute :>> actionName="qualifyHost"; attribute :>> lemma="NativeEntry.qualifyHostPreserves"; attribute :>> source="sfun"; attribute :>> obligationId="entry-safety"; }
part route3:RouteRow { attribute :>> actionName="publishCarrier"; attribute :>> lemma="NativeEntry.publishCarrierPreserves"; attribute :>> source="sfun"; attribute :>> obligationId="entry-safety"; }
part route4:RouteRow { attribute :>> actionName="loseRegistrationAck"; attribute :>> lemma="NativeEntry.loseRegistrationAckPreserves"; attribute :>> source="sfun"; attribute :>> obligationId="entry-safety"; }
part route5:RouteRow { attribute :>> actionName="confirmSameRegistration"; attribute :>> lemma="NativeEntry.confirmSameRegistrationPreserves"; attribute :>> source="sfun"; attribute :>> obligationId="entry-safety"; }
part route6:RouteRow { attribute :>> actionName="jointIssue"; attribute :>> lemma="NativeEntry.jointIssuePreserves"; attribute :>> source="sfun"; attribute :>> obligationId="entry-safety"; }
part route7:RouteRow { attribute :>> actionName="writeEntryState"; attribute :>> lemma="NativeEntry.writeEntryStatePreserves"; attribute :>> source="sfun"; attribute :>> obligationId="entry-safety"; }
part route8:RouteRow { attribute :>> actionName="allocateMarker"; attribute :>> lemma="NativeEntry.allocateMarkerPreserves"; attribute :>> source="sfun"; attribute :>> obligationId="entry-safety"; }
part route9:RouteRow { attribute :>> actionName="certifyTransfer"; attribute :>> lemma="NativeEntry.certifyTransferPreserves"; attribute :>> source="rc-borrow"; attribute :>> obligationId="entry-safety"; }
part route10:RouteRow { attribute :>> actionName="releaseSource"; attribute :>> lemma="NativeEntry.releaseSourcePreserves"; attribute :>> source="rc-borrow"; attribute :>> obligationId="entry-safety"; }
part route11:RouteRow { attribute :>> actionName="closeIngress"; attribute :>> lemma="NativeEntry.closeIngressPreserves"; attribute :>> source="tcl"; attribute :>> obligationId="entry-safety"; }
part route12:RouteRow { attribute :>> actionName="exhaustCarrier"; attribute :>> lemma="NativeEntry.exhaustCarrierPreserves"; attribute :>> source="sfun"; attribute :>> obligationId="entry-safety"; }
part route13:RouteRow { attribute :>> actionName="rejectClosed"; attribute :>> lemma="NativeEntry.rejectClosedPreserves"; attribute :>> source="sfun"; attribute :>> obligationId="entry-safety"; }
part route14:RouteRow { attribute :>> actionName="freezeWriters"; attribute :>> lemma="NativeEntry.freezeWritersPreserves"; attribute :>> source="gc-round"; attribute :>> obligationId="entry-safety"; }
part route15:RouteRow { attribute :>> actionName="scanSource"; attribute :>> lemma="NativeEntry.scanSourcePreserves"; attribute :>> source="gc-round"; attribute :>> obligationId="entry-safety"; }
part route16:RouteRow { attribute :>> actionName="scanBoth"; attribute :>> lemma="NativeEntry.scanBothPreserves"; attribute :>> source="gc-round"; attribute :>> obligationId="entry-safety"; }
part route17:RouteRow { attribute :>> actionName="scanCarrier"; attribute :>> lemma="NativeEntry.scanCarrierPreserves"; attribute :>> source="gc-round"; attribute :>> obligationId="entry-safety"; }
part route18:RouteRow { attribute :>> actionName="thawWriters"; attribute :>> lemma="NativeEntry.thawWritersPreserves"; attribute :>> source="gc-round"; attribute :>> obligationId="entry-safety"; }
part route19:RouteRow { attribute :>> actionName="enterNested"; attribute :>> lemma="NativeEntry.enterNestedPreserves"; attribute :>> source="tcl"; attribute :>> obligationId="entry-safety"; }
part route20:RouteRow { attribute :>> actionName="leaveNested"; attribute :>> lemma="NativeEntry.leaveNestedPreserves"; attribute :>> source="tcl"; attribute :>> obligationId="entry-safety"; }
part route21:RouteRow { attribute :>> actionName="recordOutcome"; attribute :>> lemma="NativeEntry.recordOutcomePreserves"; attribute :>> source="sfun"; attribute :>> obligationId="entry-safety"; }
part route22:RouteRow { attribute :>> actionName="loseCompletion"; attribute :>> lemma="NativeEntry.loseCompletionPreserves"; attribute :>> source="catcher"; attribute :>> obligationId="entry-safety"; }
part route23:RouteRow { attribute :>> actionName="landNested"; attribute :>> lemma="NativeEntry.landNestedPreserves"; attribute :>> source="catcher"; attribute :>> obligationId="entry-safety"; }
part route24:RouteRow { attribute :>> actionName="settleKnown"; attribute :>> lemma="NativeEntry.settleKnownPreserves"; attribute :>> source="sfun"; attribute :>> obligationId="entry-safety"; }
part route25:RouteRow { attribute :>> actionName="recoverRecorded"; attribute :>> lemma="NativeEntry.recoverRecordedPreserves"; attribute :>> source="catcher"; attribute :>> obligationId="entry-safety"; }
part route26:RouteRow { attribute :>> actionName="closeScanAdmission"; attribute :>> lemma="NativeEntry.closeScanAdmissionPreserves"; attribute :>> source="gc-round"; attribute :>> obligationId="entry-safety"; }
part route27:RouteRow { attribute :>> actionName="confirmGrace"; attribute :>> lemma="NativeEntry.confirmGracePreserves"; attribute :>> source="gc-round"; attribute :>> obligationId="entry-safety"; }
part route28:RouteRow { attribute :>> actionName="retireCarrier"; attribute :>> lemma="NativeEntry.retireCarrierPreserves"; attribute :>> source="sfun"; attribute :>> obligationId="entry-safety"; }
part def JoinRow { attribute key:String; attribute lemma:String; attribute source:String; attribute premise:String; attribute status:String; }
part join0:JoinRow { attribute :>> key="fresh-native-issue"; attribute :>> lemma="NativeEntry.jointIssueNativeStep"; attribute :>> source="run"; attribute :>> premise="fresh generation/owner and remaining NativeScope.initial premises; not arbitrary restored scope"; attribute :>> status="conditional-lemma"; }
part join1:JoinRow { attribute :>> key="root-before-marker"; attribute :>> lemma="NativeEntry.markerHasRootAndGuard"; attribute :>> source="sfun"; attribute :>> premise="initial source eligibility and linearizable root publication"; attribute :>> status="conditional-lemma"; }
part join2:JoinRow { attribute :>> key="close-is-not-drain"; attribute :>> lemma="NativeEntry.closePreservesEnrolled"; attribute :>> source="rc-freeze"; attribute :>> premise="accepted operation retains registry while ingress is closed"; attribute :>> status="conditional-lemma"; }
part join3:JoinRow { attribute :>> key="freeze-with-borrow"; attribute :>> lemma="NativeEntry.freezeDoesNotWaitForBorrow"; attribute :>> source="rc-freeze"; attribute :>> premise="source pin denotes scannable cell; mutator not running while slot updates"; attribute :>> status="conditional-lemma"; }
part join4:JoinRow { attribute :>> key="current-root-transfer"; attribute :>> lemma="NativeEntry.transferNeedsCurrentSlot"; attribute :>> source="rc-root"; attribute :>> premise="freeze invalidates receipt; target root storage remains stable"; attribute :>> status="conditional-lemma"; }
part join5:JoinRow { attribute :>> key="unknown-custody"; attribute :>> lemma="NativeEntry.unknownRetainsCarrier"; attribute :>> source="catcher"; attribute :>> premise="completion record matches same operation; no fabricated oracle"; attribute :>> status="conditional-lemma"; }
part join6:JoinRow { attribute :>> key="grace-before-retire"; attribute :>> lemma="NativeEntry.retireNeedsGraceAndDrain"; attribute :>> source="gc-round"; attribute :>> premise="scan snapshot enrollment and close are atomic model actions"; attribute :>> status="conditional-lemma"; }
part def ObligationRow { attribute key:String; attribute status:String; attribute condition:String; }
part obligation0:ObligationRow { attribute :>> key="entry-safety"; attribute :>> status="conditional-model"; attribute :>> condition="29 guarded actions preserve scoped root coverage and custody"; }
part obligation1:ObligationRow { attribute :>> key="fresh-join"; attribute :>> status="conditional-model"; attribute :>> condition="exact paired jointIssue to actual NativeScope.issue; fresh instance only"; }
part obligation2:ObligationRow { attribute :>> key="source-eligibility"; attribute :>> status="unresolved"; attribute :>> condition="source owner supplies real storage identity and scanner coverage before carrier registration"; }
part obligation3:ObligationRow { attribute :>> key="noncollect-prefix"; attribute :>> status="unresolved"; attribute :>> condition="all enabled converters, allocation hooks and callouts obey declared no-collect/no-abandon interval"; }
part obligation4:ObligationRow { attribute :>> key="joint-native-cut"; attribute :>> status="unresolved"; attribute :>> condition="real entry issuer and publication atomicity across source, VM, thread and stable registry"; }
part obligation5:ObligationRow { attribute :>> key="registration-recovery"; attribute :>> status="unresolved"; attribute :>> condition="EntryId lookup and stable recipient survive lost publication response and abnormal unwind"; }
part obligation6:ObligationRow { attribute :>> key="tcl-profile"; attribute :>> status="unresolved"; attribute :>> condition="same interpreter thread, command/data owner lifetime and installed Tcl source correspondence"; }
part obligation7:ObligationRow { attribute :>> key="scan-native-cut"; attribute :>> status="unresolved"; attribute :>> condition="root freeze/manifest enrollment, update and unregister grace refine model atomic actions"; }
part obligation8:ObligationRow { attribute :>> key="nested-landing"; attribute :>> status="unresolved"; attribute :>> condition="all caught and escaping exits preserve source/bank/marker and actual C extent"; }
part obligation9:ObligationRow { attribute :>> key="full-product"; attribute :>> status="unresolved"; attribute :>> condition="arbitrary nested and resumed NativeScope state coupling, not resetting thread history"; }
part obligation10:ObligationRow { attribute :>> key="c23-refinement"; attribute :>> status="unresolved"; attribute :>> condition="actual atomic storage, orders, lock domains and reads-from prove the abstract publication cuts"; }
part def MemoryRow { attribute key:String; attribute ordering:String; attribute condition:String; attribute obligationId:String; }
part memory0:MemoryRow { attribute :>> key="source-before-load"; attribute :>> ordering="acquire owner lifetime before payload access"; attribute :>> condition="root borrow or equivalent qualified owner interval; locking freed RC memory is invalid"; attribute :>> obligationId="source-eligibility"; }
part memory1:MemoryRow { attribute :>> key="registry-publication"; attribute :>> ordering="release immutable EntryId/root bundle; acquire acknowledges same bundle"; attribute :>> condition="source remains held on unknown publication; partial raw storage is not published"; attribute :>> obligationId="joint-native-cut"; }
part memory2:MemoryRow { attribute :>> key="entry-close"; attribute :>> ordering="one linearization for acceptance versus close; accepted count retained"; attribute :>> condition="source reservation is not execution permission; losing closure race cannot mutate PSTATE"; attribute :>> obligationId="joint-native-cut"; }
part memory3:MemoryRow { attribute :>> key="gc-freeze"; attribute :>> ordering="stop native slot writers; do not wait for root borrows"; attribute :>> condition="scanner updates source/carrier canonical cells; reload after thaw before use"; attribute :>> obligationId="scan-native-cut"; }
part memory4:MemoryRow { attribute :>> key="outcome-before-release"; attribute :>> ordering="stable record publication precedes dropping execution enrollment"; attribute :>> condition="only same operation delivery or reconciliation may settle; no fresh execution on uncertainty"; attribute :>> obligationId="registration-recovery"; }
part memory5:MemoryRow { attribute :>> key="scanner-retirement"; attribute :>> ordering="close lookup/enrollment then drain already captured scans"; attribute :>> condition="zero native callbacks alone is not a descriptor/root reclamation permit"; attribute :>> obligationId="scan-native-cut"; }
part def GainRow { attribute key:String; attribute benefit:String; attribute overhead:String; attribute positive:String; attribute refutation:String; }
part gain0:GainRow { attribute :>> key="root-bank-reuse"; attribute :>> benefit="reuse existing SFUN RC bank and SCMOBJ-first generator prefix"; attribute :>> overhead="no mandatory second bank; one stable scope record per active entry"; attribute :>> positive="approved noncollecting prefix and source lifetime proof"; attribute :>> refutation="wrapping every argument with duplicate pins adds work without new coverage"; }
part gain1:GainRow { attribute :>> key="gc-progress"; attribute :>> benefit="GC can update pinned roots without waiting for native borrowers"; attribute :>> overhead="freeze/thaw and canonical-slot reload; existing scan can supply these"; attribute :>> positive="all parked native values are in enumerated slots"; attribute :>> refutation="drain borrowers during freeze creates collector/callback circular wait"; }
part gain2:GainRow { attribute :>> key="source-transfer"; attribute :>> benefit="release redundant source lease after registered target coverage"; attribute :>> overhead="one matching registration acknowledgment; overlap covers handoff"; attribute :>> positive="target is included in every applicable GC snapshot"; attribute :>> refutation="RC refcount alone does not prove target scanner coverage"; }
part gain3:GainRow { attribute :>> key="unknown"; attribute :>> benefit="zero blind re-registration or call replay after response loss"; attribute :>> overhead="O(K) stable records for K outstanding entries; retention unbounded on permanent uncertainty"; attribute :>> positive="same EntryId/operation lookup works after unwinding"; attribute :>> refutation="timeout as proof of failure permits double execution or premature release"; }
part gain4:GainRow { attribute :>> key="close-and-drain"; attribute :>> benefit="one authority for entry closure and local scanner retirement"; attribute :>> overhead="accepted-operation ledger plus scan admission/grace; closure is not a free operation"; attribute :>> positive="reuse actual GC round barriers without merging callback counts"; attribute :>> refutation="global counter or scan waits can erase concurrency gain"; }
part gain5:GainRow { attribute :>> key="language"; attribute :>> benefit="C23 can express all required boundaries without introducing a second runtime"; attribute :>> overhead="Zig would need the same FFI/GC/control refinement in addition to C23 baseline"; attribute :>> positive="incremental language benefit must be proved separately"; attribute :>> refutation="changing language does not remove native extent or root handoff obligations"; }
part def EdgeRow { attribute fromNode:String; attribute toNode:String; attribute contract:String; }
part edge0:EdgeRow { attribute :>> fromNode="Tcl_owner"; attribute :>> toNode="source_lease"; attribute :>> contract="protect owner before data_rc load"; }
part edge1:EdgeRow { attribute :>> fromNode="run_startup_root"; attribute :>> toNode="source_lease"; attribute :>> contract="reuse scanned context slot"; }
part edge2:EdgeRow { attribute :>> fromNode="SFUN_closure_root"; attribute :>> toNode="source_lease"; attribute :>> contract="borrow registered source cell"; }
part edge3:EdgeRow { attribute :>> fromNode="source_lease"; attribute :>> toNode="carrier_reservation"; attribute :>> contract="nonallocating stable reservation; retain source on failure"; }
part edge4:EdgeRow { attribute :>> fromNode="carrier_reservation"; attribute :>> toNode="registered_bundle"; attribute :>> contract="publish same EntryId and root/guard bundle"; }
part edge5:EdgeRow { attribute :>> fromNode="registered_bundle"; attribute :>> toNode="joint_issuer"; attribute :>> contract="source + VM + thread/return + registry acknowledgment"; }
part edge6:EdgeRow { attribute :>> fromNode="joint_issuer"; attribute :>> toNode="entry_writes"; attribute :>> contract="before r[0], conversion or marker allocation"; }
part edge7:EdgeRow { attribute :>> fromNode="registered_bundle"; attribute :>> toNode="GC_scan"; attribute :>> contract="freeze writers; borrowers may remain"; }
part edge8:EdgeRow { attribute :>> fromNode="GC_scan"; attribute :>> toNode="transfer_receipt"; attribute :>> contract="reload current slots after thaw; freeze revokes old receipt"; }
part edge9:EdgeRow { attribute :>> fromNode="transfer_receipt"; attribute :>> toNode="source_release"; attribute :>> contract="registered target retains coverage"; }
part edge10:EdgeRow { attribute :>> fromNode="entry_writes"; attribute :>> toNode="nested_callback"; attribute :>> contract="new nested identity; outer enrollment remains"; }
part edge11:EdgeRow { attribute :>> fromNode="nested_callback"; attribute :>> toNode="completion_ledger"; attribute :>> contract="landing settles or retains subtree"; }
part edge12:EdgeRow { attribute :>> fromNode="completion_ledger"; attribute :>> toNode="unknown_custodian"; attribute :>> contract="recorded result can be delivered; unrecorded uncertainty stays rooted"; }
part edge13:EdgeRow { attribute :>> fromNode="completion_ledger"; attribute :>> toNode="close_scan_admission"; attribute :>> contract="close ingress and settle operations first"; }
part edge14:EdgeRow { attribute :>> fromNode="close_scan_admission"; attribute :>> toNode="GC_grace"; attribute :>> contract="drain already enrolled scans"; }
part edge15:EdgeRow { attribute :>> fromNode="GC_grace"; attribute :>> toNode="local_detach"; attribute :>> contract="no global module-unload claim"; }
part edge16:EdgeRow { attribute :>> fromNode="SysML"; attribute :>> toNode="QNT"; attribute :>> contract="29 source-routed atomic actions and scoped premises"; }
part edge17:EdgeRow { attribute :>> fromNode="QNT"; attribute :>> toNode="Lean"; attribute :>> contract="binding-aware typed IR plus reachable-state induction"; }
part edge18:EdgeRow { attribute :>> fromNode="Lean"; attribute :>> toNode="NativeScope"; attribute :>> contract="actual fresh-issue Step join; full product still open"; }
part edge19:EdgeRow { attribute :>> fromNode="SysML"; attribute :>> toNode="ASCENT"; attribute :>> contract="source hashes, cut profiles, issuers and unresolved obligations"; }
part edge20:EdgeRow { attribute :>> fromNode="Lean"; attribute :>> toNode="ASCENT"; attribute :>> contract="compiled lemmas and negative controls; current native admission blocked"; }

part def ComponentRow { attribute componentId:String; attribute actionSlice:String; attribute sharedContract:String; attribute proof:String; attribute source:String; }
part component0:ComponentRow { attribute :>> componentId="root-ingress"; attribute :>> actionSlice="pinSource/reserveCarrier/exhaustCarrier"; attribute :>> sharedContract="source-eligibility"; attribute :>> proof="NativeEntry.closedEntryCannotPin"; attribute :>> source="rc-borrow"; }
part component1:ComponentRow { attribute :>> componentId="root-registration"; attribute :>> actionSlice="publishCarrier/loseRegistrationAck/confirmSameRegistration"; attribute :>> sharedContract="registration-recovery"; attribute :>> proof="NativeEntry.issuerNeedsKnownRegistration"; attribute :>> source="sfun"; }
part component2:ComponentRow { attribute :>> componentId="joint-issuer"; attribute :>> actionSlice="jointIssue/writeEntryState/allocateMarker"; attribute :>> sharedContract="joint-native-cut"; attribute :>> proof="NativeEntry.jointIssueNativeStep"; attribute :>> source="run"; }
part component3:ComponentRow { attribute :>> componentId="native-execution"; attribute :>> actionSlice="enterNested/loseCompletion/recoverRecorded"; attribute :>> sharedContract="nested-landing"; attribute :>> proof="NativeEntry.unknownRetainsCarrier"; attribute :>> source="catcher"; }
part component4:ComponentRow { attribute :>> componentId="root-lifetime"; attribute :>> actionSlice="freezeWriters/scanBoth/confirmGrace/retireCarrier"; attribute :>> sharedContract="scan-native-cut"; attribute :>> proof="NativeEntry.retireNeedsGraceAndDrain"; attribute :>> source="gc-round"; }

part def AuthorityRow { attribute key:String; attribute source:String; attribute actionSlice:String; attribute permission:String; attribute proof:String; attribute limit:String; }
part authority0:AuthorityRow { attribute :>> key="root-preparation"; attribute :>> source="sfun"; attribute :>> actionSlice="pinSource/reserveCarrier/qualifyHost/publishCarrier"; attribute :>> permission="prepare registered roots only; no entry PSTATE writes or collecting marker"; attribute :>> proof="NativeEntry.preparationCannotExecute"; attribute :>> limit="source eligibility and bounded native allocation custody are separate premises"; }
part authority1:AuthorityRow { attribute :>> key="execution"; attribute :>> source="run"; attribute :>> actionSlice="jointIssue/writeEntryState/allocateMarker"; attribute :>> permission="execute this accepted entry after known root registration"; attribute :>> proof="NativeEntry.jointIssueNativeStep"; attribute :>> limit="fresh NativeScope instance only; restored-history composition unresolved"; }
}
