package GambitRcRootRelease { private import ScalarValues::*;
part def SourceRow { attribute key:String; attribute path:String; attribute needle:String; attribute limit:String; }
part source0:SourceRow { attribute :>> key="scan"; attribute :>> path="vendor/gambit/lib/_mem/rc-roots.inc"; attribute :>> needle="___SPINLOCK_LOCK(context->mem.rc_gate_);"; attribute :>> limit="entire normal list scan under same gate"; }
part source1:SourceRow { attribute :>> key="unlink"; attribute :>> path="vendor/gambit/lib/_mem/rc-allocation.inc"; attribute :>> needle="if (--h->refcount != 0) return 0;"; attribute :>> limit="zero reference under gate; not stable receipt"; }
part source2:SourceRow { attribute :>> key="free"; attribute :>> path="vendor/gambit/lib/_mem/rc-allocation.inc"; attribute :>> needle="if (reclaim) ___FREE_MEM(h);"; attribute :>> limit="native free after unlock"; }
part source3:SourceRow { attribute :>> key="borrow"; attribute :>> path="vendor/gambit/lib/_mem/rc-allocation.inc"; attribute :>> needle="___SCMOBJ *___borrow_rc_root"; attribute :>> limit="pins storage and contributes to refcount"; }
part source4:SourceRow { attribute :>> key="cleanup"; attribute :>> path="vendor/gambit/lib/_mem/rc-allocation.inc"; attribute :>> needle="___SPINLOCK_DESTROY(___ps->context->mem.rc_gate_);"; attribute :>> limit="whole-domain teardown is stronger than node unlink"; }
part source5:SourceRow { attribute :>> key="copy"; attribute :>> path="vendor/gambit/lib/_mem/copy-reservations.inc"; attribute :>> needle="work->tail_cell_ = cell;"; attribute :>> limit="normal Tail points to destination payload; inspect assignment chain"; }
part source6:SourceRow { attribute :>> key="diagnostic"; attribute :>> path="vendor/gambit/lib/_mem/copy-reservations.inc"; attribute :>> needle="invalid_copy_cell = cell;"; attribute :>> limit="exceptional source address escape; no recovery qualification"; }
part source7:SourceRow { attribute :>> key="root-task"; attribute :>> path="vendor/gambit/lib/_mem/collection-round.inc"; attribute :>> needle="context = task->origin->context;"; attribute :>> limit="pre-claim context load must be covered"; }
part source8:SourceRow { attribute :>> key="bank"; attribute :>> path="vendor/gambit/lib/c_intf.c"; attribute :>> needle="___EXP_FUNC(void,___end_sfun)"; attribute :>> limit="borrow return then owner release"; }
part source9:SourceRow { attribute :>> key="tcl"; attribute :>> path="vendor/gambit/examples/tcltk/tcltk.scm"; attribute :>> needle="scheme_delete_cmd"; attribute :>> limit="separate Scheme payload and native storage obligations"; }
part source10:SourceRow { attribute :>> key="allocator"; attribute :>> path="vendor/gambit/lib/os_base.c"; attribute :>> needle="free (ptr);"; attribute :>> limit="origin-matched provider; backend result receipt remains premise"; }
part source11:SourceRow { attribute :>> key="origin-model"; attribute :>> path="dev/refactoring/modern-c/models/quint/darwin_target_lease.qnt"; attribute :>> needle="action beginOriginFree="; attribute :>> limit="existing model lacks explicit root-storage precondition"; }
part def ObligationRow { attribute key:String; attribute status:String; attribute condition:String; }
part obligation0:ObligationRow { attribute :>> key="node-safety"; attribute :>> status="conditional-model"; attribute :>> condition="same gate; bounded balanced references; managed source acquisition; no escaping normal slot"; }
part obligation1:ObligationRow { attribute :>> key="alias-closure"; attribute :>> status="unresolved"; attribute :>> condition="all exported slots, diagnostic overrides and raw FFI readers enrolled or denied"; }
part obligation2:ObligationRow { attribute :>> key="domain-grace"; attribute :>> status="unresolved"; attribute :>> condition="pre-claim readers, root tasks, descendants and external owners drained or handed off"; }
part obligation3:ObligationRow { attribute :>> key="native-free"; attribute :>> status="unresolved"; attribute :>> condition="non-abandoning capture or authoritative same-operation receipt; never blind retry"; }
part obligation4:ObligationRow { attribute :>> key="c23-refinement"; attribute :>> status="unresolved"; attribute :>> condition="gate implementation, release/acquire, source lifetime and native widths qualified"; }
part def RouteRow { attribute actionName:String; attribute lemma:String; attribute source:String; attribute obligation:String; }
part route0:RouteRow { attribute :>> actionName="acquireBorrow"; attribute :>> lemma="RcRootRelease.acquireBorrowPreserves"; attribute :>> source="unlink"; attribute :>> obligation="node-safety"; }
part route1:RouteRow { attribute :>> actionName="exportAlias"; attribute :>> lemma="RcRootRelease.exportAliasPreserves"; attribute :>> source="unlink"; attribute :>> obligation="node-safety"; }
part route2:RouteRow { attribute :>> actionName="closeSource"; attribute :>> lemma="RcRootRelease.closeSourcePreserves"; attribute :>> source="unlink"; attribute :>> obligation="node-safety"; }
part route3:RouteRow { attribute :>> actionName="dropOwner"; attribute :>> lemma="RcRootRelease.dropOwnerPreserves"; attribute :>> source="unlink"; attribute :>> obligation="node-safety"; }
part route4:RouteRow { attribute :>> actionName="returnBorrow"; attribute :>> lemma="RcRootRelease.returnBorrowPreserves"; attribute :>> source="unlink"; attribute :>> obligation="node-safety"; }
part route5:RouteRow { attribute :>> actionName="returnAlias"; attribute :>> lemma="RcRootRelease.returnAliasPreserves"; attribute :>> source="unlink"; attribute :>> obligation="node-safety"; }
part route6:RouteRow { attribute :>> actionName="beginScan"; attribute :>> lemma="RcRootRelease.beginScanPreserves"; attribute :>> source="scan"; attribute :>> obligation="node-safety"; }
part route7:RouteRow { attribute :>> actionName="endScan"; attribute :>> lemma="RcRootRelease.endScanPreserves"; attribute :>> source="scan"; attribute :>> obligation="node-safety"; }
part route8:RouteRow { attribute :>> actionName="enterReader"; attribute :>> lemma="RcRootRelease.enterReaderPreserves"; attribute :>> source="root-task"; attribute :>> obligation="node-safety"; }
part route9:RouteRow { attribute :>> actionName="exitReader"; attribute :>> lemma="RcRootRelease.exitReaderPreserves"; attribute :>> source="root-task"; attribute :>> obligation="node-safety"; }
part route10:RouteRow { attribute :>> actionName="unlinkAndPermit"; attribute :>> lemma="RcRootRelease.unlinkAndPermitPreserves"; attribute :>> source="unlink"; attribute :>> obligation="node-safety"; }
part route11:RouteRow { attribute :>> actionName="beginFree"; attribute :>> lemma="RcRootRelease.beginFreePreserves"; attribute :>> source="allocator"; attribute :>> obligation="node-safety"; }
part route12:RouteRow { attribute :>> actionName="loseFreeResult"; attribute :>> lemma="RcRootRelease.loseFreeResultPreserves"; attribute :>> source="allocator"; attribute :>> obligation="node-safety"; }
part route13:RouteRow { attribute :>> actionName="backendReceipt"; attribute :>> lemma="RcRootRelease.backendReceiptPreserves"; attribute :>> source="allocator"; attribute :>> obligation="node-safety"; }
part route14:RouteRow { attribute :>> actionName="settleFree"; attribute :>> lemma="RcRootRelease.settleFreePreserves"; attribute :>> source="allocator"; attribute :>> obligation="node-safety"; }
part route15:RouteRow { attribute :>> actionName="retireDomain"; attribute :>> lemma="RcRootRelease.retireDomainPreserves"; attribute :>> source="root-task"; attribute :>> obligation="node-safety"; }
part def GainRow { attribute key:String; attribute saved:String; attribute added:String; attribute condition:String; attribute status:String; }
part gain0:GainRow { attribute :>> key="normal-node-grace"; attribute :>> saved="0 extra whole-GC barriers per admitted node; reuse existing gate"; attribute :>> added="existing gate serialization remains; no speedup measured"; attribute :>> condition="synchronous scan; source admission closed; no escaping RC slot"; attribute :>> status="source-bound/conditional"; }
part gain1:GainRow { attribute :>> key="last-borrow"; attribute :>> saved="no second per-node borrow census; existing refcount includes borrow"; attribute :>> added="balanced ownership proof and bounded counters"; attribute :>> condition="borrow increments and return decrements same node"; attribute :>> status="source-bound"; }
part gain2:GainRow { attribute :>> key="domain-retirement"; attribute :>> saved="avoid waiting for unrelated domain borrowers on a single-node release"; attribute :>> added="whole-domain reader/task/owner census still required"; attribute :>> condition="node receipt never authorizes gate destruction"; attribute :>> status="unresolved-native"; }
part gain3:GainRow { attribute :>> key="unknown-free"; attribute :>> saved="0 speculative retry frees; 0 GC scans of detached possibly freed storage"; attribute :>> added="O(K) stable records and retained origin holds for K unresolved operations; potentially unbounded retention"; attribute :>> condition="pre-reserved independent metadata; authoritative operation reconciliation"; attribute :>> status="conditional-model"; }
part gain4:GainRow { attribute :>> key="legacy-retirement"; attribute :>> saved="0 current runtime paths retired by this research"; attribute :>> added="future typed release adapter and managed source acquisition"; attribute :>> condition="all caller and bulk-cleanup refinements pass"; attribute :>> status="design-only"; }
part def EdgeRow { attribute fromNode:String; attribute toNode:String; attribute contract:String; }
part edge0:EdgeRow { attribute :>> fromNode="Source owner"; attribute :>> toNode="RC domain gate"; attribute :>> contract="close lookup before header load; drain acquired references"; }
part edge1:EdgeRow { attribute :>> fromNode="RC domain gate"; attribute :>> toNode="Slot-release receipt"; attribute :>> contract="last zero + unlink + synchronous scan grace; alias closure"; }
part edge2:EdgeRow { attribute :>> fromNode="Slot-release receipt"; attribute :>> toNode="Origin release service"; attribute :>> contract="single-use StorageId/generation; reserved independent record"; }
part edge3:EdgeRow { attribute :>> fromNode="Origin release service"; attribute :>> toNode="Native free"; attribute :>> contract="retain original allocator family and provider"; }
part edge4:EdgeRow { attribute :>> fromNode="Native free"; attribute :>> toNode="Unknown custody"; attribute :>> contract="no blind retry; no payload dereference"; }
part edge5:EdgeRow { attribute :>> fromNode="Native free"; attribute :>> toNode="Origin retirement"; attribute :>> contract="authoritative completion, not physical-effect inference"; }
part edge6:EdgeRow { attribute :>> fromNode="Root task readers"; attribute :>> toNode="Domain retirement"; attribute :>> contract="pre-claim readers and descendants drained; separate permit"; }
part def IssuerRow { attribute key:String; attribute source:String; attribute signature:String; attribute gap:String; }
part issuer0:IssuerRow { attribute :>> key="source-owner"; attribute :>> source="tcl"; attribute :>> signature="source admission closed before header load; existing acquisitions drained"; attribute :>> gap="raw ClientData acquisition closure unresolved"; }
part issuer1:IssuerRow { attribute :>> key="rc-domain"; attribute :>> source="unlink"; attribute :>> signature="same-gate final zero, unlink and pre-reserved record commit"; attribute :>> gap="current Boolean is not persistent receipt"; }
part issuer2:IssuerRow { attribute :>> key="scan-authority"; attribute :>> source="copy"; attribute :>> signature="normal scan complete and no exported slot dereference"; attribute :>> gap="diagnostic and override reader closure unresolved"; }
part issuer3:IssuerRow { attribute :>> key="origin-service"; attribute :>> source="allocator"; attribute :>> signature="original allocator family and one-use OperationId"; attribute :>> gap="free completion receipt is a native premise"; }
part issuer4:IssuerRow { attribute :>> key="roster-owner"; attribute :>> source="root-task"; attribute :>> signature="pre-claim readers and descendants drained before gate destruction"; attribute :>> gap="whole-domain census unresolved"; }
}
