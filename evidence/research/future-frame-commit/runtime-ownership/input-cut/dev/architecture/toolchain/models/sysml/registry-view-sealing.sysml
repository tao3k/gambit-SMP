package RegistryViewSealing {
 private import ScalarValues::*;
 part def RegistrySpec { attribute key : String; attribute anchor : String; attribute condition : String; }
 part registry0 : RegistrySpec { attribute :>> key = "five-roots"; attribute :>> anchor = "_env.scm:290-314"; attribute :>> condition = "Five list globals initialized empty; five define-* helpers prepend; only managed profile may close writers"; }
 part registry1 : RegistrySpec { attribute :>> key = "stock-registrations"; attribute :>> anchor = "_ptree1.scm:483-526; _back.scm:575-594"; attribute :>> condition = "Preserve initialization completion, duplicate precedence and cross-category parser priority; do not normalize to an unordered name set"; }
 part registry2 : RegistrySpec { attribute :>> key = "parser-read"; attribute :>> anchor = "_ptree1.scm:2785-2847"; attribute :>> condition = "Parser checks flag, parameterized, boolean, namable, named-boolean in that order; registry receipt is a parser input"; }
 part registry3 : RegistrySpec { attribute :>> key = "identity"; attribute :>> anchor = "_env.scm:335-343; _prims.scm:1790-1796"; attribute :>> condition = "assq memq eq? require consistent symbol identities and private primitive names; spelling alone needs a proved bijection"; }
 part registry4 : RegistrySpec { attribute :>> key = "extension"; attribute :>> anchor = "_env.scm:296-314"; attribute :>> condition = "Late registration creates a new managed registry snapshot; unmediated writes taint dependent admission rather than blessing old keys"; }
 part def AliasSpec { attribute key : String; attribute anchor : String; attribute condition : String; }
 part alias0 : AliasSpec { attribute :>> key = "parser-owned"; attribute :>> anchor = "_ptree1.scm:2852-2866"; attribute :>> condition = "Fresh extracted names spine can be privately sealed; shared symbols remain identity-bearing leaves"; }
 part alias1 : AliasSpec { attribute :>> key = "constructor-borrow"; attribute :>> anchor = "_env.scm:327-331"; attribute :>> condition = "Both named constructors retain the caller names tail; copying only the outer record does not close writable aliases"; }
 part alias2 : AliasSpec { attribute :>> key = "view-borrow"; attribute :>> anchor = "_env.scm:102-111,335-343"; attribute :>> condition = "env-declare stores supplied record; env-decl-ref exposes complete list; seal private copy or prove exclusive writer closure"; }
 part alias3 : AliasSpec { attribute :>> key = "revoke-drain"; attribute :>> anchor = "proposed service contract"; attribute :>> condition = "Stop new leases atomically with retirement; coherent pinned immutable attempts may drain; tainted attempts cannot publish; roots survive until all holders exit"; }
 part def ChainSpec { attribute key : String; attribute anchor : String; attribute qntAction : String; attribute leanLemma : String; attribute condition : String; }
 part chain0 : ChainSpec { attribute :>> key = "per-name-arith"; attribute :>> anchor = "_prims.scm:1793-1796,1818-1835; _back.scm:579-580"; attribute :>> qntAction = "advance"; attribute :>> leanLemma = "namedGenericStop"; attribute :>> condition = "Every step queries the current provider captured canonical name; named + does not cover ##+"; }
 part chain1 : ChainSpec { attribute :>> key = "unsafe-priority"; attribute :>> anchor = "_prims.scm:1827-1835,1889-1890"; attribute :>> qntAction = "advance"; attribute :>> leanLemma = "unsafeFirst"; attribute :>> condition = "Unsafe distinct fallback precedes arithmetic mode; ##+ has absent unsafe fallback=self"; }
 part chain2 : ChainSpec { attribute :>> key = "fx-unsafe"; attribute :>> anchor = "_prims.scm:2075; _prims.scm:1803-1806"; attribute :>> qntAction = "advance"; attribute :>> leanLemma = "fixUnsafe"; attribute :>> condition = "fx+ selects ##fx+ only when safe? is false"; }
 part chain3 : ChainSpec { attribute :>> key = "initial-gate"; attribute :>> anchor = "_ptree1.scm:353-378"; attribute :>> qntAction = "beginAttempt"; attribute :>> leanLemma = "arityReject"; attribute :>> condition = "Resolve application/operand views per caller and preserve initial arity gate; no invented intermediate arity gate"; }
 part chain4 : ChainSpec { attribute :>> key = "fixed-point"; attribute :>> anchor = "_ptree1.scm:370-378; _back.scm:425-435"; attribute :>> qntAction = "completeAttempt"; attribute :>> leanLemma = "terminalPreserved"; attribute :>> condition = "Commit only after actual self step; stable private identity/helper domain; exceptions and nontermination stay explicit"; }
 part def GainSpec { attribute key : String; attribute avoided : String; attribute added : String; attribute condition : String; }
 part gain0 : GainSpec { attribute :>> key = "registry-snapshot"; attribute :>> avoided = "Per-attempt registry reconstruction and serialized profile reads"; attribute :>> added = "Ordered registry receipt, initial sealing and generation admission"; attribute :>> condition = "R registry work saved must exceed snapshot validation and key cost; current lists already share tails"; }
 part gain1 : GainSpec { attribute :>> key = "named-view"; attribute :>> avoided = "Repeated unchanged names validation and declaration materialization"; attribute :>> added = "Private payload copies or exclusive leases, roots and taint propagation"; attribute :>> condition = "Share sealed tails only; retained-memory and revocation-drain costs are accounted separately"; }
 part gain2 : GainSpec { attribute :>> key = "chain-query"; attribute :>> avoided = "Repeated equivalent specialization and global helper serialization"; attribute :>> added = "Caller/view/name/profile keys, private mapping and whole-chain guards"; attribute :>> condition = "Positive only when reused work or removed critical path exceeds added overhead; no fabricated core-count speedup"; }
 part def RefinementSpec { attribute key : String; attribute qntScope : String; attribute leanScope : String; attribute sourceDuty : String; }
 part refinement0 : RefinementSpec { attribute :>> key = "publication"; attribute :>> qntScope = "seal;beginAttempt"; attribute :>> leanScope = "leaseRetire;arityReject;namedMatch;orderedLookupTransport"; attribute :>> sourceDuty = "Writer/alias closure and atomic admission source refinement"; }
 part refinement1 : RefinementSpec { attribute :>> key = "retirement"; attribute :>> qntScope = "retire;drain;taint"; attribute :>> leanScope = "leaseRetire;taintReject"; attribute :>> sourceDuty = "Continuations and unknown holders keep roots; stale result publication forbidden"; }
 part refinement2 : RefinementSpec { attribute :>> key = "chain"; attribute :>> qntScope = "advance;completeAttempt"; attribute :>> leanScope = "namedGenericStop;unsafeFirst;fixUnsafe;terminalPreserved"; attribute :>> sourceDuty = "Conditional + chain, provider names, initial resolution and outcomes"; }
 part refinement3 : RefinementSpec { attribute :>> key = "value"; attribute :>> qntScope = "publishResult"; attribute :>> leanScope = "costPositive"; attribute :>> sourceDuty = "Observed repeat counts, keys, memory and span; no native qualification"; }
 part def GateSpec { attribute key : String; attribute qualified : Boolean; attribute condition : String; }
 part gate0 : GateSpec { attribute :>> key = "registry-writers"; attribute :>> qualified = false; attribute :>> condition = "All reachable registry writes mediated; reflective/FFI extension writes not proved closed"; }
 part gate1 : GateSpec { attribute :>> key = "named-aliases"; attribute :>> qualified = false; attribute :>> condition = "Exclusive ownership or private-copy stable snapshot from all named payload writers"; }
 part gate2 : GateSpec { attribute :>> key = "chain-source"; attribute :>> qualified = false; attribute :>> condition = "Full source simulation beyond selected total + providers, argument values, errors and nontermination"; }
 part gate3 : GateSpec { attribute :>> key = "admission-order"; attribute :>> qualified = false; attribute :>> condition = "Linearizable lease retirement, publication and memory-lifetime implementation"; }
 part gate4 : GateSpec { attribute :>> key = "observer"; attribute :>> qualified = false; attribute :>> condition = "Actual iter generated declarations, lexical symbols, source and diagnostics equivalence"; }
 part gate5 : GateSpec { attribute :>> key = "retirement"; attribute :>> qualified = false; attribute :>> condition = "Every global registry/primitive/helper consumer migrated before global authority retires"; }
 part gate6 : GateSpec { attribute :>> key = "platform"; attribute :>> qualified = false; attribute :>> condition = "Roots continuations GC FFI SMP and performance remain independently unqualified"; }
 attribute workspaceCount : Integer = 2;
 attribute stockRegistrationCount : Integer = 41;
 attribute actualAdmitted : Boolean = false;
 part history : GambitAssuranceRouting::ModelNeed { ref part :>> owner = GambitBuildAssurance::planner.component; attribute :>> obligationId = "RV-H"; attribute :>> kind = "interleaving"; attribute :>> subjectPath = "models/build/registry_view_sealing.qnt"; attribute :>> subjectScope = "registry_view_sealing:Test$"; attribute :>> premise = "Conditional source correspondence; local proof is not source/platform admission"; }
 part induction : GambitAssuranceRouting::ModelNeed { ref part :>> owner = GambitBuildAssurance::planner.component; attribute :>> obligationId = "RV-I"; attribute :>> kind = "induction"; attribute :>> subjectPath = "models/build/RegistryViewSealing.lean"; attribute :>> subjectScope = "RegistryViewSealing:leaseRetire;arityReject;taintReject;namedGenericStop;unsafeFirst;fixUnsafe;terminalPreserved;namedMatch;orderedLookupTransport;costPositive"; attribute :>> premise = "Conditional source correspondence; local proof is not source/platform admission"; }
 part source : GambitAssuranceRouting::ModelNeed { ref part :>> owner = GambitBuildAssurance::planner.component; attribute :>> obligationId = "RV-S"; attribute :>> kind = "source-refinement"; attribute :>> subjectPath = "dev/architecture/toolchain/registry-view-sealing-design.org"; attribute :>> subjectScope = "RV-S:source"; attribute :>> premise = "Conditional source correspondence; local proof is not source/platform admission"; }
 part platform : GambitAssuranceRouting::ModelNeed { ref part :>> owner = GambitBuildAssurance::planner.component; attribute :>> obligationId = "RV-E"; attribute :>> kind = "environment-refinement"; attribute :>> subjectPath = "dev/architecture/toolchain/registry-view-sealing-design.org"; attribute :>> subjectScope = "RV-E:platform"; attribute :>> premise = "Conditional source correspondence; local proof is not source/platform admission"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = DeclarationSpecializationContext::source; }
}
