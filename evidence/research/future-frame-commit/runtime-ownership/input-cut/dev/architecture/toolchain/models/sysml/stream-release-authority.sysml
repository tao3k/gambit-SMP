package StreamReleaseAuthority {
 private import ScalarValues::*;
 part def Issuer { attribute key : String; attribute anchor : String; attribute existing : String; attribute mayIssue : String; attribute cannotIssue : String; }
 part issuer0 : Issuer { attribute :>> key = "managed-view-contract"; attribute :>> anchor = "stream.ss:19; lexer.ss:20; base.ss:7-8; runtime/error.ss:16-20,37-43"; attribute :>> existing = "Current stream/token/error shapes, without owner-token coverage proof"; attribute :>> mayIssue = "Proposed Scheme/native-contract admission establishes that every resource-capable alias keeps its owner token reachable"; attribute :>> cannotIssue = "Wrapper death alone cannot prove raw stream aliases dead; detached token/chunk views have separate owners"; }
 part issuer1 : Issuer { attribute :>> key = "gc-private-notifier"; attribute :>> anchor = "mem.c:4039-4064,4997-5105,6843-6900; _kernel.scm:2106-2116"; attribute :>> existing = "Collector will eligibility and later Scheme will action; no public stream-detachment receipt"; attribute :>> mayIssue = "Proposed restricted notifier produces owner/generation/close-epoch-bound notice after its callback-held owner reference drains"; attribute :>> cannotIssue = "Will eligibility is a past strong-reachability fact, not current irreversibility or permission to free; action is strongly traced and can retain/resurrect testator"; }
 part issuer2 : Issuer { attribute :>> key = "borrow-registry"; attribute :>> anchor = "mem.c:703-826,3969-3986,6845-6850; os_dyn.c:748-769,1047-1053"; attribute :>> existing = "RC register/data/refcount/release primitives; ordinary field mutations, not a new concurrent admission protocol"; attribute :>> mayIssue = "Proposed owner service closes new reserve/commit admission atomically and accounts for prepared reservations, native roots and canonical releases"; attribute :>> cannotIssue = "A prior open read, RC count zero or cancellation request cannot authorize a late borrow or global managed unreachability"; }
 part issuer3 : Issuer { attribute :>> key = "outcome-custodian"; attribute :>> anchor = "os_dyn.c:1047-1053; tcltk.scm:188-194,297-326; runtime/error.ss:67-72"; attribute :>> existing = "Actual external release callbacks and exception control, not a universal operation-settlement ledger"; attribute :>> mayIssue = "Proposed authoritative operation record distinguishes unknown grant, canonical release and rootless pending release acknowledgement"; attribute :>> cannotIssue = "Unknown reply cannot justify retry, erasing responsibility or keeping a self-root until a GC notice that it prevents"; }
 part issuer4 : Issuer { attribute :>> key = "retirement-coordinator"; attribute :>> anchor = "mem.c:684-699,760-778; _io.scm:10003-10014"; attribute :>> existing = "Object freeing/cleanup and port close exist independently; composed old-stream permit does not exist"; attribute :>> mayIssue = "Proposed join checks owner identity, generation, close epoch, coverage, private notice, reservation/borrow drain and settled outcomes before one resource release"; attribute :>> cannotIssue = "GC callback alone cannot issue native resource close, thread-affinity clearance or reuse of an old-generation permit"; }
 part def Gate { attribute key : String; attribute qualified : Boolean; attribute condition : String; }
 part gate0 : Gate { attribute :>> key = "owner-token-coverage"; attribute :>> qualified = false; attribute :>> condition = "Every governed stream-capable alias traces the owner token; no strong reverse monitor/action/control-record edge; arbitrary raw aliases retain legacy ownership"; }
 part gate1 : Gate { attribute :>> key = "private-notifier-proof"; attribute :>> qualified = false; attribute :>> condition = "No strong action capture, publication of testator, user callback, capture in notifier or delayed callback-owned root; will notices are identity-bound and rootless"; }
 part gate2 : Gate { attribute :>> key = "registry-root-closure"; attribute :>> qualified = false; attribute :>> condition = "All participating processor/VM native roots, actual external holders and temporary reservations scanned and accounted; current processor-zero mark_rc is not closure proof"; }
 part gate3 : Gate { attribute :>> key = "admission-linearization"; attribute :>> qualified = false; attribute :>> condition = "Reserve and commit validate the same close generation; root publication precedes exposure; prepared requests rejected after close retain rollback custody"; }
 part gate4 : Gate { attribute :>> key = "unknown-outcome-settlement"; attribute :>> qualified = false; attribute :>> condition = "Canonical registry state settles grant/release without retry; rootless release-ack record cannot keep managed owner alive or be erased before resolution"; }
 part gate5 : Gate { attribute :>> key = "release-refinement"; attribute :>> qualified = false; attribute :>> condition = "Source-to-model reachability and ordering, native reclamation/grace, close affinity and exactly one owner/generation-matched consume remain unqualified"; }
 part def Gain { attribute key : String; attribute avoided : String; attribute added : String; attribute condition : String; }
 part gain0 : Gain { attribute :>> key = "root-lifetime"; attribute :>> avoided = "After canonical external release, no mandatory managed owner root merely to await an acknowledgement"; attribute :>> added = "One stable rootless outcome/tombstone record until acknowledgement settles"; attribute :>> condition = "No Scheme object or resource-capable pointer hidden in the supposedly rootless record; outstanding grants remain rooted"; }
 part gain1 : Gain { attribute :>> key = "admission-work"; attribute :>> avoided = "No new accepted borrow after close; stale open observations cannot enlarge the drain set"; attribute :>> added = "One reserve and one commit revalidation per proposed borrow plus root publication and rollback/outcome records"; attribute :>> condition = "O(B) bookkeeping for B requests and O(outstanding requests + pending notices) storage; no fixed latency or speedup inferred"; }
 part gain2 : Gain { attribute :>> key = "self-retention"; attribute :>> avoided = "Avoid monitor-action/capture/native-root cycles and false releases from uncovered aliases"; attribute :>> added = "Owner-token coverage proof, restricted notifier and generation-qualified permit join"; attribute :>> condition = "Correctness/progress prerequisite, not a numeric throughput claim; genuine live errors/captures can retain resources indefinitely"; }
 part gain3 : Gain { attribute :>> key = "unchanged-baseline"; attribute :>> avoided = "Prior reset and qualified ignored-string opportunities remain separate and are not counted again"; attribute :>> added = "Same semantic/native lifetime support required in modern C and Zig"; attribute :>> condition = "Modern C remains mandatory; no uniquely Zig positive net work proved"; }
 attribute ownerGeneration : Integer = 17;
 attribute actualAdmitted : Boolean = false;
 part def ReleaseWitness { attribute admissionsClosed : Boolean; attribute ownerCoverage : Boolean; attribute privateNotice : Boolean; attribute epochMatches : Boolean; attribute reservations : Integer; attribute borrows : Integer; attribute pending : Integer; attribute requested : Boolean; }
 requirement def ReleaseLaw { subject witness : ReleaseWitness; require constraint { not witness.requested or (witness.admissionsClosed and witness.ownerCoverage and witness.privateNotice and witness.epochMatches and witness.reservations == 0 and witness.borrows == 0 and witness.pending == 0) } }
 part history : GambitAssuranceRouting::ModelNeed { ref part :>> owner = GambitBuildAssurance::scheduler.component; attribute :>> obligationId = "RA-H"; attribute :>> kind = "interleaving"; attribute :>> subjectPath = "models/build/stream_release_authority.qnt"; attribute :>> subjectScope = "stream_release_authority:Test$"; attribute :>> premise = "Finite proposed owner-token, admission, native-root, private notification and grant/release-unknown histories; managed reachability coverage and notifier closure are premises"; }
 part induction : GambitAssuranceRouting::ModelNeed { ref part :>> owner = GambitBuildAssurance::scheduler.component; attribute :>> obligationId = "RA-I"; attribute :>> kind = "induction"; attribute :>> subjectPath = "models/build/StreamReleaseAuthority.lean"; attribute :>> subjectScope = "StreamReleaseAuthority:closedRejects;staleEpochRejects;pinKeepsCapture;actionBackedge;rootlessAck;permitNeedsDrain;pendingBlocks;oneConsume"; attribute :>> premise = "Conditional close/identity, strong-edge implication, rootless-record and permit kernels; no actual collector reachability certificate or C atomic proof"; }
 part source : GambitAssuranceRouting::ModelNeed { ref part :>> owner = GambitBuildAssurance::scheduler.component; attribute :>> obligationId = "RA-S"; attribute :>> kind = "source-refinement"; attribute :>> subjectPath = "dev/architecture/toolchain/stream-release-authority-design.org"; attribute :>> subjectScope = "RA-S:release-issuer-source"; attribute :>> premise = "Current will/RC/exception/callback sources identified; no existing composite credential issuer; alias/token coverage and proposed notifier/registry simulation open"; }
 part platform : GambitAssuranceRouting::ModelNeed { ref part :>> owner = GambitBuildAssurance::scheduler.component; attribute :>> obligationId = "RA-E"; attribute :>> kind = "environment-refinement"; attribute :>> subjectPath = "dev/architecture/toolchain/stream-release-authority-design.org"; attribute :>> subjectScope = "RA-E:release-native-order"; attribute :>> premise = "All-processor root closure, C reserve/commit ordering, pin rollback, notification grace and thread-affine resource cleanup unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SpanStorageHandoff::source; }
}
