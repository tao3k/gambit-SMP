package NotifierRootRetirement {
 private import ScalarValues::*;
 part def RootBoundary { attribute key : String; attribute anchor : String; attribute actualEdge : String; attribute requiredChange : String; }
 part root0 : RootBoundary { attribute :>> key = "argument-and-dispatcher"; attribute :>> anchor = "_kernel.scm:2106-2116"; attribute :>> actualEdge = "testator/action locals survive slot clearing; action result is discarded before void"; attribute :>> requiredChange = "Return is an event; exact descriptor liveness decides remaining roots"; }
 part root1 : RootBoundary { attribute :>> key = "register-bank"; attribute :>> anchor = "mem.c:6511-6523; gambit.h.in:6802-6803,7060-7066"; attribute :>> actualEdge = "mark_registers scans full PSTATE r bank; W_ALL/R_ALL synchronize selected cached machine state"; attribute :>> requiredChange = "Qualified point must exclude testator from scanned bank and any cached value that can be restored; do not erase live unrelated values"; }
 part root2 : RootBoundary { attribute :>> key = "saved-temporaries"; attribute :>> anchor = "gambit.h.in:8059-8084,11623; mem.c:6526-6537"; attribute :>> actualEdge = "GC_RESTORE copies saved value into caller then overwrites saved slot with VOID"; attribute :>> requiredChange = "A cleared saved slot transfers rather than extinguishes the root; require destination liveness and all save/restore paths"; }
 part root3 : RootBoundary { attribute :>> key = "active-and-internal-frames"; attribute :>> anchor = "mem.c:3898-3966; _kernel.scm:1284-1344; _t-c-1.scm:1947-1963,1986-2008"; attribute :>> actualEdge = "RETI/RETN descriptors choose live frame slots; internal returns save/restore GVM registers"; attribute :>> requiredChange = "Bind receipt to generated PointId/FrameSpec and backend/configuration; no receipt inside restorable save region"; }
 part root4 : RootBoundary { attribute :>> key = "captured-frames-and-denv"; attribute :>> anchor = "gambit.h.in:6314-6330,6378-6388,6589-6606,6715-6735; _kernel.scm:3613-3635; mem.c:3667-3895,4096-4145"; attribute :>> actualEdge = "Capture stores frame/denv; continuation-copy shares fields; thread-save retains frame in thread continuation; return/restore installs frames again"; attribute :>> requiredChange = "No exported root-bearing capture in restricted profile, including interrupt/exception/thread paths; dropping one continuation is insufficient"; }
 part root5 : RootBoundary { attribute :>> key = "error-and-winding"; attribute :>> anchor = "runtime/error.ss:37-43,67-72; _thread.scm:4794-4812,4914-4988,5047-5076"; attribute :>> actualEdge = "Gerbil raise may attach continuation; winding runs before/after across exits and reentry"; attribute :>> requiredChange = "Exception or capture permanently taints this dispatch attempt; preserve generic semantics and deny its receipt"; }
 part def Gate { attribute key : String; attribute qualified : Boolean; attribute condition : String; }
 part gate0 : Gate { attribute :>> key = "exact-program-point"; attribute :>> qualified = false; attribute :>> condition = "Actual generated notifier/dispatcher PointId, FrameSpec, configuration and all normal/exceptional edges identified"; }
 part gate1 : Gate { attribute :>> key = "register-save-closure"; attribute :>> qualified = false; attribute :>> condition = "Scanned register bank, cached registers, saved destinations and internal-return restores all accounted"; }
 part gate2 : Gate { attribute :>> key = "capture-effect-closure"; attribute :>> qualified = false; attribute :>> condition = "No root-bearing capture or publication through direct/indirect calls, interrupt, thread-save, denv, handlers or StackTrace"; }
 part gate3 : Gate { attribute :>> key = "retirement-cut"; attribute :>> qualified = false; attribute :>> condition = "Issuer executes after verified last invocation-root use with no future restoration edge; source-to-model simulation required"; }
 part gate4 : Gate { attribute :>> key = "receipt-identity"; attribute :>> qualified = false; attribute :>> condition = "Owner generation, close epoch, dispatch attempt, root-domain epoch and program digest matched; ticket private"; }
 part gate5 : Gate { attribute :>> key = "exception-custody"; attribute :>> qualified = false; attribute :>> condition = "Failed/escaped/unknown attempt cannot issue receipt; error/capture/slot remains under explicit custody without waiting on itself"; }
 part gate6 : Gate { attribute :>> key = "receipt-release-join"; attribute :>> qualified = false; attribute :>> condition = "Rootless receipt publication, duplicate settlement, control-storage grace and ancestor release permit join qualified"; }
 part def Gain { attribute key : String; attribute avoided : String; attribute added : String; attribute condition : String; }
 part gain0 : Gain { attribute :>> key = "dead-root-retention"; attribute :>> avoided = "Eliminate notifier-attributable retention after a certified cut; no forced extra GC assumed"; attribute :>> added = "Compile-time root/effect proof plus point-specific retirement work"; attribute :>> condition = "Retiring K proven-dead root locations costs O(K); no whole-heap walk per notice; K and runtime speed unmeasured"; }
 part gain1 : Gain { attribute :>> key = "repeated-control"; attribute :>> avoided = "One canonical attempt slot prevents replayed notices from repeating action or granting another receipt"; attribute :>> added = "O(W) live slots and constant identity checks per delivery; retry/error custody"; attribute :>> condition = "Root-bearing multi-shot captures stay legal outside restricted profile but cannot qualify this attempt"; }
 part gain2 : Gain { attribute :>> key = "failure-isolation"; attribute :>> avoided = "No false release from after-thunk, slot clear, saved-slot clear or caught exception"; attribute :>> added = "Monotone capture/failure taint and separate returned/root-retired/sealed states"; attribute :>> condition = "No bounded retention or guaranteed notification latency; failed attempts may retain resources indefinitely"; }
 part gain3 : Gain { attribute :>> key = "modern-c-and-zig"; attribute :>> avoided = "Reuse Scheme semantic completion and generated modern-C FrameSpec/PointId contract"; attribute :>> added = "Both languages need identical GC/control/effect, root-map and publication obligations"; attribute :>> condition = "No additional positive Zig net benefit established; avoid a second handwritten runtime or duplicate root maps"; }
 attribute receiptGeneration : Integer = 17;
 attribute actualAdmitted : Boolean = false;
 part def RootRetirementReceipt { attribute ownerIdentity : String; attribute ownerGeneration : Integer; attribute closeEpoch : Integer; attribute dispatchAttempt : Integer; attribute gcTicketIdentity : String; attribute vmIdentity : String; attribute rootDomainEpoch : Integer; attribute programDigest : String; attribute backendConfiguration : String; attribute pointId : String; attribute frameSpecDigest : String; attribute normalReturnWitness : String; attribute restorationClosureWitness : String; }
 part def RetirementEvidence { attribute requested : Boolean; attribute normalReturn : Boolean; attribute rootsAbsent : Boolean; attribute futureRestoreClosed : Boolean; attribute noCapture : Boolean; attribute noFailure : Boolean; attribute matched : Boolean; }
 requirement def RetirementLaw { subject evidence : RetirementEvidence; require constraint { not evidence.requested or (evidence.normalReturn and evidence.rootsAbsent and evidence.futureRestoreClosed and evidence.noCapture and evidence.noFailure and evidence.matched) } }
 part history : GambitAssuranceRouting::ModelNeed { ref part :>> owner = GambitBuildAssurance::scheduler.component; attribute :>> obligationId = "NR-H"; attribute :>> kind = "interleaving"; attribute :>> subjectPath = "models/build/notifier_root_retirement.qnt"; attribute :>> subjectScope = "notifier_root_retirement:Test$"; attribute :>> premise = "Finite argument/register/save/stack/capture/error lifetimes; repeated continuation resumes and delayed receipt controls; actual roots and effect closure assumed"; }
 part induction : GambitAssuranceRouting::ModelNeed { ref part :>> owner = GambitBuildAssurance::scheduler.component; attribute :>> obligationId = "NR-I"; attribute :>> kind = "induction"; attribute :>> subjectPath = "models/build/NotifierRootRetirement.lean"; attribute :>> subjectScope = "NotifierRootRetirement:savedClearTransfers;copyRetains;returnNotRetired;taintSticky;normalNeeded;captureRejects;closedPreserved;matchRequired"; attribute :>> premise = "Eight conditional support/transition kernels; no actual compiler root-map or transitive no-capture proof"; }
 part source : GambitAssuranceRouting::ModelNeed { ref part :>> owner = GambitBuildAssurance::scheduler.component; attribute :>> obligationId = "NR-S"; attribute :>> kind = "source-refinement"; attribute :>> subjectPath = "dev/architecture/toolchain/notifier-root-retirement-design.org"; attribute :>> subjectScope = "NR-S:root-retirement-source"; attribute :>> premise = "Consumers and transfers derived; exact generated notifier points, complete effect/restore closure and source simulation remain open"; }
 part platform : GambitAssuranceRouting::ModelNeed { ref part :>> owner = GambitBuildAssurance::scheduler.component; attribute :>> obligationId = "NR-E"; attribute :>> kind = "environment-refinement"; attribute :>> subjectPath = "dev/architecture/toolchain/notifier-root-retirement-design.org"; attribute :>> subjectScope = "NR-E:root-retirement-native"; attribute :>> premise = "GC-safe cut, ABI/register/save/interrupt interactions, identity publication and control-storage grace unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = OwnerNotifierClosure::source; }
}
