package SpecializerProviderSemantics {
 private import ScalarValues::*;
 part def CaseSpec { attribute key : String; attribute anchor : String; attribute captures : String; attribute selection : String; attribute condition : String; }
 part case0 : CaseSpec { attribute :>> key = "safe-boolean"; attribute :>> anchor = "_prims.scm:1798-1801,1880"; attribute :>> captures = "boolean? self and target-local ##boolean? captured during setup"; attribute :>> selection = "Always return captured ##boolean?; env/args ignored by this selector"; attribute :>> condition = "Do not add invocation-time global lookup or reinterpret safe as a predicate on env"; }
 part case1 : CaseSpec { attribute :>> key = "unsafe-boolean"; attribute :>> anchor = "_prims.scm:1803-1806,1883"; attribute :>> captures = "boolean=? self and ##boolean=? captured during setup"; attribute :>> selection = "not safe?(env) chooses selected; otherwise self"; attribute :>> condition = "Default safe is true; preserve actual lexical declaration environment"; }
 part case2 : CaseSpec { attribute :>> key = "arith-plus"; attribute :>> anchor = "_prims.scm:1818-1835,1889"; attribute :>> captures = "+ self, proc-name +, fx+, fl+, ##+"; attribute :>> selection = "Read named arith first; unsafe unequal self takes priority over fixnum/flonum; otherwise choose mode or self"; attribute :>> condition = "Injective relocation preserves unsafe==self test; same proc-name and ordered env declarations"; }
 part case3 : CaseSpec { attribute :>> key = "arith-internal-plus"; attribute :>> anchor = "_prims.scm:1890"; attribute :>> captures = "##+ self, ##fx+, ##fl+; absent unsafe argument means self"; attribute :>> selection = "Even under not safe, fall through to arithmetic when unsafe aliases self"; attribute :>> condition = "Do not represent absent unsafe as a distinct sentinel primitive"; }
 part case4 : CaseSpec { attribute :>> key = "arith-division"; attribute :>> anchor = "_prims.scm:1893-1894"; attribute :>> captures = "/ has absent fix name, fl/, ##/; ##/ has absent fix and unsafe"; attribute :>> selection = "Absent fix selects self; named lookup miss is #f, not self"; attribute :>> condition = "Managed completeness may reject a missing name but must not silently change selector semantics"; }
 part def ContractSpec { attribute key : String; attribute anchor : String; attribute required : String; attribute gap : String; }
 part contract0 : ContractSpec { attribute :>> key = "lookup-commutation"; attribute :>> anchor = "_back.scm:288-301; _prims.scm:1790-1796"; attribute :>> required = "New target lookup(name) = lifted relocation(old lookup(name)); setup resolves captures once"; attribute :>> gap = "Arbitrary dynamically replaced lookup callbacks not qualified"; }
 part contract1 : ContractSpec { attribute :>> key = "environment"; attribute :>> anchor = "_env.scm:335-343; _ptree1.scm:574-575; _back.scm:579-580"; attribute :>> required = "safe defaults true; arith defaults generic; first matching named/universal declaration wins; reuse qualified persistent declaration views, not the entire shared mutable env graph"; attribute :>> gap = "Full Gerbil emission to actual Gambit env equivalence remains open"; }
 part contract2 : ContractSpec { attribute :>> key = "private-binding"; attribute :>> anchor = "_gvm.scm:165-197; _t-c-1.scm:295-303"; attribute :>> required = "One primitive table/relocation domain per workspace; self and alternatives resolve locally"; attribute :>> gap = "Inline/provider emission globals and full alias closure remain AR-S prerequisites"; }
 part contract3 : ContractSpec { attribute :>> key = "observation"; attribute :>> anchor = "iter/macros.ss:124-150; compiler/driver.ss:787-797,963-978"; attribute :>> required = "Preserve declaration scope, binding equality/distinction, generated reader origin and admitted failure/status surface"; attribute :>> gap = "Instrumented read trace is a service observer premise, not an observed native compilation trace"; }
 part def GainSpec { attribute key : String; attribute avoided : String; attribute added : String; attribute condition : String; }
 part gain0 : GainSpec { attribute :>> key = "recipe-sharing"; attribute :>> avoided = "Repeated immutable metadata preparation and admitted frontend work"; attribute :>> added = "Capture lookup, per-workspace primitive objects/providers and relocation"; attribute :>> condition = "Savings must exceed freeze + reconstruction + validation; no eliminated per-call environment choice is assumed"; }
 part gain1 : GainSpec { attribute :>> key = "parallel-selectors"; attribute :>> avoided = "Global lookup/target state serialization after complete ownership migration"; attribute :>> added = "Private tables, declaration views, callback/root custody and workspace memory"; attribute :>> condition = "Removed critical-path delay exceeds added context/coordination cost; no claimed speed ratio"; }
 part gain2 : GainSpec { attribute :>> key = "retirement"; attribute :>> avoided = "Global captured primitive references and redundant serialization after all consumers migrate"; attribute :>> added = "Generated recipe schemas, source-equivalence and environment/observer proof maintenance"; attribute :>> condition = "Compile and link plus all provider variants migrate; three selected families do not qualify every primitive"; }
 part def RefinementSpec { attribute key : String; attribute qntScope : String; attribute leanScope : String; attribute sourceDuty : String; }
 part refinement0 : RefinementSpec { attribute :>> key = "selection"; attribute :>> qntScope = "instantiate;invoke"; attribute :>> leanScope = "safeTransport;unsafeTransport;arithTransport"; attribute :>> sourceDuty = "Source factory and recipe evaluation refine modeled branches under equivalent declaration environments"; }
 part refinement1 : RefinementSpec { attribute :>> key = "lookup"; attribute :>> qntScope = "configureMissing;configureNoUnsafe"; attribute :>> leanScope = "captureTransport;missingDifferent"; attribute :>> sourceDuty = "Lookup miss remains #f; absent optional name means self; constructor effects/failures preserved"; }
 part refinement2 : RefinementSpec { attribute :>> key = "private-observer"; attribute :>> qntScope = "invoke;changeOrigin"; attribute :>> leanScope = "relocationInjective;namedDeclarations;declarationOrder"; attribute :>> sourceDuty = "Injective whole-graph map, per-name declaration view and generated source/status equivalence"; }
 part refinement3 : RefinementSpec { attribute :>> key = "net-benefit"; attribute :>> qntScope = "settleOutcome;releaseContext"; attribute :>> leanScope = "costPositive"; attribute :>> sourceDuty = "Truthful completion/root closure and actual work/span/memory evidence remain external premises"; }
 part def GateSpec { attribute key : String; attribute qualified : Boolean; attribute condition : String; }
 part gate0 : GateSpec { attribute :>> key = "lookup-closure"; attribute :>> qualified = false; attribute :>> condition = "Target-local capture lookup commutes, including missing and optional names"; }
 part gate1 : GateSpec { attribute :>> key = "provider-semantics"; attribute :>> qualified = false; attribute :>> condition = "All selected factory branches and setup effects refine the recipes"; }
 part gate2 : GateSpec { attribute :>> key = "environment-fidelity"; attribute :>> qualified = false; attribute :>> condition = "Per-primitive named declarations, order/defaults and safety view agree"; }
 part gate3 : GateSpec { attribute :>> key = "private-binding"; attribute :>> qualified = false; attribute :>> condition = "Mutable primitive/reference/provider closure is private and coherent"; }
 part gate4 : GateSpec { attribute :>> key = "observer-fidelity"; attribute :>> qualified = false; attribute :>> condition = "Identity, generated origin, diagnostics/status and required read observations agree"; }
 part gate5 : GateSpec { attribute :>> key = "caller-retirement"; attribute :>> qualified = false; attribute :>> condition = "All relevant compile/link/provider consumers migrated; AR-S remains prerequisite"; }
 part gate6 : GateSpec { attribute :>> key = "platform-benefit"; attribute :>> qualified = false; attribute :>> condition = "Native GC/FFI/SMP and measured work/span/memory not qualified"; }
 attribute workspaceCount : Integer = 2;
 attribute actualAdmitted : Boolean = false;
 part history : GambitAssuranceRouting::ModelNeed { ref part :>> owner = GambitBuildAssurance::planner.component; attribute :>> obligationId = "SP-H"; attribute :>> kind = "interleaving"; attribute :>> subjectPath = "models/build/specializer_provider_semantics.qnt"; attribute :>> subjectScope = "specializer_provider_semantics:Test$"; attribute :>> premise = "Selected specializer transport under injective relocation and equivalent lookup/declarations; actual source/platform closure open"; }
 part induction : GambitAssuranceRouting::ModelNeed { ref part :>> owner = GambitBuildAssurance::planner.component; attribute :>> obligationId = "SP-I"; attribute :>> kind = "induction"; attribute :>> subjectPath = "models/build/SpecializerProviderSemantics.lean"; attribute :>> subjectScope = "SpecializerProviderSemantics:safeTransport;unsafeTransport;arithTransport;captureTransport;missingDifferent;relocationInjective;namedDeclarations;declarationOrder;costPositive"; attribute :>> premise = "Selected specializer transport under injective relocation and equivalent lookup/declarations; actual source/platform closure open"; }
 part source : GambitAssuranceRouting::ModelNeed { ref part :>> owner = GambitBuildAssurance::planner.component; attribute :>> obligationId = "SP-S"; attribute :>> kind = "source-refinement"; attribute :>> subjectPath = "dev/architecture/toolchain/specializer-provider-semantics-design.org"; attribute :>> subjectScope = "SP-S:source"; attribute :>> premise = "Selected specializer transport under injective relocation and equivalent lookup/declarations; actual source/platform closure open"; }
 part platform : GambitAssuranceRouting::ModelNeed { ref part :>> owner = GambitBuildAssurance::planner.component; attribute :>> obligationId = "SP-E"; attribute :>> kind = "environment-refinement"; attribute :>> subjectPath = "dev/architecture/toolchain/specializer-provider-semantics-design.org"; attribute :>> subjectScope = "SP-E:platform"; attribute :>> premise = "Selected specializer transport under injective relocation and equivalent lookup/declarations; actual source/platform closure open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = AliasWorkspaceReconstruction::source; }
}
