package FfiScanReadyHandoff {
 private import ScalarValues::*;
 part def CallerSpec { attribute key : String; attribute anchor : String; attribute condition : String; }
 part caller0 : CallerSpec { attribute :>> key = "native-rc"; attribute :>> anchor = "mem.c:703-825,3969-3986,6845-6850; os_dyn.c:764-769"; attribute :>> condition = "alloc_rc registers current PSTATE before payload assignment; native storage alone is not a nonzero-processor root; proposed VM domain must own both existing RC slot and provisional frame"; }
 part caller1 : CallerSpec { attribute :>> key = "marker-allocation"; attribute :>> anchor = "c_intf.c:6511-6546; mem.c:1789-1814,1647"; attribute :>> condition = "Explicit proc must be rooted before make_vector can enter GC; initializing marker with #f obeys its constructor contract but does not protect proc_or_false"; }
 part caller2 : CallerSpec { attribute :>> key = "gc-join"; attribute :>> anchor = "setup.c:1182-1198,1028-1029,1065-1105"; attribute :>> condition = "Allocator GC is an all-processors sync operation; a preparer waiting inside it cannot be a prerequisite for collector root readiness"; }
 part caller3 : CallerSpec { attribute :>> key = "exception-exit"; attribute :>> anchor = "setup.c:3355-3389,853-866,3408-3417; gambit.h.in:10043-10059"; attribute :>> condition = "call can rethrow before normal marker cleanup; explicit completion guards must catch permitted runtime unwind, keep custody, close marker and only then propagate"; }
 part caller4 : CallerSpec { attribute :>> key = "native-lifetime"; attribute :>> anchor = "mem.c:760-791,684-699,4928-4934; tcltk.scm:150,193-194,297-337"; attribute :>> condition = "RC refcount does not protect against cleanup_rc freeing a whole chain; storage pin, owner-exit veto/handoff and final reader drain are distinct from GC scan readiness"; }
 part def ProtocolSpec { attribute key : String; attribute anchor : String; attribute condition : String; }
 part protocol0 : ProtocolSpec { attribute :>> key = "reserve-before-borrow"; attribute :>> anchor = "gambit.h.in:8059-8084; mem.c:703-719"; attribute :>> condition = "Reserve stable native root-frame storage before dropping any existing root; failure leaves origin custody; reject incoming movable C value without an admissible source root"; }
 part protocol1 : ProtocolSpec { attribute :>> key = "publish-before-join"; attribute :>> anchor = "mem.c:816-825; c_intf.c:6524-6538"; attribute :>> condition = "Accepted intent initializes root cells without allocation and release-publishes them through VM enrollment gate; root-frame publication is not commit of the target RC payload"; }
 part protocol2 : ProtocolSpec { attribute :>> key = "reclassify-lease"; attribute :>> anchor = "setup.c:1196; mem.c:1647"; attribute :>> condition = "Before requesting allocating GC, convert mutable-preparation lease to scan-ready custody and stop the attached context; collector waits for preparation closure and parked participants, not operation return"; }
 part protocol3 : ProtocolSpec { attribute :>> key = "scan-and-reload"; attribute :>> anchor = "mem.c:3984,6522,6537,6800"; attribute :>> condition = "Collector scans all admitted VM domains including processor 1 and writes moved values back; owner reloads through current-epoch cell before marker initialization or RC commit"; }
 part protocol4 : ProtocolSpec { attribute :>> key = "guard-and-retire"; attribute :>> anchor = "setup.c:3383-3385; c_intf.c:6555-6561"; attribute :>> condition = "Failure and supported unwind retain frame until acknowledged terminal outcome, native/reader pins and nested children settle; unknown result is neither quiescence nor permission to free"; }
 part def RouteSpec { attribute key : String; attribute anchor : String; attribute qntAction : String; attribute leanLemma : String; attribute condition : String; }
 part route0 : RouteSpec { attribute :>> key = "registration"; attribute :>> anchor = "mem.c:723-825; gambit.h.in:8059-8084"; attribute :>> qntAction = "publishRoot"; attribute :>> leanLemma = "publicationPreserves"; attribute :>> condition = "VM intent membership and original-root-to-frame coverage must linearize with collector freeze"; }
 part route1 : RouteSpec { attribute :>> key = "custody"; attribute :>> anchor = "setup.c:1182-1198"; attribute :>> qntAction = "handoff"; attribute :>> leanLemma = "handoffRetainsCustody"; attribute :>> condition = "Handoff removes GC-blocking preparation while retaining root and storage ownership; operation can remain incomplete"; }
 part route2 : RouteSpec { attribute :>> key = "coverage"; attribute :>> anchor = "mem.c:3969-3986,6845-6850"; attribute :>> qntAction = "scanRoot"; attribute :>> leanLemma = "reloadAfterMove"; attribute :>> condition = "Processor ownership must not exclude temporary frame cells or registered RC payload slots from VM scan"; }
 part route3 : RouteSpec { attribute :>> key = "publication"; attribute :>> anchor = "c_intf.c:6524-6544"; attribute :>> qntAction = "resume"; attribute :>> leanLemma = "staleLocalRejected"; attribute :>> condition = "Root reload follows GC completion before use; old copied Scheme words cannot initialize a marker after relocation"; }
 part route4 : RouteSpec { attribute :>> key = "retirement"; attribute :>> anchor = "setup.c:3383-3385; mem.c:4933-4934"; attribute :>> qntAction = "retireFrame"; attribute :>> leanLemma = "unknownRetainsCustody"; attribute :>> condition = "Completion guard, readers, storage pins and nested callback identity must close before descriptor withdrawal"; }
 part def GainSpec { attribute key : String; attribute avoided : String; attribute added : String; attribute condition : String; }
 part gain0 : GainSpec { attribute :>> key = "cycle-removal"; attribute :>> avoided = "Waiting for the same allocating writer to return before its GC can start"; attribute :>> added = "Nonallocating preparation, published frame, context park and explicit resume"; attribute :>> condition = "Finite model reaches collector freeze while operation outcome is pending; native lock/progress refinement remains open"; }
 part gain1 : GainSpec { attribute :>> key = "root-reuse"; attribute :>> avoided = "Repeated reconstruction/copying of a temporary root set on each GC; redundant per-copy publication counters if lifetime coverage already holds"; attribute :>> added = "One activation frame with k traceable slots, per-GC slot visitation, enrollment and retirement metadata"; attribute :>> condition = "O(k) retained slots per live activation; reuse of frame does not eliminate tracing or root scanning"; }
 part gain2 : GainSpec { attribute :>> key = "modern-c"; attribute :>> avoided = "Second-language ownership/exception bridge is unnecessary for this contract"; attribute :>> added = "Modern C adapters, generated explicit guards, VM root-domain scan and cleanup coordination"; attribute :>> condition = "C can implement all required mechanisms; neither Zig defer nor a reference count alone handles Gambit nonlocal unwind or whole-PSTATE cleanup"; }
 part def RefinementSpec { attribute key : String; attribute qntScope : String; attribute leanScope : String; attribute sourceDuty : String; }
 part refinement0 : RefinementSpec { attribute :>> key = "incoming"; attribute :>> qntScope = "reserve;reserveFailure;beginIntent;abortPreparation;publishRoot;releaseSource"; attribute :>> leanScope = "publicationPreserves;releaseSourcePreserves"; attribute :>> sourceDuty = "Prove source root validity before first safepoint, nonallocating frame initialization, accepted-intent linearization and failure ownership"; }
 part refinement1 : RefinementSpec { attribute :>> key = "gc-handoff"; attribute :>> qntScope = "handoff;requestGC;closeAdmission;freeze;scanRoot;scanRcDomain;finishGC;resume;parkAgain"; attribute :>> leanScope = "handoffRetainsCustody;noReturnNeeded;preparingBlocks;reloadAfterMove;staleLocalRejected;registrationAloneInsufficient"; attribute :>> sourceDuty = "Compose per-context parking with real sync-op execution and full participant roster; all-owner physical root scan and C publication order remain changes to prove"; }
 part refinement2 : RefinementSpec { attribute :>> key = "exit"; attribute :>> qntScope = "allocateMarker;completeMarker;commitRc;failOp;unwindOp;markUnknown;settleOutcome;retryDelivery;releasePin;retireFrame"; attribute :>> leanScope = "unknownNotQuiescence;readerBlocksRetirement;unknownRetainsCustody;nestedBlocksParent;retryIsNotReexecution"; attribute :>> sourceDuty = "Separate known runtime unwind from uncooperative foreign exits; commit outcome and root transfer are recorded before delivery; multi-shot continuation receives fresh activation identity"; }
 part refinement3 : RefinementSpec { attribute :>> key = "cost"; attribute :>> qntScope = "beginReader;endReader"; attribute :>> leanScope = "netBenefit"; attribute :>> sourceDuty = "Storage-reader pin is not permission for raw concurrent Scheme-value reads; bound registration and tracing costs without person-day or performance claims"; }
 part def PriorSpec { attribute key : String; attribute path : String; attribute invariant : String; attribute qntAction : String; attribute leanLemma : String; attribute condition : String; }
 part prior0 : PriorSpec { attribute :>> key = "strong-receipt"; attribute :>> path = "models/build/root_producer_census.qnt"; attribute :>> invariant = "safe"; attribute :>> qntAction = "handoff"; attribute :>> leanLemma = "handoffRetainsCustody"; attribute :>> condition = "Refines the prior writerGcCycle refusal into a proposed scan-ready handoff; actual product refinement remains open"; }
 part prior1 : PriorSpec { attribute :>> key = "scan-count"; attribute :>> path = "models/gambit/gc_scan_termination.qnt"; attribute :>> invariant = "safe"; attribute :>> qntAction = "requestGC"; attribute :>> leanLemma = "preparingBlocks"; attribute :>> condition = "Root preparation ownership is distinct from active collector worker credit and all-processors sync-op participation"; }
 part prior2 : PriorSpec { attribute :>> key = "work-closure"; attribute :>> path = "models/gambit/gc_work_closure.qnt"; attribute :>> invariant = "terminationSafe"; attribute :>> qntAction = "scanRcDomain"; attribute :>> leanLemma = "registrationAloneInsufficient"; attribute :>> condition = "GC payload closure still needs root-domain coverage; nonzero RC scan is a required runtime change"; }
 part def GateSpec { attribute key : String; attribute qualified : Boolean; attribute condition : String; }
 part gate0 : GateSpec { attribute :>> key = "producer-closure"; attribute :>> qualified = false; attribute :>> condition = "Incoming roots, provisional frames and permanent RC/still adapters require complete source and generated-map coverage"; }
 part gate1 : GateSpec { attribute :>> key = "vm-ownership"; attribute :>> qualified = false; attribute :>> condition = "Stable native frame/RC storage must outlive PSTATE cleanup and all reader/borrow pins; real handoff remains unimplemented"; }
 part gate2 : GateSpec { attribute :>> key = "gc-seal"; attribute :>> qualified = false; attribute :>> condition = "No allocation or callback in mutable preparation; parked contexts must still execute or validly delegate their sync-op participant role"; }
 part gate3 : GateSpec { attribute :>> key = "scan-coverage"; attribute :>> qualified = false; attribute :>> condition = "Nonzero RC scan and VM provisional-frame adapter are proposed; current processor-zero-only scan cannot qualify them"; }
 part gate4 : GateSpec { attribute :>> key = "retirement"; attribute :>> qualified = false; attribute :>> condition = "All runtime throw/catch, nested activation, marker invalidation and unknown-result custody paths need source refinement"; }
 part gate5 : GateSpec { attribute :>> key = "source-replacement"; attribute :>> qualified = false; attribute :>> condition = "New completion guards, gate/enrollment and root descriptors have no runtime implementation or native acceptance"; }
 part gate6 : GateSpec { attribute :>> key = "platform"; attribute :>> qualified = false; attribute :>> condition = "C release/acquire, locks, relocation writeback, signal/native ingress and host attestation are not qualified"; }
 part def CensusSpec { attribute key : String; attribute anchor : String; attribute condition : String; attribute status : String; attribute qntAction : String; attribute leanLemma : String; }
 part census0 : CensusSpec { attribute :>> key = "incoming-root"; attribute :>> anchor = "mem.c:1743-1751,1778-1786; gambit.h.in:8059-8084"; attribute :>> condition = "Origin must remain in a valid generated/saved/registered/nonmoving root until frame publication; arbitrary raw movable C input is rejected"; attribute :>> status = "source-contract-open"; attribute :>> qntAction = "beginIntent"; attribute :>> leanLemma = "publicationPreserves"; }
 part census1 : CensusSpec { attribute :>> key = "descriptor"; attribute :>> anchor = "mem.c:703-719"; attribute :>> condition = "Native allocation may fail before taking over custody; initialize descriptor and cells before publication; no GC allocation in preparing region"; attribute :>> status = "proposed-stable-arena"; attribute :>> qntAction = "reserveFailure"; attribute :>> leanLemma = "releaseSourcePreserves"; }
 part census2 : CensusSpec { attribute :>> key = "intent"; attribute :>> anchor = "mem.c:723-754"; attribute :>> condition = "Accepted operation gets stable VM/owner/domain/activation identity before admission cutoff; an old accepted preparation may finish publishing after cutoff"; attribute :>> status = "proposed-enrollment-gate"; attribute :>> qntAction = "beginIntent"; attribute :>> leanLemma = "preparingBlocks"; }
 part census3 : CensusSpec { attribute :>> key = "rc-payload"; attribute :>> anchor = "mem.c:816-825,3969-3986,6845-6850"; attribute :>> condition = "Provisional candidate and existing committed RC payload are separate scan slots; registration on processor 1 cannot rely on processor-zero-only mark_rc"; attribute :>> status = "current-coverage-gap"; attribute :>> qntAction = "scanRcDomain"; attribute :>> leanLemma = "registrationAloneInsufficient"; }
 part census4 : CensusSpec { attribute :>> key = "publication"; attribute :>> anchor = "c_intf.c:6524-6538"; attribute :>> condition = "Fully initialized mutable root cells become collector-visible before dropping origin custody; descriptor publication is not application commit"; attribute :>> status = "C-memory-order-open"; attribute :>> qntAction = "publishRoot"; attribute :>> leanLemma = "publicationPreserves"; }
 part census5 : CensusSpec { attribute :>> key = "lease-conversion"; attribute :>> anchor = "setup.c:1196; mem.c:1647"; attribute :>> condition = "Mutable preparation no longer blocks GC once scannable frame and stop record are accepted; storage pin remains owned without excluding scanner writeback"; attribute :>> status = "conditional-model-closed"; attribute :>> qntAction = "handoff"; attribute :>> leanLemma = "handoffRetainsCustody"; }
 part census6 : CensusSpec { attribute :>> key = "participant"; attribute :>> anchor = "setup.c:1028-1029,1068-1099"; attribute :>> condition = "Park means no root mutation, not an OS wait that prevents the processor from running the selected GC sync operation"; attribute :>> status = "source-participant-refinement-open"; attribute :>> qntAction = "freeze"; attribute :>> leanLemma = "preparingBlocks"; }
 part census7 : CensusSpec { attribute :>> key = "scan-root"; attribute :>> anchor = "mem.c:3984,6522,6537"; attribute :>> condition = "Collector uses admitted VM adapters including nonzero owner and rewrites all moved slot values; marker still-body scan composes with base root model"; attribute :>> status = "source-adapter-open"; attribute :>> qntAction = "scanRoot"; attribute :>> leanLemma = "reloadAfterMove"; }
 part census8 : CensusSpec { attribute :>> key = "reload"; attribute :>> anchor = "c_intf.c:6535-6544"; attribute :>> condition = "Resume acquire-observes GC completion and reloads cell; rejects stale epoch/generation or stale C local before initializing marker"; attribute :>> status = "conditional-model-closed"; attribute :>> qntAction = "resume"; attribute :>> leanLemma = "staleLocalRejected"; }
 part census9 : CensusSpec { attribute :>> key = "marker"; attribute :>> anchor = "c_intf.c:6511-6561; setup.c:3338-3353"; attribute :>> condition = "Marker allocation follows handoff; initial #f body then current rooted proc; transfer accepted only with initialized externally held still marker"; attribute :>> status = "source-guard-open"; attribute :>> qntAction = "allocateMarker"; attribute :>> leanLemma = "reloadAfterMove"; }
 part census10 : CensusSpec { attribute :>> key = "outcome"; attribute :>> anchor = "setup.c:3383-3385,853-866"; attribute :>> condition = "Committed receipt and known terminal guard are distinct from response delivery; unknown running operation must still park before a later GC"; attribute :>> status = "conditional-model-closed"; attribute :>> qntAction = "markUnknown"; attribute :>> leanLemma = "unknownNotQuiescence"; }
 part census11 : CensusSpec { attribute :>> key = "continuation"; attribute :>> anchor = "setup.c:3295-3309; c_intf.c:6560"; attribute :>> condition = "Root reachability does not revive a killed C activation; restored continuation cannot reuse retired frame capability; new execution receives new operation identity"; attribute :>> status = "multi-shot-refinement-open"; attribute :>> qntAction = "retryDelivery"; attribute :>> leanLemma = "retryIsNotReexecution"; }
 part def SettleSpec { attribute key : String; attribute anchor : String; attribute condition : String; attribute status : String; attribute qntAction : String; attribute leanLemma : String; }
 part settle0 : SettleSpec { attribute :>> key = "origin-transfer"; attribute :>> anchor = "gambit.h.in:8059-8084; c_intf.c:6530"; attribute :>> condition = "Do not withdraw origin before a collector-visible root frame has custody"; attribute :>> status = "conditional-model-closed"; attribute :>> qntAction = "releaseSource"; attribute :>> leanLemma = "releaseSourcePreserves"; }
 part settle1 : SettleSpec { attribute :>> key = "preparation"; attribute :>> anchor = "setup.c:1182-1198"; attribute :>> condition = "Preparation must terminate without allocating; acknowledged abort preserves original root, unknown preparation remains blocking"; attribute :>> status = "nonallocation-proof-open"; attribute :>> qntAction = "abortPreparation"; attribute :>> leanLemma = "preparingBlocks"; }
 part settle2 : SettleSpec { attribute :>> key = "gc-join"; attribute :>> anchor = "setup.c:1028-1029,1068-1099"; attribute :>> condition = "All live activations parked or safely delegated before freeze; collector never waits for operation completion"; attribute :>> status = "conditional-model-closed"; attribute :>> qntAction = "freeze"; attribute :>> leanLemma = "noReturnNeeded"; }
 part settle3 : SettleSpec { attribute :>> key = "marker-exit"; attribute :>> anchor = "setup.c:3383-3385; c_intf.c:6555-6561"; attribute :>> condition = "Guard catches admitted runtime unwind, invalidates marker, records error, retains frame until cleanup is known"; attribute :>> status = "source-catcher-open"; attribute :>> qntAction = "unwindOp"; attribute :>> leanLemma = "unknownRetainsCustody"; }
 part settle4 : SettleSpec { attribute :>> key = "native-pin"; attribute :>> anchor = "mem.c:760-777,684-699,4934"; attribute :>> condition = "Native pin prevents unlink/free through ordinary release and whole-processor cleanup; it is not a GC-exclusion lease"; attribute :>> status = "source-cleanup-interception-open"; attribute :>> qntAction = "releasePin"; attribute :>> leanLemma = "readerBlocksRetirement"; }
 part settle5 : SettleSpec { attribute :>> key = "nested-child"; attribute :>> anchor = "setup.c:3295-3309"; attribute :>> condition = "Parent descriptor remains while child activation is live; no stack address resurrection on repeated continuation restore"; attribute :>> status = "conditional-model-closed"; attribute :>> qntAction = "retireFrame"; attribute :>> leanLemma = "nestedBlocksParent"; }
 part settle6 : SettleSpec { attribute :>> key = "reader-drain"; attribute :>> anchor = "mem.c:3981-3985; c_intf.c:6536"; attribute :>> condition = "Close new readers and drain accepted metadata/storage pins before withdrawal; raw value readers require attached-context safepoints"; attribute :>> status = "C-memory-order-open"; attribute :>> qntAction = "endReader"; attribute :>> leanLemma = "readerBlocksRetirement"; }
 attribute workspaceCount : Integer = 2;
 attribute operationCount : Integer = 2;
 attribute actualAdmitted : Boolean = false;
 part history : GambitAssuranceRouting::ModelNeed { ref part :>> owner = GambitBuildAssurance::planner.component; attribute :>> obligationId = "FSH-H"; attribute :>> kind = "interleaving"; attribute :>> subjectPath = "models/build/ffi_scan_ready_handoff.qnt"; attribute :>> subjectScope = "ffi_scan_ready_handoff:Test$"; attribute :>> premise = "Conditional modern C root handoff, not source/native qualification; full root registry, unwind, participant and C memory-model refinement remain open"; }
 part induction : GambitAssuranceRouting::ModelNeed { ref part :>> owner = GambitBuildAssurance::planner.component; attribute :>> obligationId = "FSH-I"; attribute :>> kind = "induction"; attribute :>> subjectPath = "models/build/FfiScanReadyHandoff.lean"; attribute :>> subjectScope = "FfiScanReadyHandoff:publicationPreserves;releaseSourcePreserves;handoffRetainsCustody;noReturnNeeded;preparingBlocks;unknownNotQuiescence;reloadAfterMove;staleLocalRejected;readerBlocksRetirement;unknownRetainsCustody;nestedBlocksParent;registrationAloneInsufficient;retryIsNotReexecution;netBenefit"; attribute :>> premise = "Conditional modern C root handoff, not source/native qualification; full root registry, unwind, participant and C memory-model refinement remain open"; }
 part source : GambitAssuranceRouting::ModelNeed { ref part :>> owner = GambitBuildAssurance::planner.component; attribute :>> obligationId = "FSH-S"; attribute :>> kind = "source-refinement"; attribute :>> subjectPath = "dev/architecture/toolchain/ffi-scan-ready-handoff-design.org"; attribute :>> subjectScope = "FSH-S:source"; attribute :>> premise = "Conditional modern C root handoff, not source/native qualification; full root registry, unwind, participant and C memory-model refinement remain open"; }
 part platform : GambitAssuranceRouting::ModelNeed { ref part :>> owner = GambitBuildAssurance::planner.component; attribute :>> obligationId = "FSH-E"; attribute :>> kind = "environment-refinement"; attribute :>> subjectPath = "dev/architecture/toolchain/ffi-scan-ready-handoff-design.org"; attribute :>> subjectScope = "FSH-E:platform"; attribute :>> premise = "Conditional modern C root handoff, not source/native qualification; full root registry, unwind, participant and C memory-model refinement remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = RootProducerCensus::source; }
}
