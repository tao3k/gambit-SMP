package StorageHandoff {
 private import ScalarValues::*;
 part def CallerSpec { attribute key : String; attribute anchor : String; attribute condition : String; }
 part caller0 : CallerSpec { attribute :>> key = "still-allocator"; attribute :>> anchor = "mem.c:1556-1690,6800-6805"; attribute :>> condition = "PSTATE still chain owns physical blocks; charged and deferred words are distinct; pending allocation reservation must settle before seal"; }
 part caller1 : CallerSpec { attribute :>> key = "c-closure"; attribute :>> anchor = "os_dyn.c:744-769,1047-1058; c_intf.c:1731-1738"; attribute :>> condition = "Native RC code holds Scheme proc; relocation root and executable allocation lifetime are separate; no assumption that proc is still"; }
 part caller2 : CallerSpec { attribute :>> key = "tcl-client"; attribute :>> anchor = "examples/tcltk/tcltk.scm:136-194,297-338"; attribute :>> condition = "Tcl holds RC client data plus still vector; callback result string has separate Tcl release_string lifetime; failed creation needs qualified ownership evidence"; }
 part caller3 : CallerSpec { attribute :>> key = "foreign-release"; attribute :>> anchor = "c_intf.c:1683-1710,5156-5190; mem.c:4397-4406,4437-4448"; attribute :>> condition = "Foreign wrapper release clears callback/pointer before invocation; collector frees wrapper without propagating returned error; new asynchronous duty requires explicit settlement"; }
 part caller4 : CallerSpec { attribute :>> key = "exit-and-census"; attribute :>> anchor = "setup.c:918-978; mem.c:4928-4934,6268-6291"; attribute :>> condition = "Old cleanup frees still chain then native RC headers; live census enumerates current processors only; VM arena must join scan and capacity census"; }
 part def ProtocolSpec { attribute key : String; attribute anchor : String; attribute condition : String; }
 part protocol0 : ProtocolSpec { attribute :>> key = "close-and-seal"; attribute :>> anchor = "mem.c:1571-1684,4210-4247; proposed admission cut"; attribute :>> condition = "Close native writers and allocation; drain raw borrows and accepted operations; exact whole arena membership, generation and GC epoch; roots and release lane admitted"; }
 part protocol1 : ProtocolSpec { attribute :>> key = "atomic-authority"; attribute :>> anchor = "mem.c:723-739,1681-1684; proposed VM arena authority"; attribute :>> condition = "Publish destination storage/RC membership, accounting delta, release duty and exact receipt together; source cleanup loses authority at same commit"; }
 part protocol2 : ProtocolSpec { attribute :>> key = "unknown-outcome"; attribute :>> anchor = "setup.c:973-978; proposed durable receipt lookup"; attribute :>> condition = "Precommit source retains custody; postcommit VM authority retains it; unknown ack blocks reclaim, not necessarily exit; repeated reclaim preserves monotonic retired identities"; }
 part protocol3 : ProtocolSpec { attribute :>> key = "gc-and-exit"; attribute :>> anchor = "mem.c:4210-4247,6268-6291,7002-7038; setup.c:930-933"; attribute :>> condition = "Serialize handoff with epoch freeze; invalidate stale seal after GC; destination scanner/census remains after processor leaves; join is not transfer"; }
 part protocol4 : ProtocolSpec { attribute :>> key = "release-and-retire"; attribute :>> anchor = "c_intf.c:1699-1707; examples/tcltk/tcltk.scm:188-194"; attribute :>> condition = "Lease/root survival differs from raw pin; destructor owner outlives creator; drain callbacks before final release; error or unknown retains separate task custody without blind pointer retry"; }
 part def RouteSpec { attribute key : String; attribute anchor : String; attribute qntAction : String; attribute leanLemma : String; attribute condition : String; }
 part route0 : RouteSpec { attribute :>> key = "registration"; attribute :>> anchor = "mem.c:1571-1684; os_dyn.c:764-769"; attribute :>> qntAction = "seal"; attribute :>> leanLemma = "rawBlocksSeal"; attribute :>> condition = "No in-flight raw borrow, writer, allocation, requested reserve or creator-only affinity at seal"; }
 part route1 : RouteSpec { attribute :>> key = "accounting"; attribute :>> anchor = "mem.c:1605,1624-1633,1668,6804-6805"; attribute :>> qntAction = "commitHandoff"; attribute :>> leanLemma = "chargeConservation"; attribute :>> condition = "Fold deferred charge once; remove source authority and publish target chain/RC/receipt atomically"; }
 part route2 : RouteSpec { attribute :>> key = "coverage"; attribute :>> anchor = "mem.c:4210-4247,6268-6291"; attribute :>> qntAction = "endGC"; attribute :>> leanLemma = "epochInvalidates"; attribute :>> condition = "Source-or-target arena scanned and counted once independently of processor membership; GC invalidates seal"; }
 part route3 : RouteSpec { attribute :>> key = "retirement"; attribute :>> anchor = "c_intf.c:1699-1707; mem.c:4404-4406"; attribute :>> qntAction = "reclaim"; attribute :>> leanLemma = "releaseErrorRetains"; attribute :>> condition = "Error/unknown task, unresolved receipt, lease and scan ticket prevent reclaim; no callback retry after pointer clear"; }
 part route4 : RouteSpec { attribute :>> key = "resize"; attribute :>> anchor = "setup.c:930-978; mem.c:4928-4934"; attribute :>> qntAction = "depart"; attribute :>> leanLemma = "transferredMayExit"; attribute :>> condition = "Committed durable VM authority permits processor departure even if caller acknowledgement remains unknown"; }
 part def GainSpec { attribute key : String; attribute avoided : String; attribute added : String; attribute condition : String; }
 part gain0 : GainSpec { attribute :>> key = "arena-handoff"; attribute :>> avoided = "Payload graph copying solely to escape creator processor; repeat root rebinding per borrower"; attribute :>> added = "O(1) ownership commit only after O(N+R) admission inventory or maintained metadata; retained whole-arena memory"; attribute :>> condition = "Positive only when avoided copy/rebinding work exceeds inventory, synchronization and retained-memory cost; no claim of zero-copy across VM"; }
 part gain1 : GainSpec { attribute :>> key = "capacity-and-scan"; attribute :>> avoided = "Duplicate enumeration or missing target arenas after shrink; source/target double charge"; attribute :>> added = "Epoch membership, exact scanner assignment and charged/deferred/reserve ledger; O(N) tracing retained"; attribute :>> condition = "Correctness gain is structural; scanning remains mandatory; consolidation need not improve asymptotic GC time"; }
 part gain2 : GainSpec { attribute :>> key = "compiler-service"; attribute :>> avoided = "Creator-processor affinity for qualified shared semantic bundles and native holders"; attribute :>> added = "Lease/receipt authority, foreign owner lane, callback drain and unknown-result retention"; attribute :>> condition = "Parallel span improves only when affinity was critical path and independent sessions exist; unbounded leases can erase memory benefit"; }
 part def RefinementSpec { attribute key : String; attribute qntScope : String; attribute leanScope : String; attribute sourceDuty : String; }
 part refinement0 : RefinementSpec { attribute :>> key = "seal"; attribute :>> qntScope = "closeAdmission;seal;failAllocation"; attribute :>> leanScope = "rawBlocksSeal;reserveBlocksSeal"; attribute :>> sourceDuty = "Close every refcount/data/list writer, allocation and native callback admission; no waiting with an allocation lock or GC participation debt"; }
 part refinement1 : RefinementSpec { attribute :>> key = "transfer"; attribute :>> qntScope = "commitHandoff;lookupReceipt"; attribute :>> leanScope = "chargeConservation;handoffNoDoubleCharge;exactChain;rcDetached"; attribute :>> sourceDuty = "Linearize complete arena authority and exact idempotent receipt; prove C release/acquire plus exclusive plain-list mutation and allocation debt settlement"; }
 part refinement2 : RefinementSpec { attribute :>> key = "epoch"; attribute :>> qntScope = "beginGC;scan;endGC;depart"; attribute :>> leanScope = "epochInvalidates;transferredMayExit"; attribute :>> sourceDuty = "Refine source scan/mark/sweep/capacity census and resize barriers; root graph/still-object scanner retained; no stale receipt after membership changes"; }
 part refinement3 : RefinementSpec { attribute :>> key = "retire"; attribute :>> qntScope = "startRelease;errorRelease;settleRelease;reclaim"; attribute :>> leanScope = "leaseBlocksFree;unknownBlocksFree;releaseErrorRetains;netBenefit"; attribute :>> sourceDuty = "All true native holders, callback/continuation pins and destructor outcomes accounted; real source behavior and net work/span/retention remain open"; }
 part def GateSpec { attribute key : String; attribute qualified : Boolean; attribute condition : String; }
 part gate0 : GateSpec { attribute :>> key = "producer-closure"; attribute :>> qualified = false; attribute :>> condition = "Exact still/RC/refcount writers, Tcl callback/delete/failure and native trampoline configuration admitted"; }
 part gate1 : GateSpec { attribute :>> key = "vm-ownership"; attribute :>> qualified = false; attribute :>> condition = "Whole arena/RC/roots/receipt authority implemented and source cleanup excluded after transfer"; }
 part gate2 : GateSpec { attribute :>> key = "gc-seal"; attribute :>> qualified = false; attribute :>> condition = "Actual allocation reserve, preaccepted writer and GC participant quiescence refined without circular waiting"; }
 part gate3 : GateSpec { attribute :>> key = "scan-coverage"; attribute :>> qualified = false; attribute :>> condition = "Target arena included exactly once in setup, strong/weak/sweep and capacity/bytes census after resize"; }
 part gate4 : GateSpec { attribute :>> key = "retirement"; attribute :>> qualified = false; attribute :>> condition = "Destructor thread/VM affinity, in-flight callbacks, native pins, continuations and unknown outcomes closed"; }
 part gate5 : GateSpec { attribute :>> key = "source-replacement"; attribute :>> qualified = false; attribute :>> condition = "Old per-PSTATE free/RC/root/accounting authority retired only for migrated domains; unsupported foreign users excluded"; }
 part gate6 : GateSpec { attribute :>> key = "platform"; attribute :>> qualified = false; attribute :>> condition = "C weak memory, configured ABI/GC, host registration, native correctness and measured benefit remain unqualified"; }
 attribute workspaceCount : Integer = 2;
 attribute actualAdmitted : Boolean = false;
 part history : GambitAssuranceRouting::ModelNeed { ref part :>> owner = GambitBuildAssurance::planner.component; attribute :>> obligationId = "SH-H"; attribute :>> kind = "interleaving"; attribute :>> subjectPath = "models/build/storage_handoff_receipt.qnt"; attribute :>> subjectScope = "storage_handoff_receipt:Test$"; attribute :>> premise = "Conditional storage authority contract; actual source/native closure remains open"; }
 part induction : GambitAssuranceRouting::ModelNeed { ref part :>> owner = GambitBuildAssurance::planner.component; attribute :>> obligationId = "SH-I"; attribute :>> kind = "induction"; attribute :>> subjectPath = "models/build/StorageHandoffReceipt.lean"; attribute :>> subjectScope = "StorageHandoffReceipt:rawBlocksSeal;reserveBlocksSeal;epochInvalidates;chargeConservation;handoffNoDoubleCharge;exactChain;rcDetached;transferredMayExit;leaseBlocksFree;unknownBlocksFree;releaseErrorRetains;netBenefit"; attribute :>> premise = "Conditional storage authority contract; actual source/native closure remains open"; }
 part source : GambitAssuranceRouting::ModelNeed { ref part :>> owner = GambitBuildAssurance::planner.component; attribute :>> obligationId = "SH-S"; attribute :>> kind = "source-refinement"; attribute :>> subjectPath = "dev/architecture/toolchain/storage-handoff-receipt-design.org"; attribute :>> subjectScope = "SH-S:source"; attribute :>> premise = "Conditional storage authority contract; actual source/native closure remains open"; }
 part platform : GambitAssuranceRouting::ModelNeed { ref part :>> owner = GambitBuildAssurance::planner.component; attribute :>> obligationId = "SH-E"; attribute :>> kind = "environment-refinement"; attribute :>> subjectPath = "dev/architecture/toolchain/storage-handoff-receipt-design.org"; attribute :>> subjectScope = "SH-E:platform"; attribute :>> premise = "Conditional storage authority contract; actual source/native closure remains open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = VMRootRegistry::source; }
}
