package SignalRouteRetirement {
 private import ScalarValues::*;
 part def Contract { attribute key : String; attribute anchor : String; attribute actionName : String; attribute lemmaName : String; attribute duty : String; attribute status : String; }
 part contract0 : Contract { attribute :>> key = "derived-credit"; attribute :>> anchor = "os_time.c:987-996; os_tty.c:8700-8732; setup.c:110-136"; attribute :>> actionName = "publishReason"; attribute :>> lemmaName = "publicationConserves"; attribute :>> duty = "Handler publishes native reason or transfers failure custody before last old-route access; count zero is not work closure"; attribute :>> status = "new signal contract"; }
 part contract1 : Contract { attribute :>> key = "entry"; attribute :>> anchor = "os_base.c:1817-1839; os_time.c:987-996"; attribute :>> actionName = "pinEntry"; attribute :>> lemmaName = "admitPreserves"; attribute :>> duty = "Permanent trampoline uses one tagged lock-free admission/refcount CAS before dereferencing route or endpoint; paused pre-CAS handler is uncounted but harmless"; attribute :>> status = "C/ABI refinement open"; }
 part contract2 : Contract { attribute :>> key = "revoke"; attribute :>> anchor = "os_time.c:1095-1105; os_tty.c:8804-8824"; attribute :>> actionName = "revoke"; attribute :>> lemmaName = "revokedEntryDenied"; attribute :>> duty = "Close same atomic admission gate first; late handlers cannot acquire old generation; do not confuse disposition update with grace completion"; attribute :>> status = "new linearization point"; }
 part contract3 : Contract { attribute :>> key = "storage-commit"; attribute :>> anchor = "os_io.c:11808-11828; setup.c:932-978"; attribute :>> actionName = "retireRoute"; attribute :>> lemmaName = "pinnedBlocksRetire"; attribute :>> duty = "Retire old route/native endpoint only after admission closed, active pins zero, work/fault debt zero and old-roster receipt; stable shell outlives VM"; attribute :>> status = "staged lifetime"; }
 part contract4 : Contract { attribute :>> key = "masks"; attribute :>> anchor = "os_thread.c:874-914; os_time.c:1055-1075; os_tty.c:8780-8789"; attribute :>> actionName = "maskThread"; attribute :>> lemmaName = "oneThreadNotGlobal"; attribute :>> duty = "Track actual calling-thread mask and normalized results; thread roster/birth fence needed for any all-thread claim; masking is not route reclamation authority"; attribute :>> status = "platform receipt required"; }
 part contract5 : Contract { attribute :>> key = "failure"; attribute :>> anchor = "os_base.c:1833-1837; os_time.c:1062,1075,1101-1103"; attribute :>> actionName = "notificationFailed"; attribute :>> lemmaName = "unknownNotificationBlocks"; attribute :>> duty = "Unknown mask/disposition/wake result retains coordinator and delivery custody; no false drain acknowledgement or blocking of GC roles"; attribute :>> status = "typed receipts required"; }
 part contract6 : Contract { attribute :>> key = "participant"; attribute :>> anchor = "setup.c:1049-1149; _kernel.scm:1448-1471"; attribute :>> actionName = "enterCollective"; attribute :>> lemmaName = "rosterEveryParticipant"; attribute :>> duty = "Drain while old roster/root/finite-wait services remain alive; caller POSIX mask is distinct from Scheme sync-op service mask"; attribute :>> status = "prior loop refinement"; }
 part contract7 : Contract { attribute :>> key = "mailbox"; attribute :>> anchor = "setup.c:110-136; os_setup.c:3037-3056; os_io.c:8503-8590"; attribute :>> actionName = "denyLate"; attribute :>> lemmaName = "deniedNeedsCustodian"; attribute :>> duty = "Denied or ambiguous late signal goes to process-lifetime native mailbox, not stale VM pointer or automatic next-generation replay; preserve reason policy"; attribute :>> status = "semantic mapping open"; }
 part def Gain { attribute key : String; attribute avoided : String; attribute added : String; attribute condition : String; }
 part gain0 : Gain { attribute :>> key = "retirement"; attribute :>> avoided = "Old route reclamation need not wait for unrelated threads to mask under the qualified atomic gate"; attribute :>> added = "Permanent shell plus tagged gate and active pins"; attribute :>> condition = "A selected pre-CAS handler may be denied after route retirement; every legacy bypass must first migrate"; }
 part gain1 : Gain { attribute :>> key = "latency"; attribute :>> avoided = "Owner can continue old-roster GC while coordinator awaits handler/work closure"; attribute :>> added = "Nonblocking retirement state machine, native reason mailbox and finite-wait fallback"; attribute :>> condition = "Progress requires handler termination, scheduler/OS fairness and prior wake protocol; no measured speedup"; }
 part gain2 : Gain { attribute :>> key = "ownership"; attribute :>> avoided = "Avoid fd/route ABA and silent late-signal reassignment"; attribute :>> added = "Generation overflow policy, reason custody and typed failures"; attribute :>> condition = "O(R+H+T) route/active-handler/thread-policy metadata; process shell cannot be reclaimed by individual VM"; }
 part gain3 : Gain { attribute :>> key = "language"; attribute :>> avoided = "Modern C preserves Scheme semantics and C portability with generated typed adapters"; attribute :>> added = "C atomics, stable shell, semantic reason dispatch and source proof"; attribute :>> condition = "Zig cannot remove signal ABI, root lifetime, grace or semantic ownership proofs; no mandatory incremental benefit established"; }
 part def Gate { attribute key : String; attribute qualified : Boolean; attribute duty : String; }
 part gate0 : Gate { attribute :>> key = "atomic-entry"; attribute :>> qualified = false; attribute :>> duty = "Tagged gate representable and always lock-free on admitted ABI; overflow, nested handler and SC/source proof"; }
 part gate1 : Gate { attribute :>> key = "stable-shell"; attribute :>> qualified = false; attribute :>> duty = "Trampoline code, gate and mailbox outlive all handler selections; VM cleanup/dlclose cannot reclaim them"; }
 part gate2 : Gate { attribute :>> key = "semantic-mailbox"; attribute :>> qualified = false; attribute :>> duty = "Late pending reason identity and destination policy resolved; no automatic old-to-new replay or silent drop"; }
 part gate3 : Gate { attribute :>> key = "producer-closure"; attribute :>> qualified = false; attribute :>> duty = "HB/TTY/SIGCHLD/crash and external disposition owners audited; no legacy handler bypass"; }
 part gate4 : Gate { attribute :>> key = "thread-policy"; attribute :>> qualified = false; attribute :>> duty = "All-thread mask claims use complete thread birth/join roster and known per-thread results; pending signal policy explicit"; }
 part gate5 : Gate { attribute :>> key = "old-roster"; attribute :>> qualified = false; attribute :>> duty = "Root adapters, finite native wake fallback and selected sync-op/resize/NOOP integration qualified"; }
 part gate6 : Gate { attribute :>> key = "retirement"; attribute :>> qualified = false; attribute :>> duty = "No unknown notification/close/route custody; dependency grace and inherited host attestation remain unqualified"; }
 part history : GambitAssuranceRouting::ModelNeed { ref part :>> owner = GambitBuildAssurance::planner.component; attribute :>> obligationId = "SRR-H"; attribute :>> kind = "interleaving"; attribute :>> subjectPath = "models/build/signal_route_retirement.qnt"; attribute :>> subjectScope = "safe: three handlers on two hosts, pre-CAS selection, gate/refcounts, masks and old-roster work"; attribute :>> premise = "Conditional signal retirement design; no native runtime or whole-source admission"; }
 part induction : GambitAssuranceRouting::ModelNeed { ref part :>> owner = GambitBuildAssurance::planner.component; attribute :>> obligationId = "SRR-I"; attribute :>> kind = "induction"; attribute :>> subjectPath = "models/build/SignalRouteRetirement.lean"; attribute :>> subjectScope = "gate transition preservation, typed mask, work custody and boundary lemmas"; attribute :>> premise = "Conditional signal retirement design; no native runtime or whole-source admission"; }
 part source : GambitAssuranceRouting::ModelNeed { ref part :>> owner = GambitBuildAssurance::planner.component; attribute :>> obligationId = "SRR-S"; attribute :>> kind = "source-refinement"; attribute :>> subjectPath = "dev/architecture/toolchain/signal-route-retirement-design.org"; attribute :>> subjectScope = "actual disposition, callback, mask and cleanup seams"; attribute :>> premise = "Conditional signal retirement design; no native runtime or whole-source admission"; }
 part platform : GambitAssuranceRouting::ModelNeed { ref part :>> owner = GambitBuildAssurance::planner.component; attribute :>> obligationId = "SRR-E"; attribute :>> kind = "environment-refinement"; attribute :>> subjectPath = "dev/architecture/toolchain/signal-route-retirement-design.org"; attribute :>> subjectScope = "Darwin delivery, atomic lock-freedom and stable code lifetime"; attribute :>> premise = "Conditional signal retirement design; no native runtime or whole-source admission"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = NativeWakeChannel::source; }
 part def ContractDependency { ref part dependent : Contract; ref part prerequisite : Contract; attribute reason : String; }
 part edge0 : ContractDependency { ref part :>> dependent = contract2; ref part :>> prerequisite = contract1; attribute :>> reason = "Revoke shares same entry/count atomic gate"; }
 part edge1 : ContractDependency { ref part :>> dependent = contract3; ref part :>> prerequisite = contract2; attribute :>> reason = "Closed gate precedes active-pin zero"; }
 part edge2 : ContractDependency { ref part :>> dependent = contract3; ref part :>> prerequisite = contract0; attribute :>> reason = "Handler exit is not work drain"; }
 part edge3 : ContractDependency { ref part :>> dependent = contract3; ref part :>> prerequisite = contract5; attribute :>> reason = "Unknown result retains custody"; }
 part edge4 : ContractDependency { ref part :>> dependent = contract3; ref part :>> prerequisite = contract6; attribute :>> reason = "Old roster remains until drain receipt"; }
 part edge5 : ContractDependency { ref part :>> dependent = contract1; ref part :>> prerequisite = contract7; attribute :>> reason = "Denied entry requires stable destination"; }
 part edge6 : ContractDependency { ref part :>> dependent = contract5; ref part :>> prerequisite = contract4; attribute :>> reason = "Mask failure is not an acknowledgement"; }
 part edge7 : ContractDependency { ref part :>> dependent = contract6; ref part :>> prerequisite = contract0; attribute :>> reason = "Selected work snapshots preserve late work"; }
 part edge8 : ContractDependency { ref part :>> dependent = contract7; ref part :>> prerequisite = contract0; attribute :>> reason = "Stable mailbox preserves semantic reason custody"; }
 part edge9 : ContractDependency { ref part :>> dependent = contract3; ref part :>> prerequisite = contract7; attribute :>> reason = "Old route retirement cannot free process mailbox"; }
}
