package SignalGateMailbox {
 private import ScalarValues::*;
 part def Contract { attribute key : String; attribute anchor : String; attribute actionName : String; attribute lemmaName : String; attribute duty : String; attribute status : String; }
 part contract0 : Contract { attribute :>> key = "derived-credit"; attribute :>> anchor = "setup.c:206-228; os_io.c:8514-8558"; attribute :>> actionName = "takeMailbox"; attribute :>> lemmaName = "takePreservesCoverage"; attribute :>> duty = "Atomic exchange owns one coalescible batch; concurrent publications remain pending; no load-then-clear and no count-from-bit inference"; attribute :>> status = "new native mailbox"; }
 part contract1 : Contract { attribute :>> key = "cas"; attribute :>> anchor = "gambit.h.in:11014-11026; os_base.c:1825-1837"; attribute :>> actionName = "mismatchCas"; attribute :>> lemmaName = "failedCasNoPin"; attribute :>> duty = "One strong CAS on coherent unsigned gate snapshot; failure updates expected but grants no pin/route access; bounded fallback only for admitted reason"; attribute :>> status = "C packing/ABI open"; }
 part contract2 : Contract { attribute :>> key = "overflow"; attribute :>> anchor = "gambit.h.in:11014-11026; os_time.c:987-996"; attribute :>> actionName = "overflowSnapshot"; attribute :>> lemmaName = "fullCountDenied"; attribute :>> duty = "Count saturation denies before increment; no field carry or modular generation reuse; exhausted generation seals slot"; attribute :>> status = "typed denial"; }
 part contract3 : Contract { attribute :>> key = "storage-commit"; attribute :>> anchor = "setup.c:932-978; os_io.c:11808-11828"; attribute :>> actionName = "retireVm"; attribute :>> lemmaName = "leaseBlocksRetirement"; attribute :>> duty = "Target VM lease, handler pins, selected work and old-roster/native retirement receipts must close before VM deletion"; attribute :>> status = "prior guards inherited"; }
 part contract4 : Contract { attribute :>> key = "mailbox"; attribute :>> anchor = "os_setup.c:3037-3056; setup.c:110-136"; attribute :>> actionName = "completeProcess"; attribute :>> lemmaName = "finishPreservesCoverage"; attribute :>> duty = "Process-lifetime shell owns denied reasons after old VM retirement; mailbox contains no Scheme/VM pointer and survives completion of old batch"; attribute :>> status = "process owner retained"; }
 part contract5 : Contract { attribute :>> key = "semantic"; attribute :>> anchor = "os_setup.c:3044-3049; os_io.c:8503-8558; os_tty.c:8700-8732"; attribute :>> actionName = "closedSnapshot"; attribute :>> lemmaName = "vmSpecificNotReason"; attribute :>> duty = "Only process-scoped coalescible native reasons with generation-invariant meaning admit this fallback; source behavior alone does not prove policy equivalence"; attribute :>> status = "per-reason proof open"; }
 part contract6 : Contract { attribute :>> key = "binding"; attribute :>> anchor = "os_setup.c:3044-3049; setup.c:95-136"; attribute :>> actionName = "commitBinding"; attribute :>> lemmaName = "retiredVmNotTarget"; attribute :>> duty = "Normal process custodian explicitly authorizes batch target under lease; unknown decision retains original lease, never auto-rebinds next VM"; attribute :>> status = "typed policy receipt"; }
 part contract7 : Contract { attribute :>> key = "participant"; attribute :>> anchor = "setup.c:1049-1113; _kernel.scm:1448-1471"; attribute :>> actionName = "enterCollective"; attribute :>> lemmaName = "rosterEveryParticipant"; attribute :>> duty = "Bound work keeps real target VM and old roster serviceable; semantic mailbox bits are not sync-op completion"; attribute :>> status = "source loop refinement"; }
 part def Gain { attribute key : String; attribute avoided : String; attribute added : String; attribute condition : String; }
 part gain0 : Gain { attribute :>> key = "gate-cost"; attribute :>> avoided = "Avoid unbounded CAS retry and unsafe reads after rejection"; attribute :>> added = "Per admitted entry one snapshot load, one successful strong CAS and one final decrement, plus work/wake publication"; attribute :>> condition = "Logical operation counts only; packing must be lock-free and all fields use the same atomic protocol"; }
 part gain1 : Gain { attribute :>> key = "batching"; attribute :>> avoided = "Coalescible process reasons need one pending bit and one exchange per batch"; attribute :>> added = "Stable native custodian, atomic fetch-or/exchange and effect reconciliation"; attribute :>> condition = "Only equivalent reason effects may merge; counted payloads and policy-dependent identities require other transport"; }
 part gain2 : Gain { attribute :>> key = "lifetime"; attribute :>> avoided = "Old VM may retire while denied process reasons remain safely owned"; attribute :>> added = "Target lease per authorized batch; journal for unknown decision; global shell lifetime"; attribute :>> condition = "Mailbox does not eliminate required roots for VM-specific payloads; no automatic new-generation target"; }
 part gain3 : Gain { attribute :>> key = "language"; attribute :>> avoided = "Modern C can share one generated reason/profile, gate and receipt contract"; attribute :>> added = "Atomics, explicit enum outcomes and semantic refinement obligations"; attribute :>> condition = "Zig cannot remove CAS, coalescing, policy or lifetime proofs; no extra language net benefit established"; }
 part def Gate { attribute key : String; attribute qualified : Boolean; attribute duty : String; }
 part gate0 : Gate { attribute :>> key = "gate-encoding"; attribute :>> qualified = false; attribute :>> duty = "Exact unsigned representation, coherent snapshot, tag/count widths and overflow non-wrap proof"; }
 part gate1 : Gate { attribute :>> key = "atomic-platform"; attribute :>> qualified = false; attribute :>> duty = "Always-lock-free signal-safe strong CAS/fetch-or/exchange on admitted target; no libatomic mutex"; }
 part gate2 : Gate { attribute :>> key = "reason-policy"; attribute :>> qualified = false; attribute :>> duty = "Per-signal coalescing and generation-invariant process intent proven observationally against Scheme callbacks"; }
 part gate3 : Gate { attribute :>> key = "binding-lifecycle"; attribute :>> qualified = false; attribute :>> duty = "VM registry lease and policy journal atomic acceptance, unknown-result query and rollback refined"; }
 part gate4 : Gate { attribute :>> key = "mailbox-lifetime"; attribute :>> qualified = false; attribute :>> duty = "Stable code/native slots/process custodian outlive handlers and all VM cleanup; no hidden payload root"; }
 part gate5 : Gate { attribute :>> key = "source-replacement"; attribute :>> qualified = false; attribute :>> duty = "All signal/direct/embedding aliases migrated; old flag clear and signal-time VM walk cannot bypass contract"; }
 part gate6 : Gate { attribute :>> key = "retirement"; attribute :>> qualified = false; attribute :>> duty = "Old-roster/root/native-close/OS-join/fallback plus inherited host attestation remain unqualified"; }
 part history : GambitAssuranceRouting::ModelNeed { ref part :>> owner = GambitBuildAssurance::planner.component; attribute :>> obligationId = "SGM-H"; attribute :>> kind = "interleaving"; attribute :>> subjectPath = "models/build/signal_gate_mailbox.qnt"; attribute :>> subjectScope = "safe: coherent CAS snapshot, capacity one, two generations, coalescible batch and leased binding"; attribute :>> premise = "Conditional design only; generic signal number has no VM generation identity"; }
 part induction : GambitAssuranceRouting::ModelNeed { ref part :>> owner = GambitBuildAssurance::planner.component; attribute :>> obligationId = "SGM-I"; attribute :>> kind = "induction"; attribute :>> subjectPath = "models/build/SignalGateMailbox.lean"; attribute :>> subjectScope = "failure/overflow admission, mailbox coverage transition induction and binding/retirement lemmas"; attribute :>> premise = "Conditional design only; generic signal number has no VM generation identity"; }
 part source : GambitAssuranceRouting::ModelNeed { ref part :>> owner = GambitBuildAssurance::planner.component; attribute :>> obligationId = "SGM-S"; attribute :>> kind = "source-refinement"; attribute :>> subjectPath = "dev/architecture/toolchain/signal-gate-mailbox-design.org"; attribute :>> subjectScope = "concrete reason/callback/counter/clear/VM target source seams"; attribute :>> premise = "Conditional design only; generic signal number has no VM generation identity"; }
 part platform : GambitAssuranceRouting::ModelNeed { ref part :>> owner = GambitBuildAssurance::planner.component; attribute :>> obligationId = "SGM-E"; attribute :>> kind = "environment-refinement"; attribute :>> subjectPath = "dev/architecture/toolchain/signal-gate-mailbox-design.org"; attribute :>> subjectScope = "unsigned gate encoding, signal-safe atomic ABI and persistent process custody"; attribute :>> premise = "Conditional design only; generic signal number has no VM generation identity"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SignalRouteRetirement::source; }
 part def ContractDependency { ref part dependent : Contract; ref part prerequisite : Contract; attribute reason : String; }
 part edge0 : ContractDependency { ref part :>> dependent = contract1; ref part :>> prerequisite = contract2; attribute :>> reason = "Count full is a denial without pin"; }
 part edge1 : ContractDependency { ref part :>> dependent = contract1; ref part :>> prerequisite = contract5; attribute :>> reason = "CAS fallback requires admitted semantic profile"; }
 part edge2 : ContractDependency { ref part :>> dependent = contract0; ref part :>> prerequisite = contract5; attribute :>> reason = "Only equivalent reasons may coalesce"; }
 part edge3 : ContractDependency { ref part :>> dependent = contract4; ref part :>> prerequisite = contract0; attribute :>> reason = "Exchange owns batch independently of new publication"; }
 part edge4 : ContractDependency { ref part :>> dependent = contract6; ref part :>> prerequisite = contract4; attribute :>> reason = "Normal custodian owns unbound batch"; }
 part edge5 : ContractDependency { ref part :>> dependent = contract6; ref part :>> prerequisite = contract5; attribute :>> reason = "Explicit target choice requires semantic policy"; }
 part edge6 : ContractDependency { ref part :>> dependent = contract3; ref part :>> prerequisite = contract6; attribute :>> reason = "Unknown target decision keeps VM lease"; }
 part edge7 : ContractDependency { ref part :>> dependent = contract3; ref part :>> prerequisite = contract1; attribute :>> reason = "Counted entry still blocks retirement"; }
 part edge8 : ContractDependency { ref part :>> dependent = contract3; ref part :>> prerequisite = contract7; attribute :>> reason = "Selected work and old roster settle"; }
 part edge9 : ContractDependency { ref part :>> dependent = contract7; ref part :>> prerequisite = contract6; attribute :>> reason = "Target binding precedes collective service"; }
}
