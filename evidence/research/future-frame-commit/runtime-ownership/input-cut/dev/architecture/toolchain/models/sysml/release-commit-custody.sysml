package ReleaseCommitCustody {
 private import ScalarValues::*;
 part def Contract { attribute key : String; attribute anchor : String; attribute actionName : String; attribute lemmaName : String; attribute guardName : String; attribute duty : String; attribute status : String; }
 part contract0 : Contract { attribute :>> key = "derived-credit"; attribute :>> anchor = "mem.c:4210-4248; setup.c:3384-3420"; attribute :>> actionName = "retireToken"; attribute :>> lemmaName = "rootRetirementRequiresSettled"; attribute :>> guardName = "s.tdone"; attribute :>> duty = "Released token is narrower than physical guard Done; retain root/session through caller debt, reader drain and GC epoch retirement"; attribute :>> status = "new token consumers and parent closure required"; }
 part contract1 : Contract { attribute :>> key = "execution-owner"; attribute :>> anchor = "c_intf.c:6555-6562; mem.c:1461-1467; gambit.h.in:8531-8535"; attribute :>> actionName = "enterSegment"; attribute :>> lemmaName = "criticalNeedsCustody"; attribute :>> guardName = "s.lroot"; attribute :>> duty = "Alternative A retains session and scanned roots, suppresses cancellation before entering the no-GC/no-callback decrement-to-record interval"; attribute :>> status = "source call body bounded; cancellation and escape closure not qualified"; }
 part contract2 : Contract { attribute :>> key = "gc-handshake"; attribute :>> anchor = "setup.c:67-92; mem.c:6798-6800,6845-6854,7071"; attribute :>> actionName = "collectCut"; attribute :>> lemmaName = "requestDoesNotAuthorizeGC"; attribute :>> guardName = "not(s.critical)"; attribute :>> duty = "GC request is not collector entry permission; require parked/root and old-roster cut, or a bounded interval that completes before participating"; attribute :>> status = "no spinning GC wait under root/registry lock"; }
 part contract3 : Contract { attribute :>> key = "storage-commit"; attribute :>> anchor = "mem.c:684-699,4210-4248; setup.c:781-804"; attribute :>> actionName = "retireVm"; attribute :>> lemmaName = "outstandingBlocksVm"; attribute :>> guardName = "not(s.lowner)"; attribute :>> duty = "VM retirement excludes unknown guard custody, exported handles, current invocations and inherited processor/storage debt"; attribute :>> status = "token receipt alone never permits shutdown"; }
 part contract4 : Contract { attribute :>> key = "token-authority"; attribute :>> anchor = "mem.c:1487-1497,1683,4210-4248; _kernel.scm:1020-1065"; attribute :>> actionName = "releaseToken"; attribute :>> lemmaName = "repeatReleaseIdempotent"; attribute :>> guardName = "s.troot"; attribute :>> duty = "Alternative B uses one stable atomic Active-to-Released token as native authority and marker validity; scalar count becomes nonauthoritative or is removed for this ownership class"; attribute :>> status = "requires allocator/scanner/return-to-C migration; no extra log beside old decrement"; }
 part contract5 : Contract { attribute :>> key = "unknown-keeper"; attribute :>> anchor = "setup.c:3384-3420; c_intf.c:6555-6562"; attribute :>> actionName = "abandonLegacy"; attribute :>> lemmaName = "unknownKeepsKeeper"; attribute :>> guardName = "not(s.ldead)"; attribute :>> duty = "Stable VM guardian retains roots and session on unlogged legacy outcome; no timeout transfer or blind retry; confirmed death still needs root/roster handoff"; attribute :>> status = "loss of process is outside in-memory recovery"; }
 part contract6 : Contract { attribute :>> key = "record-window"; attribute :>> anchor = "mem.c:1461-1467; c_intf.c:6555-6562"; attribute :>> actionName = "recordDrop"; attribute :>> lemmaName = "legacyAmbiguity"; attribute :>> guardName = "s.lp==2"; attribute :>> duty = "Pending log alone cannot distinguish decrement-before-abandonment from abandonment-before-decrement; quiescent single-credit count audit supplies extra evidence only under explicit closure"; attribute :>> status = "conditional no-abandonment, qualified exclusive-credit audit, or redesigned authority required"; }
 part contract7 : Contract { attribute :>> key = "release-query"; attribute :>> anchor = "mem.c:1447-1467; gambit.h.in:9981-9988"; attribute :>> actionName = "queryToken"; attribute :>> lemmaName = "tokenReplyRecoverable"; attribute :>> guardName = "s.troot"; attribute :>> duty = "After lost reply acquire exact generation token; helper may reconstruct release receipt but cannot declare caller restoration or live catcher complete"; attribute :>> status = "stable token storage, lookup admission and no ABA required"; }
 part def Gain { attribute key : String; attribute avoided : String; attribute added : String; attribute condition : String; }
 part gain0 : Gain { attribute :>> key = "bounded-legacy-segment"; attribute :>> avoided = "Retain current marker ABI and one required legacy still decrement"; attribute :>> added = "Cancellation save/disable/restore, sole executor, pinned roots, progress publication and delayed GC participation"; attribute :>> condition = "Qualify bounded interval and every escape; unlogged loss needs quarantine or separately admitted exclusive-credit audit"; }
 part gain1 : Gain { attribute :>> key = "atomic-authority"; attribute :>> avoided = "Remove the independent decrement-versus-record ambiguity for token-managed native ownership"; attribute :>> added = "Atomic token state, stable directory, active-token root scan, return-to-C identity read and retained tombstones"; attribute :>> condition = "Only if every marker allocation/scanning/native-release/validity consumer migrates; keeping both authorities defeats claim"; }
 part gain2 : Gain { attribute :>> key = "unknown-custody"; attribute :>> avoided = "Preserve roots and session until actual outcome and caller duties are known"; attribute :>> added = "Retention may be unbounded without progress or externally qualified root/roster recovery"; attribute :>> condition = "Stronger token release recovers accounting outcome only; physical caller debt remains"; }
 part gain3 : Gain { attribute :>> key = "modern-c-net-benefit"; attribute :>> avoided = "Generated C contracts can share token directory, GC epoch and completion support across necessary components"; attribute :>> added = "Representation/ABI migration, memory ordering and scan overhead remain in C and Zig"; attribute :>> condition = "No speedup established; token path earns adoption by removing ambiguity and retiring old marker-native counting, not by adding another wrapper"; }
 part def Gate { attribute key : String; attribute qualified : Boolean; attribute duty : String; }
 part gate0 : Gate { attribute :>> key = "native-interruption"; attribute :>> qualified = false; attribute :>> duty = "Every actual native throw, pthread cancellation, signal action, thread-exit and embedding escape is classified; no absence claim from narrow grep"; }
 part gate1 : Gate { attribute :>> key = "gc-participant-cut"; attribute :>> qualified = false; attribute :>> duty = "Root snapshot, marker/body exclusion, bounded poll deferral and old-roster participants close before collector access"; }
 part gate2 : Gate { attribute :>> key = "token-authority-migration"; attribute :>> qualified = false; attribute :>> duty = "Managed markers have no second authoritative native scalar reference; allocator, root scanner, raw inc/dec and return-to-C use same generation token"; }
 part gate3 : Gate { attribute :>> key = "stable-token-lifetime"; attribute :>> qualified = false; attribute :>> duty = "Pin directory before lookup, exclude generation/counter wrap, retain released identity until reader/query retirement; no raw access after expiry"; }
 part gate4 : Gate { attribute :>> key = "caller-debt"; attribute :>> qualified = false; attribute :>> duty = "Release known does not settle catcher/register/continuation/native-resource obligations or prove a dead thread handed them off"; }
 part gate5 : Gate { attribute :>> key = "c11-source-refinement"; attribute :>> qualified = false; attribute :>> duty = "Single atomic transition mapping, release/acquire reads-from, scanner epoch and cancellation-state restoration proven for concrete C ABI"; }
 part gate6 : Gate { attribute :>> key = "darwin-native"; attribute :>> qualified = false; attribute :>> duty = "Public libpthread source and archived manual are platform evidence, not matching installed library, effective argv or native SMP acceptance"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Nine literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "RCC-H"; attribute :>> kind = "interleaving"; attribute :>> subjectPath = "models/build/release_commit_custody.qnt"; attribute :>> subjectScope = "safe: legacy decrement-record ambiguity, interruption custody, pending cancellation and GC, authoritative token retry and separate physical guard completion"; attribute :>> premise = "No-abandonment cleanup, VM root-domain coverage and directory lifetime are premises, not implemented facilities; current native profile remains unqualified"; }
 part induction : GambitAssuranceRouting::ModelNeed { ref part :>> owner = GambitBuildAssurance::planner.component; attribute :>> obligationId = "RCC-I"; attribute :>> kind = "induction"; attribute :>> subjectPath = "models/build/ReleaseCommitCustody.lean"; attribute :>> subjectScope = "authoritative-token step/history safety, repeated-release idempotence, legacy indistinguishable outcomes and separate root/session debt"; attribute :>> premise = "No-abandonment cleanup, VM root-domain coverage and directory lifetime are premises, not implemented facilities; current native profile remains unqualified"; }
 part source : GambitAssuranceRouting::ModelNeed { ref part :>> owner = GambitBuildAssurance::planner.component; attribute :>> obligationId = "RCC-S"; attribute :>> kind = "source-refinement"; attribute :>> subjectPath = "dev/architecture/toolchain/release-commit-custody-design.org"; attribute :>> subjectScope = "actual interrupt/poll/throw/marker/refcount/scanner paths; closure of cancellation and two alternative release architectures"; attribute :>> premise = "No-abandonment cleanup, VM root-domain coverage and directory lifetime are premises, not implemented facilities; current native profile remains unqualified"; }
 part platform : GambitAssuranceRouting::ModelNeed { ref part :>> owner = GambitBuildAssurance::planner.component; attribute :>> obligationId = "RCC-E"; attribute :>> kind = "environment-refinement"; attribute :>> subjectPath = "dev/architecture/toolchain/release-commit-custody-design.org"; attribute :>> subjectScope = "C11 single-transition/refcount distinction, cancellation restore semantics, GC epoch and effective Darwin library/object refinement"; attribute :>> premise = "No-abandonment cleanup, VM root-domain coverage and directory lifetime are premises, not implemented facilities; current native profile remains unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = StableGuardSettlement::source; }
 part def ContractDependency { ref part dependent : Contract; ref part prerequisite : Contract; attribute reason : String; }
 part edge0 : ContractDependency { ref part :>> dependent = contract2; ref part :>> prerequisite = contract1; attribute :>> reason = "Shared roots and participation must cover collector cut"; }
 part edge1 : ContractDependency { ref part :>> dependent = contract6; ref part :>> prerequisite = contract1; attribute :>> reason = "Legacy record interval remains under ownership"; }
 part edge2 : ContractDependency { ref part :>> dependent = contract5; ref part :>> prerequisite = contract6; attribute :>> reason = "Ambiguous record cannot authorize repeating decrement"; }
 part edge3 : ContractDependency { ref part :>> dependent = contract5; ref part :>> prerequisite = contract1; attribute :>> reason = "Guardian retains stable root/session custody"; }
 part edge4 : ContractDependency { ref part :>> dependent = contract4; ref part :>> prerequisite = contract1; attribute :>> reason = "Token alternative also requires stable root and lookup ownership, not execution of legacy decrement"; }
 part edge5 : ContractDependency { ref part :>> dependent = contract7; ref part :>> prerequisite = contract4; attribute :>> reason = "Query reads the same authoritative released token"; }
 part edge6 : ContractDependency { ref part :>> dependent = contract0; ref part :>> prerequisite = contract7; attribute :>> reason = "Release outcome precedes separate caller retirement"; }
 part edge7 : ContractDependency { ref part :>> dependent = contract0; ref part :>> prerequisite = contract2; attribute :>> reason = "Root storage retirement follows collector and reader grace cut"; }
 part edge8 : ContractDependency { ref part :>> dependent = contract3; ref part :>> prerequisite = contract0; attribute :>> reason = "VM retirement waits for physical guard settlement"; }
 part edge9 : ContractDependency { ref part :>> dependent = contract3; ref part :>> prerequisite = contract5; attribute :>> reason = "Unknown legacy outcome still blocks shutdown"; }
 part def MemoryEdge { attribute key : String; attribute writer : String; attribute publication : String; attribute reader : String; attribute observation : String; attribute lifetime : String; }
 part memory0 : MemoryEdge { attribute :>> key = "segment-entry"; attribute :>> writer = "owner disables cancellation under existing entry custody"; attribute :>> publication = "save state and disable before claim; SC baseline"; attribute :>> reader = "same physical owner"; attribute :>> observation = "check successful admission before legacy decrement"; attribute :>> lifetime = "native asynchronous entry/foreign longjmp not covered by merely disabling Scheme interrupts"; }
 part memory1 : MemoryEdge { attribute :>> key = "legacy-decrement"; attribute :>> writer = "sole owner writes vector false and decrements owned still count"; attribute :>> publication = "ordinary stores under GC exclusion; then release progress"; attribute :>> reader = "same executor and final custodian"; attribute :>> observation = "acquire recorded progress; pending record is insufficient"; attribute :>> lifetime = "thread cannot be abandoned between count update and progress record"; }
 part memory2 : MemoryEdge { attribute :>> key = "token-release"; attribute :>> writer = "stable identity token already published and pinned"; attribute :>> publication = "single Active-to-Released CAS acq_rel success"; attribute :>> reader = "repeat requester or helper"; attribute :>> observation = "acquire failure/load same generation; no second decrement"; attribute :>> lifetime = "one atomic object supplies validity and native authority; ghost drop counter is not physical log"; }
 part memory3 : MemoryEdge { attribute :>> key = "gc-root-snapshot"; attribute :>> writer = "owner publishes mutable roots and participates in GC epoch"; attribute :>> publication = "release parked/root epoch; existing baseline requires audit"; attribute :>> reader = "collector and resumed owner"; attribute :>> observation = "acquire matching epoch/cut before scanning or resuming"; attribute :>> lifetime = "no collector read of changing plain marker fields; pending request alone is not a cut"; }
 part memory4 : MemoryEdge { attribute :>> key = "query"; attribute :>> writer = "directory admits reader before token dereference"; attribute :>> publication = "SC gate admission; candidate acq_rel"; attribute :>> reader = "query after lost reply"; attribute :>> observation = "acquire released token identity"; attribute :>> lifetime = "token storage and tombstones outlive readers and eligible retries"; }
 part memory5 : MemoryEdge { attribute :>> key = "caller-done"; attribute :>> writer = "owner completes catch restoration and remaining native effects"; attribute :>> publication = "release physical guard Done"; attribute :>> reader = "outer stable custodian"; attribute :>> observation = "acquire exact Done transaction"; attribute :>> lifetime = "token Released is not this Done; thread loss leaves caller debt"; }
 part memory6 : MemoryEdge { attribute :>> key = "cancel-restore"; attribute :>> writer = "stable custodian finishes mandatory ownership/Done publication"; attribute :>> publication = "restore caller original cancellation state after no more vulnerable PSTATE accesses"; attribute :>> reader = "pending cancellation may be delivered at or after restoration"; attribute :>> observation = "no forced enabling when caller entered disabled"; attribute :>> lifetime = "external guardian outlives nonreturning restoration; installed libpthread semantics unqualified"; }
 part memory7 : MemoryEdge { attribute :>> key = "retirement"; attribute :>> writer = "closer closes directory and root registration admission"; attribute :>> publication = "release close and reader decrement; SC baseline"; attribute :>> reader = "VM/GC custodian"; attribute :>> observation = "acquire final zero on same generation plus collector grace acknowledgement"; attribute :>> lifetime = "neither token state nor atomic count permits early free"; }
 part memory8 : MemoryEdge { attribute :>> key = "quiescent-audit"; attribute :>> writer = "old native writer stopped and all other reference mutators excluded"; attribute :>> publication = "successful termination/GC/root handoff and private-credit receipt"; attribute :>> reader = "stable VM custodian"; attribute :>> observation = "ordinary count and marker reads only after happens-before/quiescence; no atomic cast over plain fields"; attribute :>> lifetime = "same rooted generation, exact one-credit baseline, no alias increments; partial invalidation is not decrement evidence"; }
}
