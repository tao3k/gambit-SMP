package GcDrainRetirementCut {
 private import ScalarValues::*;
 part def ProgramPoint { attribute key : String; attribute anchor : String; attribute descriptor : String; attribute actualEdge : String; attribute requiredChange : String; }
 part point0 : ProgramPoint { attribute :>> key = "will-pre-action-poll"; attribute :>> anchor = "_kernel.c:17146-17160; _kernel.scm:2106-2116"; attribute :>> descriptor = "L1: RETI cfs=4 link=0 gcmap=0x3f1"; attribute :>> actualEdge = "R2=testator; R3=action; R1 copies R2; POLL precedes generic action jump"; attribute :>> requiredChange = "Reject issuance: action not returned; poll may preserve all registers"; }
 part point1 : ProgramPoint { attribute :>> key = "will-action-return"; attribute :>> anchor = "_kernel.c:17161-17169; descriptor:30131"; attribute :>> descriptor = "L2: RETN fs=1 link=0 gcmap=0x1"; attribute :>> actualEdge = "Reload RA and pop frame; L3 sets only R1=VOID then returns"; attribute :>> requiredChange = "Possible per-attempt generated epilogue cut only after qualified dead-register retirement and no restore/capture edges"; }
 part point2 : ProgramPoint { attribute :>> key = "finalizer-next-will"; attribute :>> anchor = "_kernel.c:17094-17121; descriptor:30127"; attribute :>> descriptor = "L1: RETN fs=1 link=0 gcmap=0x1"; attribute :>> actualEdge = "Reload/pop caller frame; fetch next will; next action can run or empty list tail-calls registry"; attribute :>> requiredChange = "Queue empty is not register/saved retirement or no-reentry proof; do not sign a batch from queue state"; }
 part point3 : ProgramPoint { attribute :>> key = "final-will-registry"; attribute :>> anchor = "_kernel.c:17236-17270"; attribute :>> descriptor = "No return descriptor in this host"; attribute :>> actualEdge = "Writes R1/R2 and conditionally R3 while unlinking cleared actions; does not clear saved or R4"; attribute :>> requiredChange = "Audit global registry and retained actions; empty path does not clear all residual roots"; }
 part point4 : ProgramPoint { attribute :>> key = "handler-to-jobs"; attribute :>> anchor = "_kernel.c:17331-17335; descriptor:30142"; attribute :>> descriptor = "L1: RETN fs=1 link=0 gcmap=0x1"; attribute :>> actualEdge = "Sets R1=gc-interrupt-jobs; reloads RA; pops frame; tail-calls execute-jobs"; attribute :>> requiredChange = "Preferred batch sealing candidate only after explicit qualified barrier; currently no issuer or full root cut"; }
 part point5 : ProgramPoint { attribute :>> key = "jobs-entry-and-callback"; attribute :>> anchor = "_kernel.c:16579-16607; descriptors:30084-30087"; attribute :>> descriptor = "L1 RETI 0/0/0x3f; L2 RETN 5/0/0x3; L3 RETI 0/0/0x3f; L4 RETI 8/0/0x3f03"; attribute :>> actualEdge = "Polls before loop and each generic job; snapshot list and job call can allocate/capture/throw"; attribute :>> requiredChange = "Generic drain job is too late to infer a prior root cut; jobs cannot confer GC provenance or bounded progress"; }
 part point6 : ProgramPoint { attribute :>> key = "internal-and-thread-restore"; attribute :>> anchor = "_kernel.scm:249-290,1320-1344; gambit.h.in:6314-6388,8059-8084"; attribute :>> descriptor = "RETI converts caller size and scans all saved GVM registers plus return point"; attribute :>> actualEdge = "POLL stack handler pushes all registers; internal return restores; thread-save/restore and GC_RESTORE transfer values"; attribute :>> requiredChange = "A receipt must close every target-root restoration path, not clear only PSTATE saved or one cached register"; }
 part def Gate { attribute key : String; attribute qualified : Boolean; attribute condition : String; }
 part gate0 : Gate { attribute :>> key = "generated-cohort"; attribute :>> qualified = false; attribute :>> condition = "Retained _kernel.c has source hash and labels, but original compiler/options/source generation receipt and current Darwin object equivalence remain unresolved"; }
 part gate1 : Gate { attribute :>> key = "exact-root-map"; attribute :>> qualified = false; attribute :>> condition = "Decode retained return descriptors and audit all ancestor maps at selected issuer; dead register masks need actual generated liveness, not numeric labels alone"; }
 part gate2 : Gate { attribute :>> key = "cached-bank-sync"; attribute :>> qualified = false; attribute :>> condition = "Account for single/multiple host, MAX_LOCAL_GVM_REGS, W_ALL/R_ALL and all scanned register-bank entries"; }
 part gate3 : Gate { attribute :>> key = "restore-closure"; attribute :>> qualified = false; attribute :>> condition = "No target-bearing internal-return, GC_SAVE destination, suspended thread, captured continuation or error can restore after signing"; }
 part gate4 : Gate { attribute :>> key = "issuer-effect-profile"; attribute :>> qualified = false; attribute :>> condition = "Generated epilogue/barrier is nonallocating/noncapturing and cannot poll into a target-root-bearing snapshot; no user jobs before sealing"; }
 part gate5 : Gate { attribute :>> key = "per-attempt-completion"; attribute :>> qualified = false; attribute :>> condition = "GC provenance and normal-return evidence bind each attempt across skipped action, failed action, nested GC and queue reentry"; }
 part gate6 : Gate { attribute :>> key = "publication-and-release"; attribute :>> qualified = false; attribute :>> condition = "Rootless receipt identity, stable storage, duplicate/unknown settlement and ancestor release permit join qualify before reclamation"; }
 part def Gain { attribute key : String; attribute avoided : String; attribute added : String; attribute condition : String; }
 part gain0 : Gain { attribute :>> key = "per-action-generated-cut"; attribute :>> avoided = "Can avoid waiting through unrelated wills and generic jobs for a completed eligible attempt"; attribute :>> added = "Generated epilogue PointId/root-mask support plus O(K) target-dead root retirement"; attribute :>> condition = "Conditional candidate, not current issuer; no latency bound, action effect/root liveness still open"; }
 part gain1 : Gain { attribute :>> key = "pre-jobs-batch-barrier"; attribute :>> avoided = "Can amortize one barrier over B completed eligible attempt slots and keep user jobs after sealing"; attribute :>> added = "Scan B status slots plus K dead-register operations; still O(B) per-attempt outcomes and O(W) storage"; attribute :>> condition = "Prefer explicit barrier at handler L1 before arbitrary job code; queue emptiness alone cannot qualify"; }
 part gain2 : Gain { attribute :>> key = "restore-aware-safety"; attribute :>> avoided = "Eliminates false retirement from R1=VOID, empty finalizer list, saved-slot clear or entry into jobs"; attribute :>> added = "Cached-bank synchronization and internal/thread/exception restoration proof"; attribute :>> condition = "No whole-heap traversal proposed; a missing closure invalidates the receipt before release"; }
 part gain3 : Gain { attribute :>> key = "modern-c-vs-zig"; attribute :>> avoided = "Reuse Scheme-generated descriptors and shared native contract; retire heuristic notification issuers only"; attribute :>> added = "Both backends need equivalent root/effect/memory-order obligations"; attribute :>> condition = "Modern C mainline; retained generated C supplies concrete integration points; no independent Zig net gain established"; }
 attribute defaultRegisters : Integer = 5;
 attribute willInternalMask : Integer = 1009;
 attribute willReturnMask : Integer = 1;
 attribute actualAdmitted : Boolean = false;
 part def CutEvidence { attribute requested : Boolean; attribute normal : Boolean; attribute rootFree : Boolean; attribute restoreClosed : Boolean; attribute syncComplete : Boolean; attribute generatedBound : Boolean; attribute identityMatched : Boolean; }
 requirement def CutLaw { subject evidence : CutEvidence; require constraint { not evidence.requested or (evidence.normal and evidence.rootFree and evidence.restoreClosed and evidence.syncComplete and evidence.generatedBound and evidence.identityMatched) } }
 part history : GambitAssuranceRouting::ModelNeed { ref part :>> owner = GambitBuildAssurance::scheduler.component; attribute :>> obligationId = "DC-H"; attribute :>> kind = "interleaving"; attribute :>> subjectPath = "models/build/gc_drain_retirement_cut.qnt"; attribute :>> subjectScope = "gc_drain_retirement_cut:Test$"; attribute :>> premise = "Retained generated path abstraction with R1/R2/R4, cached-bank synchronization, save/restore and pre-jobs candidate; no native source simulation"; }
 part induction : GambitAssuranceRouting::ModelNeed { ref part :>> owner = GambitBuildAssurance::scheduler.component; attribute :>> obligationId = "DC-I"; attribute :>> kind = "induction"; attribute :>> subjectPath = "models/build/GcDrainRetirementCut.lean"; attribute :>> subjectScope = "GcDrainRetirementCut:voidLeavesR4;registryLeavesR4;bankClearNotEnough;cacheClearNotEnough;restoreTransfers;readyExcludesRestore;readyNeedsIdentity;retireSyncClosed"; attribute :>> premise = "Eight conditional register-transfer and issuer guard kernels; actual generated liveness/effects remain source premises"; }
 part source : GambitAssuranceRouting::ModelNeed { ref part :>> owner = GambitBuildAssurance::scheduler.component; attribute :>> obligationId = "DC-S"; attribute :>> kind = "source-refinement"; attribute :>> subjectPath = "dev/architecture/toolchain/gc-drain-retirement-cut-design.org"; attribute :>> subjectScope = "DC-S:generated-cut-source"; attribute :>> premise = "Actual retained C labels and descriptors bound; generation provenance and full root/restore/effect closure unresolved"; }
 part platform : GambitAssuranceRouting::ModelNeed { ref part :>> owner = GambitBuildAssurance::scheduler.component; attribute :>> obligationId = "DC-E"; attribute :>> kind = "environment-refinement"; attribute :>> subjectPath = "dev/architecture/toolchain/gc-drain-retirement-cut-design.org"; attribute :>> subjectScope = "DC-E:generated-cut-native"; attribute :>> premise = "No current issuer; actual Darwin host/register/GC configuration, object maps, atomic publication and storage grace unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = NotifierRootRetirement::source; }
}
