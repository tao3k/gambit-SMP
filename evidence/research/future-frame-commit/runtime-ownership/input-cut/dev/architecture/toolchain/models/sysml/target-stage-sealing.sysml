package TargetStageSealing {
 private import ScalarValues::*;
 part def WriterSpec { attribute key : String; attribute anchor : String; attribute writes : String; attribute owner : String; attribute closure : String; }
 part writer0 : WriterSpec { attribute :>> key = "target-registry"; attribute :>> anchor = "_back.scm:171-266,388-509; _t-c-1.scm:225-279"; attribute :>> writes = "Target vector fields, targets-alist, target and target.* dispatch globals"; attribute :>> owner = "Immutable descriptor template + per-context selected-target instance"; attribute :>> closure = "C begin! rewrites registered target; shallow sharing of target-get result is unsafe"; }
 part writer1 : WriterSpec { attribute :>> key = "primitive-overlays"; attribute :>> anchor = "_prims.scm:6806-6809; _t-c-2.scm:2870-2875"; attribute :>> writes = "Specializer/expander/simplifier and primitive inline metadata"; attribute :>> owner = "Per-semantic-profile frozen base only after closure proof; mutable overlays per context"; attribute :>> closure = "setup-prims plus target callbacks mutate procedure metadata; function pointer equality is not immutability"; }
 part writer2 : WriterSpec { attribute :>> key = "c-interface"; attribute :>> anchor = "_t-c-1.scm:337-346; _front.scm:435-449"; attribute :>> writes = "Clears c-intf decls/procs/inits/objs after extracting their values"; attribute :>> owner = "Exclusive consumed input OR immutable snapshot + private emission copy"; attribute :>> closure = "Field clearing does not prove extracted nested values are unaliased; nested graph census remains open"; }
 part writer3 : WriterSpec { attribute :>> key = "module-heap"; attribute :>> anchor = "_t-c-1.scm:428-483"; attribute :>> writes = "Interning tables, ordered tables, queues, resource records, labels, FP/sharing/name caches"; attribute :>> owner = "EmissionWorkspace for one module attempt"; attribute :>> closure = "begin/end reset globals but interior stores must be traced; normal end is not exceptional cleanup proof"; }
 part writer4 : WriterSpec { attribute :>> key = "procedure-emission"; attribute :>> anchor = "_t-c-2.scm:26-93,239-269,347-419"; attribute :>> writes = "Per-procedure code, labels, resources, frames, allocation reserves and debug accumulator"; attribute :>> owner = "ProcedureWorkspace nested in one EmissionWorkspace"; attribute :>> closure = "Table/cell/queue aliases can retain emission data after top-level reset"; }
 part writer5 : WriterSpec { attribute :>> key = "representation"; attribute :>> anchor = "_t-c-2.scm:1424-1975,2521-2525"; attribute :>> writes = "Representation graph/current block, FP cache and tuning flags"; attribute :>> owner = "Profile configuration separated from per-procedure analysis graph"; attribute :>> closure = "Some representation hooks are commented out; syntactic store inventory is not execution reachability"; }
 part writer6 : WriterSpec { attribute :>> key = "source-output"; attribute :>> anchor = "_t-c-1.scm:1083-1108,1393-1397,2280-2288"; attribute :>> writes = "Output port, line counters, filenames, macro-definition/source tracking"; attribute :>> owner = "Attempt-owned diagnostic/source sink plus caller-owned port lease"; attribute :>> closure = "Normal close-output-port is not a cleanup guarantee on every exception path"; }
 part writer7 : WriterSpec { attribute :>> key = "link-selection"; attribute :>> anchor = "_back.scm:604-714; _t-c-1.scm:1271-1397"; attribute :>> writes = "Linker target begin/end, output state and module/link metadata"; attribute :>> owner = "Native/link context with same semantic cohort rules"; attribute :>> closure = "compile-only caller census excludes link consumers; both must migrate before retiring globals"; }
 part def FidelitySpec { attribute key : String; attribute anchor : String; attribute mustPreserve : String; attribute counterexample : String; attribute admission : String; }
 part fidelity0 : FidelitySpec { attribute :>> key = "declarations"; attribute :>> anchor = "driver.ss:702-704,787-797; compile.ss:401-426"; attribute :>> mustPreserve = "Ordered declarations, annotation scope, section kind and phi-specific inlining policy"; attribute :>> counterexample = "Flattening declaration scopes or dropping positive-phase inlining-limit changes compiler behavior"; attribute :>> admission = "Encode declaration tree/scopes, not a set of options; compare to generated-file reader observation"; }
 part fidelity1 : FidelitySpec { attribute :>> key = "lexical-identity"; attribute :>> anchor = "base.ss:185-224; compile.ss:832-854,1150-1202"; attribute :>> mustPreserve = "Binding equality/distinction, namespace/phi, substitutions, quote-syntax lifts and initializer references"; attribute :>> counterexample = "Canonicalizing distinct gensyms by spelling or stripping timestamp can collapse identities"; attribute :>> admission = "Explicit injective binder/mark reconstruction and timestamp policy; no generic byte-equality claim"; }
 part fidelity2 : FidelitySpec { attribute :>> key = "source-origin"; attribute :>> anchor = "driver.ss:33-36,787-797; _front.scm:215-239; iter/macros.ss:45-57"; attribute :>> mustPreserve = "Baseline generated-file locations and reader/wrap/expand observations; original-source map separately labeled"; attribute :>> counterexample = "sourcify-deep with one source is not automatically equivalent to read-source of emitted UTF-8/LF file"; attribute :>> admission = "Baseline generated-view map required; richer original-origin diagnostics are an explicit enhancement"; }
 part fidelity3 : FidelitySpec { attribute :>> key = "exceptions"; attribute :>> anchor = "base.ss:97-99,340-346; driver.ss:963-978"; attribute :>> mustPreserve = "Phase-tagged diagnostics, nonzero subprocess status contract, output delivery and cleanup custody"; attribute :>> counterexample = "Rethrowing a Gambit internal exception changes the current invoke nonzero-status compile-error surface"; attribute :>> admission = "Compatibility adapter for existing observations; raw exception identity/continuation transport remains restricted"; }
 part def SealSpec { attribute key : String; attribute inputGraph : String; attribute sealCondition : String; attribute consumer : String; attribute cost : String; }
 part seal0 : SealSpec { attribute :>> key = "normalized"; attribute :>> inputGraph = "Normalized nodes + environment + C-interface + module metadata"; attribute :>> sealCondition = "No external mutable aliases, OR exclusive rooted region transfer; include origins and target semantic profile"; attribute :>> consumer = "GVM lowering under same semantic identity"; attribute :>> cost = "Graph traversal, relocation and roots/retained memory"; }
 part seal1 : SealSpec { attribute :>> key = "gvm"; attribute :>> inputGraph = "Procedures/basic blocks/operands/constants + frame/module specs + C-interface"; attribute :>> sealCondition = "Frozen snapshot with alias-preserving relocation; mutable target metadata and workspaces excluded"; attribute :>> consumer = "One private emitter workspace per backend/attempt"; attribute :>> cost = "Snapshot bytes, rehydration and private primitive/target overlays"; }
 part seal2 : SealSpec { attribute :>> key = "exclusive-consume"; attribute :>> inputGraph = "Live current GVM/C-interface graph with owner-only access"; attribute :>> sealCondition = "Atomic admission closure and one consumer transfer; no retained cached alias"; attribute :>> consumer = "Current destructive emitter only under exclusive ownership"; attribute :>> cost = "Avoids freeze copy but prevents reusable shared-stage credential"; }
 part seal3 : SealSpec { attribute :>> key = "result-manifest"; attribute :>> inputGraph = "Generated C bytes/descriptors + source/diagnostic projections + native requirements"; attribute :>> sealCondition = "Complete output group, current epoch/profile, known success and closed writer admission"; attribute :>> consumer = "Gerbil scheduler/native tool service"; attribute :>> cost = "Digest, atomic commit and diagnostic materialization"; }
 part def GainSpec { attribute key : String; attribute avoided : String; attribute added : String; attribute condition : String; }
 part gain0 : GainSpec { attribute :>> key = "context-parallelism"; attribute :>> avoided = "Global target/primitive/emission serialization after complete ownership migration"; attribute :>> added = "Private workspace and overlay memory, scheduling, possible IPC"; attribute :>> condition = "Removed span exceeds added span; target registry/primitive sharing must be proven safe"; }
 part gain1 : GainSpec { attribute :>> key = "gvm-reuse"; attribute :>> avoided = "Repeated parse/normalize/lower for admitted equal inputs"; attribute :>> added = "Freeze traversal + retained snapshot + private emission materialization"; attribute :>> condition = "For k uses: (k-1)*frontWork > freezeCost + k*extraMaterialization + validation; cold single-use can lose"; }
 part gain2 : GainSpec { attribute :>> key = "structured-handoff"; attribute :>> avoided = "Repeated Scheme file write/read and avoidable process boundary work"; attribute :>> added = "Identity/origin/declaration codec + observation-compatible error adaptation"; attribute :>> condition = "Removed serialization/startup exceeds codec + root custody cost; no gain from merely changing representation"; }
 part gain3 : GainSpec { attribute :>> key = "exclusive-handoff"; attribute :>> avoided = "Unnecessary copying in a single-consumer noncached pipeline"; attribute :>> added = "Single-consumer authority and lifetime checks"; attribute :>> condition = "Useful independent of reusable caching; must not count it again as shared snapshot savings"; }
 part def RefinementSpec { attribute key : String; attribute qntScope : String; attribute leanScope : String; attribute evidenceGap : String; }
 part refinement0 : RefinementSpec { attribute :>> key = "writer-freeze"; attribute :>> qntScope = "closeAdmission;settleWriter;sealSnapshot"; attribute :>> leanScope = "sealNeedsZero;lateWriterDenied"; attribute :>> evidenceGap = "Complete actual alias/writer reachability beyond syntactic inventory remains open"; }
 part refinement1 : RefinementSpec { attribute :>> key = "private-emission"; attribute :>> qntScope = "materialize;consumePrivate;transferExclusive"; attribute :>> leanScope = "snapshotNotConsumed;exclusiveDisjoint"; attribute :>> evidenceGap = "Current c-intf consumption must refine a private graph or exclusive transfer"; }
 part refinement2 : RefinementSpec { attribute :>> key = "fidelity-projection"; attribute :>> qntScope = "publish;changeOrigin"; attribute :>> leanScope = "projectionDistinct;declarationOrder"; attribute :>> evidenceGap = "Real declaration/identity/source codec and diagnostics equivalence unproven"; }
 part refinement3 : RefinementSpec { attribute :>> key = "failure-custody"; attribute :>> qntScope = "unknownOutcome;settleOutcome;releaseContext"; attribute :>> leanScope = "unknownNotSuccess;reusePositive"; attribute :>> evidenceGap = "Native exit and callback/borrow/root closure are assumptions, not derived from the model"; }
 part def GateSpec { attribute key : String; attribute qualified : Boolean; attribute condition : String; }
 part gate0 : GateSpec { attribute :>> key = "writer-closure"; attribute :>> qualified = false; attribute :>> condition = "All stores, setter expansions, alias mutations and callbacks mapped to owners; inventory is only syntactic"; }
 part gate1 : GateSpec { attribute :>> key = "graph-seal"; attribute :>> qualified = false; attribute :>> condition = "No surviving mutable aliases; roots and identity/relocation complete; transfer excludes cached sharing"; }
 part gate2 : GateSpec { attribute :>> key = "declaration-fidelity"; attribute :>> qualified = false; attribute :>> condition = "Scope/order/section/phi and semantic options preserve real reader/parse observations"; }
 part gate3 : GateSpec { attribute :>> key = "identity-fidelity"; attribute :>> qualified = false; attribute :>> condition = "Binding/mark/gensym/quote equality and distinction preserved across module instances"; }
 part gate4 : GateSpec { attribute :>> key = "origin-fidelity"; attribute :>> qualified = false; attribute :>> condition = "Generated reader locations preserved; richer original mapping not silently substituted"; }
 part gate5 : GateSpec { attribute :>> key = "outcome-fidelity"; attribute :>> qualified = false; attribute :>> condition = "Existing compile-error/status surface and cleanup order preserved; unknown completion retains custody"; }
 part gate6 : GateSpec { attribute :>> key = "source-platform"; attribute :>> qualified = false; attribute :>> condition = "Model-to-Scheme/C memory and runtime proof plus actual work/span/memory evidence remains open"; }
 part def SealEvidence { attribute admissionClosed : Boolean; attribute writers : Integer; attribute aliasesClosed : Boolean; attribute graphCovered : Boolean; attribute sealed : Boolean; }
 requirement def SealLaw { subject s : SealEvidence; require constraint { not s.sealed or (s.admissionClosed and s.writers == 0 and s.aliasesClosed and s.graphCovered) } }
 attribute capacity : Integer = 2;
 attribute actualAdmitted : Boolean = false;
 part history : GambitAssuranceRouting::ModelNeed { ref part :>> owner = GambitBuildAssurance::planner.component; attribute :>> obligationId = "TS-H"; attribute :>> kind = "interleaving"; attribute :>> subjectPath = "models/build/target_stage_sealing.qnt"; attribute :>> subjectScope = "target_stage_sealing:Test$"; attribute :>> premise = "Target writer/freeze/consume and GeneratedScheme fidelity contracts; conditional protocol not actual compiler simulation"; }
 part induction : GambitAssuranceRouting::ModelNeed { ref part :>> owner = GambitBuildAssurance::planner.component; attribute :>> obligationId = "TS-I"; attribute :>> kind = "induction"; attribute :>> subjectPath = "models/build/TargetStageSealing.lean"; attribute :>> subjectScope = "TargetStageSealing:sealNeedsZero;lateWriterDenied;snapshotNotConsumed;exclusiveDisjoint;projectionDistinct;declarationOrder;unknownNotSuccess;reusePositive"; attribute :>> premise = "Target writer/freeze/consume and GeneratedScheme fidelity contracts; conditional protocol not actual compiler simulation"; }
 part source : GambitAssuranceRouting::ModelNeed { ref part :>> owner = GambitBuildAssurance::planner.component; attribute :>> obligationId = "TS-S"; attribute :>> kind = "source-refinement"; attribute :>> subjectPath = "dev/architecture/toolchain/target-stage-sealing-design.org"; attribute :>> subjectScope = "TS-S:source"; attribute :>> premise = "Target writer/freeze/consume and GeneratedScheme fidelity contracts; conditional protocol not actual compiler simulation"; }
 part platform : GambitAssuranceRouting::ModelNeed { ref part :>> owner = GambitBuildAssurance::planner.component; attribute :>> obligationId = "TS-E"; attribute :>> kind = "environment-refinement"; attribute :>> subjectPath = "dev/architecture/toolchain/target-stage-sealing-design.org"; attribute :>> subjectScope = "TS-E:platform"; attribute :>> premise = "Target writer/freeze/consume and GeneratedScheme fidelity contracts; conditional protocol not actual compiler simulation"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = IterCompilerService::source; }
}
