package WillActionAdmission {
 private import ScalarValues::*;
 part def Cohort { attribute key : String; attribute anchor : String; attribute observation : String; attribute limit : String; }
 part cohort0 : Cohort { attribute :>> key = "vendor-retained"; attribute :>> anchor = "vendor/gambit/lib/_kernel.c; gsc-boot.unix:5-16"; attribute :>> observation = "Git-tracked precompiled C; HEAD bytes match; recipe may deliberately preserve it"; attribute :>> limit = "No configured header or recorded original Scheme-to-C invocation in vendor checkout"; }
 part cohort1 : Cohort { attribute :>> key = "darwin-ci"; attribute :>> anchor = "../ci-source-patch-check/src/gambit/config.log:7; lib/makefile:27-37,173-185; include/gambit.h:1232,1381,1467-1490"; attribute :>> observation = "Kernel C and Scheme match vendor; GCC16, arm64, single-host unlimited, inline jumps, O1/O3; Scheme prelude enable-smp"; attribute :>> limit = "Header defaults single-threaded VM/max1; final overrides/object command and original generation not proved"; }
 part cohort2 : Cohort { attribute :>> key = "darwin-bootstrap"; attribute :>> anchor = "../gerbil-gambit-bootstrap-audit/src/gambit; build/lib/std/db/sqlite~0.scm:536-554"; attribute :>> observation = "Same kernel Scheme; different kernel C version/W^X fragments; selected path host bodies/descriptors match; no inline jumps; prelude disable-smp"; attribute :>> limit = "Statement action object/dSYM UUID match, but generated C/root maps and source-image generation provenance missing"; }
 part def ActionPoint { attribute key : String; attribute anchor : String; attribute rootDuty : String; attribute deadMask : String; attribute condition : String; }
 part point0 : ActionPoint { attribute :>> key = "registration"; attribute :>> anchor = "sqlite.ss:60-67; sqlite~0.scm:498"; attribute :>> rootDuty = "Will holds __sqlite-statement-close as action; statement is testator"; attribute :>> deadMask = "unresolved"; attribute :>> condition = "Public will identity does not grant private GC ticket"; }
 part point1 : ActionPoint { attribute :>> key = "action-entry"; attribute :>> anchor = "sqlite~0.scm:536-538; DWARF L0 line537"; attribute :>> rootDuty = "self alias must protect statement through remaining reads and final store"; attribute :>> deadMask = "unresolved"; attribute :>> condition = "DWARF source line is not a register or frame root mask"; }
 part point2 : ActionPoint { attribute :>> key = "pointer-test"; attribute :>> anchor = "sqlite~0.scm:539-542"; attribute :>> rootDuty = "ptr false skips cleanup; ptr true is read again for finalize"; attribute :>> deadMask = "unresolved"; attribute :>> condition = "Do not retire self or infer liveness from ptr nullness"; }
 part point3 : ActionPoint { attribute :>> key = "native-finalize"; attribute :>> anchor = "sqlite~0.scm:543-546; DWARF L1/L2 line543"; attribute :>> rootDuty = "Keep self for later pointer read/store; raw statement is destroyed even if status reports error"; attribute :>> deadMask = "unresolved"; attribute :>> condition = "Status is discarded in current action; destructors/effects and callbacks remain library/version dependent"; }
 part point4 : ActionPoint { attribute :>> key = "foreign-wrapper-release"; attribute :>> anchor = "sqlite~0.scm:547-550; DWARF L3 line547; _kernel.c:21940-22020"; attribute :>> rootDuty = "Keep self until slot clear; release_foreign may clear wrapper then invoke release callback"; attribute :>> deadMask = "unresolved"; attribute :>> condition = "Public foreign-release! polls; exact selected pointer release path must be qualified, generic error is not an observed SQLite failure"; }
 part point5 : ActionPoint { attribute :>> key = "slot-clear"; attribute :>> anchor = "sqlite~0.scm:551-554"; attribute :>> rootDuty = "Final explicit self use stores false; normal sequential return follows"; attribute :>> deadMask = "unresolved"; attribute :>> condition = "A semantic last use is not generated register/cached/saved retirement or concurrency exclusion"; }
 part point6 : ActionPoint { attribute :>> key = "per-action-candidate"; attribute :>> anchor = "_kernel.c:17161-17166"; attribute :>> rootDuty = "Normal return + GC ticket + root/effect/restore proof needed after VOID"; attribute :>> deadMask = "unresolved"; attribute :>> condition = "Legacy SQLite cleanup is not a restricted notifier; no current issuer"; }
 part point7 : ActionPoint { attribute :>> key = "pre-jobs-candidate"; attribute :>> anchor = "_kernel.c:17331-17335"; attribute :>> rootDuty = "All eligible attempt outcomes plus root/restore proof required before jobs"; attribute :>> deadMask = "unresolved"; attribute :>> condition = "Batch entry cannot convert cleanup completion, UUID or config metadata into root retirement"; }
 part def Gate { attribute key : String; attribute qualified : Boolean; attribute condition : String; }
 part gate0 : Gate { attribute :>> key = "generation-cohort"; attribute :>> qualified = false; attribute :>> condition = "Original compiler image, Scheme/prelude/include closure, options and successful output receipt bound; dummy bootstrap and identical output are not causal evidence"; }
 part gate1 : Gate { attribute :>> key = "configured-object"; attribute :>> qualified = false; attribute :>> condition = "Actual Darwin compile argv/header/defines, linked runtime and selected SQLite library identity bound; header defaults cannot stand for effective overrides"; }
 part gate2 : Gate { attribute :>> key = "action-dead-masks"; attribute :>> qualified = false; attribute :>> condition = "Recover selected action generated C or equivalent descriptors and generated PointIds; DWARF L0-L3 and last-use analysis alone are insufficient"; }
 part gate3 : Gate { attribute :>> key = "ffi-effect-closure"; attribute :>> qualified = false; attribute :>> condition = "Classify cleanup vs notification; qualify selected pointer releaser and native callbacks/allocations/errors; no blanket no-capture inference from C-lambda"; }
 part gate4 : Gate { attribute :>> key = "restore-closure"; attribute :>> qualified = false; attribute :>> condition = "Selected notifier/caller cached-bank, saved, internal/thread, captured/error restore paths closed per exact configuration"; }
 part gate5 : Gate { attribute :>> key = "owner-and-outcome"; attribute :>> qualified = false; attribute :>> condition = "Serialize actual native resource ownership; ptr false guard is not concurrent exclusion; distinguish finalize status from destruction and preserve exception custody"; }
 part gate6 : Gate { attribute :>> key = "candidate-publication"; attribute :>> qualified = false; attribute :>> condition = "New restricted action/barrier, GC provenance, per-attempt completion, rootless publication and ancestor release join qualified"; }
 part def Gain { attribute key : String; attribute avoided : String; attribute added : String; attribute condition : String; }
 part gain0 : Gain { attribute :>> key = "causal-build-contract"; attribute :>> avoided = "Avoid signing receipts from a nearby configure directory or matching version string"; attribute :>> added = "Bind generator image/input closure/output and C-compile/link cohorts separately"; attribute :>> condition = "Existing precompiled C remains reusable only under an explicit validated contract; no present build-time saving measured"; }
 part gain1 : Gain { attribute :>> key = "semantic-live-roots"; attribute :>> avoided = "Avoid premature self retirement across two foreign operations and final store"; attribute :>> added = "Action-specific FrameSpec/PointId and restoration proof; no invented numeric dead mask"; attribute :>> condition = "Eight program points audited; zero action machine dead masks qualified"; }
 part gain2 : Gain { attribute :>> key = "cleanup-notifier-separation"; attribute :>> avoided = "A future rootless notifier can avoid arbitrary native cleanup under its callback roots"; attribute :>> added = "Owned cleanup executor still carries affinity, error, cancellation, draining and per-resource state"; attribute :>> condition = "Not implemented; cannot count SQLite cleanup support as eliminated or claim cleanup becomes free"; }
 part gain3 : Gain { attribute :>> key = "modern-c-and-zig"; attribute :>> avoided = "Modern C can reuse current Scheme lowering and shared runtime contracts"; attribute :>> added = "Equivalent GC/FFI/effect/cohort obligations for Zig; additional backend admission required"; attribute :>> condition = "No separately demonstrated positive Zig gain; do not duplicate root maps or bypass Gambit semantics"; }
 attribute retainedCiMatch : Boolean = true;
 attribute actionMaskAvailable : Boolean = false;
 attribute restrictedAction : Boolean = false;
 attribute configuredMaxProcessors : Integer = 1;
 attribute actualAdmitted : Boolean = false;
 part def ActionEvidence { attribute requested : Boolean; attribute semanticCompletion : Boolean; attribute originalGeneration : Boolean; attribute nativeCohort : Boolean; attribute actionMaps : Boolean; attribute restricted : Boolean; attribute restoreClosed : Boolean; }
 requirement def ActionLaw { subject evidence : ActionEvidence; require constraint { not evidence.requested or (evidence.semanticCompletion and evidence.originalGeneration and evidence.nativeCohort and evidence.actionMaps and evidence.restricted and evidence.restoreClosed) } }
 part history : GambitAssuranceRouting::ModelNeed { ref part :>> owner = GambitBuildAssurance::scheduler.component; attribute :>> obligationId = "WA-H"; attribute :>> kind = "interleaving"; attribute :>> subjectPath = "models/build/will_action_admission.qnt"; attribute :>> subjectScope = "will_action_admission:Test$"; attribute :>> premise = "Actual SQLite semantic action order plus conditional provenance/dead-mask/notifier admission; no native reproduction or observed cleanup failure"; }
 part induction : GambitAssuranceRouting::ModelNeed { ref part :>> owner = GambitBuildAssurance::scheduler.component; attribute :>> obligationId = "WA-I"; attribute :>> kind = "induction"; attribute :>> subjectPath = "models/build/WillActionAdmission.lean"; attribute :>> subjectScope = "WillActionAdmission:preStoreLive;finalizeErrorStillDestroys;matchedNotGenerated;uuidNotMap;lastUseNotRetired;cleanupNotNotifier;receiptNeedsMaps;receiptNeedsRestore"; attribute :>> premise = "Eight conditional semantic-liveness/cohort/admission kernels; real action machine masks remain unavailable"; }
 part source : GambitAssuranceRouting::ModelNeed { ref part :>> owner = GambitBuildAssurance::scheduler.component; attribute :>> obligationId = "WA-S"; attribute :>> kind = "source-refinement"; attribute :>> subjectPath = "dev/architecture/toolchain/will-action-admission-design.org"; attribute :>> subjectScope = "WA-S:will-action-source"; attribute :>> premise = "Three retained cohorts, actual expanded SQLite action and UUID/line metadata; generation command/action C/dead mask/effect closure unresolved"; }
 part platform : GambitAssuranceRouting::ModelNeed { ref part :>> owner = GambitBuildAssurance::scheduler.component; attribute :>> obligationId = "WA-E"; attribute :>> kind = "environment-refinement"; attribute :>> subjectPath = "dev/architecture/toolchain/will-action-admission-design.org"; attribute :>> subjectScope = "WA-E:will-action-native"; attribute :>> premise = "Actual Darwin compile/link/runtime/SQLite library identity, complete root restore and publication unqualified; no implementation/native tests"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = GcDrainRetirementCut::source; }
}
