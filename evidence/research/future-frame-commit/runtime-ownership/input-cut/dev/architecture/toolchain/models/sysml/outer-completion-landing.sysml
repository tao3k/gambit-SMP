package OuterCompletionLanding {
 private import ScalarValues::*;
 part def Contract { attribute key : String; attribute anchor : String; attribute actionName : String; attribute lemmaName : String; attribute guardName : String; attribute duty : String; attribute status : String; }
 part contract0 : Contract { attribute :>> key = "derived-credit"; attribute :>> anchor = "setup.c:3383-3390,781-804; gambit.h.in:10376-10398"; attribute :>> actionName = "release"; attribute :>> lemmaName = "releaseSafe"; attribute :>> guardName = "s.pc[i]==8"; attribute :>> duty = "Release physical guard only after catcher restoration, marker invalidation, caller cleanup and roster handoff; an acknowledgement loss retains original custody"; attribute :>> status = "proposed stable completion receipt"; }
 part contract1 : Contract { attribute :>> key = "execution-owner"; attribute :>> anchor = "setup.c:3276-3419; pthread/pthread.c:52,115,125"; attribute :>> actionName = "enterBoundary"; attribute :>> lemmaName = "ownerInstalled"; attribute :>> guardName = "s.pc[i]==0"; attribute :>> duty = "Register durable VM/session and root custody before entering throw-capable native activation; guard identity is not continuation identity"; attribute :>> status = "current catcher wrappers do not register this owner"; }
 part contract2 : Contract { attribute :>> key = "call-catcher"; attribute :>> anchor = "setup.c:3358-3390; gambit.h.in:9981-9988"; attribute :>> actionName = "restoreCall"; attribute :>> lemmaName = "nestedPop"; attribute :>> guardName = "top(10*i+1)"; attribute :>> duty = "Pop only the current call catcher; matching return performs fp and PSR0 restoration, mismatched return propagates to restored outer catcher"; attribute :>> status = "current source ordering established; generated route unresolved"; }
 part contract3 : Contract { attribute :>> key = "storage-commit"; attribute :>> anchor = "setup.c:781-804,6425-6439; gambit.h.in:6377-6387"; attribute :>> actionName = "retireVm"; attribute :>> lemmaName = "vmRetirementExcludesHandles"; attribute :>> guardName = "s.stack.length()==0"; attribute :>> duty = "Exclude all active guards, retained exported handles, invocation authorities and roster debt before VM retirement; separate from run return"; attribute :>> status = "parent root/storage obligations remain open"; }
 part contract4 : Contract { attribute :>> key = "outer-catcher"; attribute :>> anchor = "gambit.h.in:10376-10398; _ptree2.scm:2902-3012,3239-3319"; attribute :>> actionName = "restoreOuter"; attribute :>> lemmaName = "catchRestored"; attribute :>> guardName = "top(10*i)"; attribute :>> duty = "Existing cleanup CFUN restores outer catcher before R_ALL_INL and conversion cleanup; AT_END lies inside TRY success arm and is not all-path finally"; attribute :>> status = "existing conversion cleanup retained"; }
 part contract5 : Contract { attribute :>> key = "marker-guard"; attribute :>> anchor = "setup.c:3406-3417; gambit.h.in:10043-10059; c_intf.c:6555-6563"; attribute :>> actionName = "completeMarker"; attribute :>> lemmaName = "markerCleared"; attribute :>> guardName = "s.pc[i]==4"; attribute :>> duty = "Stable guard owns allocated marker and invalidates it once on bypass; allocation failure must not invent an initialized marker"; attribute :>> status = "new all-path marker ownership needed"; }
 part contract6 : Contract { attribute :>> key = "reload-cleanup"; attribute :>> anchor = "gambit.h.in:10325-10398; _kernel.c:6004-6028"; attribute :>> actionName = "reloadRoots"; attribute :>> lemmaName = "reloaded"; attribute :>> guardName = "s.pc[i]==6"; attribute :>> duty = "Spill/reload, conversion resources, result/error propagation and any last caller PSTATE access precede stable release; physical guard cannot be replayed by continuation"; attribute :>> status = "consumer-specific obligations open"; }
 part contract7 : Contract { attribute :>> key = "run-participant"; attribute :>> anchor = "setup.c:781-804,812-835,6425-6439"; attribute :>> actionName = "transferRoster"; attribute :>> lemmaName = "rosterTransferred"; attribute :>> guardName = "s.debt[i]"; attribute :>> duty = "Secondary processor forwards error then participates forever in sync ops; only acknowledged roster/storage handoff can replace that duty"; attribute :>> status = "proposed transfer; not existing function return"; }
 part def Gain { attribute key : String; attribute avoided : String; attribute added : String; attribute condition : String; }
 part gain0 : Gain { attribute :>> key = "guard-coverage"; attribute :>> avoided = "Eliminate uncovered exceptional marker and session custody paths, conditional on complete generated boundary registration"; attribute :>> added = "One stable record per active physical activation, roots and catcher identity"; attribute :>> condition = "Safety gain; no current throughput claim. CFUN conversion cleanup already exists and cannot be counted again"; }
 part gain1 : Gain { attribute :>> key = "session-sharing"; attribute :>> avoided = "For b batches in s proven reusable sessions, at most b-s session acquisition/release pairs versus per-batch ownership"; attribute :>> added = "Still b claim/guard settlements, exported handle and invocation accounting"; attribute :>> condition = "Net work positive only saved lease work exceeds receipt, roots and retention costs; current code is not this comparator"; }
 part gain2 : Gain { attribute :>> key = "caller-retirement"; attribute :>> avoided = "Replace scattered marker/session completion policy only after all actual callers and native adapters migrate"; attribute :>> added = "Keep semantic return checks, argument cleanup, fp restoration and sync-op participation"; attribute :>> condition = "Can retire duplicate ownership policy, never erase required semantic cleanup or old-roster duties by assertion"; }
 part gain3 : Gain { attribute :>> key = "modern-c-baseline"; attribute :>> avoided = "Reuse GVM semantics and C ABI with generated typed guard descriptions"; attribute :>> added = "C11 publication, setjmp ABI and source-refinement obligations remain"; attribute :>> condition = "Zig offers no proved extra GC/session safety or runtime savings here; modern C remains required"; }
 part def Gate { attribute key : String; attribute qualified : Boolean; attribute duty : String; }
 part gate0 : Gate { attribute :>> key = "darwin-artifact-match"; attribute :>> qualified = false; attribute :>> duty = "Installed driver/header statically pinned; effective argv, environment overrides, compiler macro identity and checked-in _kernel.c/object relation unresolved"; }
 part gate1 : Gate { attribute :>> key = "smp-profile"; attribute :>> qualified = false; attribute :>> duty = "Installed header defaults to single-threaded VM; not qualification of current SMP processor roster or native ABI"; }
 part gate2 : Gate { attribute :>> key = "restore-graph"; attribute :>> qualified = false; attribute :>> duty = "Exact R1/SELF masks, same-host and host-switch, catcher stacks, generated return and exceptional edges complete"; }
 part gate3 : Gate { attribute :>> key = "unwind-cleanup"; attribute :>> qualified = false; attribute :>> duty = "Every throw/escape caller invalidates markers and settles roots exactly once; existing lexical cleanup is not sufficient proof"; }
 part gate4 : Gate { attribute :>> key = "continuation-export"; attribute :>> qualified = false; attribute :>> duty = "All external continuation holders and invocation leases registered without VM self-retention cycle; processor/arena migration proof"; }
 part gate5 : Gate { attribute :>> key = "c11-publication"; attribute :>> qualified = false; attribute :>> duty = "Execution lease establishment before immutable handoff publication and claim decrement; full C/builtin-setjmp refinement open"; }
 part gate6 : Gate { attribute :>> key = "native-retirement"; attribute :>> qualified = false; attribute :>> duty = "Parent root/roster/OS cleanup and inherited host attestation unresolved; no native admission"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Nine literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "OCL-H"; attribute :>> kind = "interleaving"; attribute :>> subjectPath = "models/build/outer_completion_landing.qnt"; attribute :>> subjectScope = "safe: nested native catcher stack, guard custody, abnormal marker completion, reload and roster debt, multi-shot handle lifetime"; attribute :>> premise = "Static declared SDK configuration is not matched SMP/native acceptance; abnormal guard and exported handle protocols are proposed"; }
 part induction : GambitAssuranceRouting::ModelNeed { ref part :>> owner = GambitBuildAssurance::planner.component; attribute :>> obligationId = "OCL-I"; attribute :>> kind = "induction"; attribute :>> subjectPath = "models/build/OuterCompletionLanding.lean"; attribute :>> subjectScope = "guard custody and completion preconditions preserved along abstract traces; nested pop and VM handle exclusion"; attribute :>> premise = "Static declared SDK configuration is not matched SMP/native acceptance; abnormal guard and exported handle protocols are proposed"; }
 part source : GambitAssuranceRouting::ModelNeed { ref part :>> owner = GambitBuildAssurance::planner.component; attribute :>> obligationId = "OCL-S"; attribute :>> kind = "source-refinement"; attribute :>> subjectPath = "dev/architecture/toolchain/outer-completion-landing-design.org"; attribute :>> subjectScope = "actual run/call/SFUN/CFUN/pthread/Tcl caller and landing paths, conditional modern C completion protocol"; attribute :>> premise = "Static declared SDK configuration is not matched SMP/native acceptance; abnormal guard and exported handle protocols are proposed"; }
 part platform : GambitAssuranceRouting::ModelNeed { ref part :>> owner = GambitBuildAssurance::planner.component; attribute :>> obligationId = "OCL-E"; attribute :>> kind = "environment-refinement"; attribute :>> subjectPath = "dev/architecture/toolchain/outer-completion-landing-design.org"; attribute :>> subjectScope = "effective Darwin argv and generated artifact, C11 publication and builtin-setjmp semantics"; attribute :>> premise = "Static declared SDK configuration is not matched SMP/native acceptance; abnormal guard and exported handle protocols are proposed"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = DecrementRestoreClosure::source; }
 part def ContractDependency { ref part dependent : Contract; ref part prerequisite : Contract; attribute reason : String; }
 part edge0 : ContractDependency { ref part :>> dependent = contract0; ref part :>> prerequisite = contract1; attribute :>> reason = "Physical owner must exist before eventual release"; }
 part edge1 : ContractDependency { ref part :>> dependent = contract2; ref part :>> prerequisite = contract1; attribute :>> reason = "Call catcher accesses original session"; }
 part edge2 : ContractDependency { ref part :>> dependent = contract5; ref part :>> prerequisite = contract2; attribute :>> reason = "After inner landing marker responsibility survives propagation"; }
 part edge3 : ContractDependency { ref part :>> dependent = contract4; ref part :>> prerequisite = contract2; attribute :>> reason = "Outer catch is reached after inner catcher restoration"; }
 part edge4 : ContractDependency { ref part :>> dependent = contract6; ref part :>> prerequisite = contract4; attribute :>> reason = "Outer catcher restoration precedes CFUN reload"; }
 part edge5 : ContractDependency { ref part :>> dependent = contract7; ref part :>> prerequisite = contract6; attribute :>> reason = "Caller roster duty remains after native root reload"; }
 part edge6 : ContractDependency { ref part :>> dependent = contract0; ref part :>> prerequisite = contract5; attribute :>> reason = "No live marker debt at final release"; }
 part edge7 : ContractDependency { ref part :>> dependent = contract0; ref part :>> prerequisite = contract6; attribute :>> reason = "No caller restoration debt at final release"; }
 part edge8 : ContractDependency { ref part :>> dependent = contract0; ref part :>> prerequisite = contract7; attribute :>> reason = "No untransferred roster debt at final release"; }
 part edge9 : ContractDependency { ref part :>> dependent = contract3; ref part :>> prerequisite = contract0; attribute :>> reason = "VM retirement excludes all uncompleted guards and handles"; }
}
