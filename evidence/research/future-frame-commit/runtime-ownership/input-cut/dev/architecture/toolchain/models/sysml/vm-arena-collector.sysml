package VMArenaCollector {
 private import ScalarValues::*;
 part def CallerSpec { attribute key : String; attribute anchor : String; attribute condition : String; }
 part caller0 : CallerSpec { attribute :>> key = "arena-setup"; attribute :>> anchor = "mem.c:4210-4247,6775-6805"; attribute :>> condition = "Initialize each arena once per epoch; positive still refcounts seed traversal; storage remains VM-owned after creator exit"; }
 part caller1 : CallerSpec { attribute :>> key = "discovery-and-workers"; attribute :>> anchor = "mem.c:3626-3647,6667-6771"; attribute :>> condition = "Discovering worker owns its local still queue; storage owner differs from scanner; claim and queue publication must preserve outstanding work"; }
 part caller2 : CallerSpec { attribute :>> key = "weak-and-sweep"; attribute :>> anchor = "mem.c:4039-4080,5032-5105,6872-6930"; attribute :>> condition = "PSTATE will-list membership needs separate handoff; retain weak/testator and GC-hash semantics; drain derived work before exactly-once arena sweep"; }
 part caller3 : CallerSpec { attribute :>> key = "capacity-census"; attribute :>> anchor = "mem.c:1556-1684,4387-4427,6256-6293,6367-6472"; attribute :>> condition = "Charge deferred words once; recompute physical live and quarantine words across VM arena membership, not current processors"; }
 part caller4 : CallerSpec { attribute :>> key = "history-consumers"; attribute :>> anchor = "mem.c:367-370,7000-7049,7509-7522; _kernel.scm:3999-4043,4126-4130"; attribute :>> condition = "Allocation history differs from occupancy; GC folds/unfolds baseline; archive departed contributions; process-statistics exposes distinct observables"; }
 part def ProtocolSpec { attribute key : String; attribute anchor : String; attribute condition : String; }
 part protocol0 : ProtocolSpec { attribute :>> key = "freeze-membership"; attribute :>> anchor = "setup.c:918-978; mem.c:7002-7009; proposed epoch cut"; attribute :>> condition = "StorageHandoffReceipt precedes creator exit; freeze VM arenas and worker tickets separately; no mid-epoch cleanup or ownership migration"; }
 part protocol1 : ProtocolSpec { attribute :>> key = "scan-work"; attribute :>> anchor = "mem.c:3626-3647,4210-4247,6686-6690"; attribute :>> condition = "Initialize marks once; discovered objects may queue on any authorized worker; queued, in-flight and unpublished work must all settle"; }
 part protocol2 : ProtocolSpec { attribute :>> key = "weak-closure"; attribute :>> anchor = "mem.c:4039-4080,5032-5105,6896-6902"; attribute :>> condition = "Strong quiescence precedes weak decisions; process_wills may add work; weak-derived closure precedes GC-hash cleanup and sweep"; }
 part protocol3 : ProtocolSpec { attribute :>> key = "sweep-authority"; attribute :>> anchor = "mem.c:4387-4427,6910-6930; c_intf.c:1683-1710"; attribute :>> condition = "One arena sweep authority; unreachable ordinary blocks freed; admitted asynchronous foreign shell remains charged until release settlement"; }
 part protocol4 : ProtocolSpec { attribute :>> key = "census-and-history"; attribute :>> anchor = "mem.c:6256-6293,6367-6472,7000-7049; _kernel.scm:4031-4043"; attribute :>> condition = "Census waits for all arena sweep receipts; count physical quarantine and reserves separately; signed baseline rebase and archived history survive departure"; }
 part def RouteSpec { attribute key : String; attribute anchor : String; attribute qntAction : String; attribute leanLemma : String; attribute condition : String; }
 part route0 : RouteSpec { attribute :>> key = "registration"; attribute :>> anchor = "setup.c:930-978; mem.c:4210-4247"; attribute :>> qntAction = "beginGC"; attribute :>> leanLemma = "retiredStillCounted"; attribute :>> condition = "Epoch arena membership includes VM-retained storage independently of current processor set"; }
 part route1 : RouteSpec { attribute :>> key = "termination"; attribute :>> anchor = "mem.c:6686-6690,6738-6767"; attribute :>> qntAction = "enterWeak"; attribute :>> leanLemma = "emptyQueueInsufficient"; attribute :>> condition = "Queue empty is insufficient while dequeued scan or publication debt remains"; }
 part route2 : RouteSpec { attribute :>> key = "coverage"; attribute :>> anchor = "mem.c:6896-6900,6928-6930"; attribute :>> qntAction = "enterCensus"; attribute :>> leanLemma = "sweepCoverage"; attribute :>> condition = "All weak closure and arena sweep authorities must complete before capacity publication"; }
 part route3 : RouteSpec { attribute :>> key = "retirement"; attribute :>> anchor = "mem.c:4400-4406; c_intf.c:1699-1707"; attribute :>> qntAction = "freeReleased"; attribute :>> leanLemma = "unknownRetains"; attribute :>> condition = "Unsettled foreign duty retains shell and capacity; no blind callback retry"; }
 part route4 : RouteSpec { attribute :>> key = "statistics"; attribute :>> anchor = "mem.c:6283-6293,7000-7049; _kernel.scm:3999-4043"; attribute :>> qntAction = "depart"; attribute :>> leanLemma = "archivePreserves"; attribute :>> condition = "Archive source history once; moving physical storage is not allocating bytes again"; }
 part def GainSpec { attribute key : String; attribute avoided : String; attribute added : String; attribute condition : String; }
 part gain0 : GainSpec { attribute :>> key = "vm-arena-authority"; attribute :>> avoided = "Creator-affinity bookkeeping and duplicate independent list/census ownership for migrated arenas"; attribute :>> added = "Arena registry, epoch tickets, exact setup/sweep assignment; O(N) body and edge scanning remains"; attribute :>> condition = "Work saving requires removed affinity/copy/rebinding greater than metadata and barriers; no collector speedup inferred"; }
 part gain1 : GainSpec { attribute :>> key = "honest-capacity"; attribute :>> avoided = "Dropped departed arena bytes, deferred double charge and foreign shell undercount"; attribute :>> added = "Charged/deferred/reserve/quarantine ledger and completed sweep census; retained unknown duties cost memory"; attribute :>> condition = "Capacity correctness is required even with zero speed gain; unbounded unresolved duties prevent bounded retention"; }
 part gain2 : GainSpec { attribute :>> key = "history-and-service"; attribute :>> avoided = "Repeated source-history recovery and processor lifetime pinning solely for statistics"; attribute :>> added = "Signed occupancy baselines or equivalent separated counters, archived history and explicit API adaptation"; attribute :>> condition = "Compiler span improves only when processor affinity was a real critical path; modern C supports contract without demonstrated Zig-specific gain"; }
 part def RefinementSpec { attribute key : String; attribute qntScope : String; attribute leanScope : String; attribute sourceDuty : String; }
 part refinement0 : RefinementSpec { attribute :>> key = "membership"; attribute :>> qntScope = "handoff;depart;beginGC"; attribute :>> leanScope = "retiredStillCounted;transferNotAllocation;archivePreserves"; attribute :>> sourceDuty = "Refine stable VM registry versus current PSTATE enumeration; all source/storage/root and native holder transfer prerequisites remain inherited"; }
 part refinement1 : RefinementSpec { attribute :>> key = "tracing"; attribute :>> qntScope = "dequeue;finishScan;enterWeak;processWeakKeep;enterSweep"; attribute :>> leanScope = "emptyQueueInsufficient;weakWorkBlocksSweep"; attribute :>> sourceDuty = "Refine real CAS winner-to-queue publication, body writeback, in-flight scan and chunk producers; no premature global termination"; }
 part refinement2 : RefinementSpec { attribute :>> key = "capacity"; attribute :>> qntScope = "sweep;enterCensus;finishGC;freeReleased"; attribute :>> leanScope = "sweepCoverage;deferredOnce;chargeQuarantine;censusMustFollowSweep;unknownRetains"; attribute :>> sourceDuty = "Prove exact survivor sets, foreign task ownership, reserve reconciliation and publish capacity after all sweep receipts"; }
 part refinement3 : RefinementSpec { attribute :>> key = "history"; attribute :>> qntScope = "handoff;depart;finishGC"; attribute :>> leanScope = "rebasePreserves;foldUnfold;signedBaselineRequired;netBenefit"; attribute :>> sourceDuty = "Define observed statistic per API/phase; signed baselines, departed history archival, F64 precision and source compatibility separately"; }
 part def GateSpec { attribute key : String; attribute qualified : Boolean; attribute condition : String; }
 part gate0 : GateSpec { attribute :>> key = "producer-closure"; attribute :>> qualified = false; attribute :>> condition = "Complete RC/still/root/weak/task/native producers and all permitted writers admitted"; }
 part gate1 : GateSpec { attribute :>> key = "vm-ownership"; attribute :>> qualified = false; attribute :>> condition = "Actual VM arena registry and parent storage/root handoff preserve bodies, RC allocations and destructor ownership"; }
 part gate2 : GateSpec { attribute :>> key = "gc-seal"; attribute :>> qualified = false; attribute :>> condition = "Real C CAS publication debt, dequeue/in-flight custody, termination and barrier refinement remain open"; }
 part gate3 : GateSpec { attribute :>> key = "scan-coverage"; attribute :>> qualified = false; attribute :>> condition = "Actual mark/reset, PSTATE weak-domain handoff, strong/weak/GC-hash, sweep and census adapters cover every target arena exactly once"; }
 part gate4 : GateSpec { attribute :>> key = "retirement"; attribute :>> qualified = false; attribute :>> condition = "Foreign affinity, task roots, pending leases and unknown outcomes settle; arena metadata reuse waits for empty storage, retired tickets and archived history"; }
 part gate5 : GateSpec { attribute :>> key = "source-replacement"; attribute :>> qualified = false; attribute :>> condition = "Per-PSTATE authority removed for migrated arenas only after complete producer/consumer migration"; }
 part gate6 : GateSpec { attribute :>> key = "platform"; attribute :>> qualified = false; attribute :>> condition = "Statistics API equivalence, overflow/F64 behavior, C memory model, host registration and native qualification remain open"; }
 attribute workspaceCount : Integer = 2;
 attribute actualAdmitted : Boolean = false;
 part history : GambitAssuranceRouting::ModelNeed { ref part :>> owner = GambitBuildAssurance::planner.component; attribute :>> obligationId = "AC-H"; attribute :>> kind = "interleaving"; attribute :>> subjectPath = "models/build/vm_arena_collector.qnt"; attribute :>> subjectScope = "vm_arena_collector:Test$"; attribute :>> premise = "Conditional target arena collector and statistics contract; actual source/native qualification remains open"; }
 part induction : GambitAssuranceRouting::ModelNeed { ref part :>> owner = GambitBuildAssurance::planner.component; attribute :>> obligationId = "AC-I"; attribute :>> kind = "induction"; attribute :>> subjectPath = "models/build/VMArenaCollector.lean"; attribute :>> subjectScope = "VMArenaCollector:rebasePreserves;archivePreserves;transferNotAllocation;foldUnfold;signedBaselineRequired;deferredOnce;emptyQueueInsufficient;weakWorkBlocksSweep;sweepCoverage;retiredStillCounted;unknownRetains;chargeQuarantine;censusMustFollowSweep;netBenefit"; attribute :>> premise = "Conditional target arena collector and statistics contract; actual source/native qualification remains open"; }
 part source : GambitAssuranceRouting::ModelNeed { ref part :>> owner = GambitBuildAssurance::planner.component; attribute :>> obligationId = "AC-S"; attribute :>> kind = "source-refinement"; attribute :>> subjectPath = "dev/architecture/toolchain/vm-arena-collector-design.org"; attribute :>> subjectScope = "AC-S:source"; attribute :>> premise = "Conditional target arena collector and statistics contract; actual source/native qualification remains open"; }
 part platform : GambitAssuranceRouting::ModelNeed { ref part :>> owner = GambitBuildAssurance::planner.component; attribute :>> obligationId = "AC-E"; attribute :>> kind = "environment-refinement"; attribute :>> subjectPath = "dev/architecture/toolchain/vm-arena-collector-design.org"; attribute :>> subjectScope = "AC-E:platform"; attribute :>> premise = "Conditional target arena collector and statistics contract; actual source/native qualification remains open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = StorageHandoff::source; }
}
