package RegistryAtomicCommit {
 private import ScalarValues::*;
 part def CommitSpec { attribute key : String; attribute anchor : String; attribute condition : String; }
 part commit0 : CommitSpec { attribute :>> key = "bundle"; attribute :>> anchor = "_env.scm:290-314; _ptree1.scm:2785-2847"; attribute :>> condition = "Replace five mutable root authorities with one immutable bundle: category roots, ordered event index, immutable receipts and authority identity"; }
 part commit1 : CommitSpec { attribute :>> key = "prepare"; attribute :>> anchor = "_env.scm:296-314; proposed seam"; attribute :>> condition = "Allocate/root candidate before publication; partial registry/index construction is private and cannot produce a committed receipt"; }
 part commit2 : CommitSpec { attribute :>> key = "existing-first"; attribute :>> anchor = "proposed event service"; attribute :>> condition = "Exact EventId plus canonical payload match returns original receipt before new-write predecessor/fence validation; collisions reject"; }
 part commit3 : CommitSpec { attribute :>> key = "publish"; attribute :>> anchor = "proposed modern C service seam"; attribute :>> condition = "Publish complete bundle once under fenced owner; compare expected base; no callback/allocation in final commit window; failed candidate never reruns expander"; }
 part commit4 : CommitSpec { attribute :>> key = "custody"; attribute :>> anchor = "_utils.scm:426-434; _thread.scm:4623-4639,4794-4812"; attribute :>> condition = "Bundle/result/candidate roots survive unknown delivery and saved continuations; process crash durability is not implied"; }
 part def IdentitySpec { attribute key : String; attribute anchor : String; attribute condition : String; }
 part identity0 : IdentitySpec { attribute :>> key = "returned-expansion"; attribute :>> anchor = "_ptree1.scm:664-669,1004-1012; gerbil/expander/core.ss:254-267"; attribute :>> condition = "Returned macro form is expanded after callback returns; fresh dynamic occurrence, not necessarily an on-stack nested child"; }
 part identity1 : IdentitySpec { attribute :>> key = "synchronous-child"; attribute :>> anchor = "gerbil/expander/core.ss:208-217,430-490"; attribute :>> condition = "A resolved expander may synchronously call expansion; suspend parent lane and commit child events in actual execution order; real iter child effect not established"; }
 part identity2 : IdentitySpec { attribute :>> key = "parent-resume"; attribute :>> anchor = "_ptree1.scm:1004-1012; proposed lane"; attribute :>> condition = "Parent-before, child and parent-after have distinct occurrence identities; source order does not sort by static parent position"; }
 part identity3 : IdentitySpec { attribute :>> key = "semantic-reentry"; attribute :>> anchor = "_thread.scm:4623-4639,4794-4812; _utils.scm:426-434"; attribute :>> condition = "Continuation restores execution, not heap registry rollback; before-store semantic replay needs fresh occurrence; transport retry retains EventId"; }
 part identity4 : IdentitySpec { attribute :>> key = "same-object-mismatch"; attribute :>> anchor = "_env.scm:327-343; proposed service"; attribute :>> condition = "Same EventId with different ordered payload/symbol/profile is a conflict, never a successful deduplicated delivery"; }
 part def RouteSpec { attribute key : String; attribute anchor : String; attribute qntAction : String; attribute leanLemma : String; attribute condition : String; }
 part route0 : RouteSpec { attribute :>> key = "whole-bundle"; attribute :>> anchor = "_env.scm:290-314; proposed seam"; attribute :>> qntAction = "publishBundle"; attribute :>> leanLemma = "wholeBundle"; attribute :>> condition = "Only complete registry/index/receipt candidate enters shared state"; }
 part route1 : RouteSpec { attribute :>> key = "old-receipt"; attribute :>> anchor = "proposed service; _env.scm:296-314"; attribute :>> qntAction = "lookupExisting"; attribute :>> leanLemma = "existingFirst"; attribute :>> condition = "Return stored receipt even if current registry is newer; payload identity must still match"; }
 part route2 : RouteSpec { attribute :>> key = "fence-base"; attribute :>> anchor = "proposed service"; attribute :>> qntAction = "publishBundle"; attribute :>> leanLemma = "fenceReject"; attribute :>> condition = "Unknown event needs current fenced authority and matching base; failed comparison has no registry effect"; }
 part route3 : RouteSpec { attribute :>> key = "nested-lineage"; attribute :>> anchor = "_ptree1.scm:664-669; gerbil/expander/core.ss:430-490"; attribute :>> qntAction = "enterChild"; attribute :>> leanLemma = "distinctOccurrences"; attribute :>> condition = "Real child/parent continuation occurrences are distinct; delivery retry is a separate request class"; }
 part route4 : RouteSpec { attribute :>> key = "retire"; attribute :>> anchor = "_thread.scm:4623-4639; _utils.scm:426-434"; attribute :>> qntAction = "finishDelivery"; attribute :>> leanLemma = "retainedRoots"; attribute :>> condition = "Lost acknowledgement and saved continuations retain custody"; }
 part def GainSpec { attribute key : String; attribute avoided : String; attribute added : String; attribute condition : String; }
 part gain0 : GainSpec { attribute :>> key = "one-commit-authority"; attribute :>> avoided = "Partial registry/journal states and duplicate writes during qualified retry"; attribute :>> added = "Immutable bundle/index, payload validation, candidate roots and fenced publication"; attribute :>> condition = "Correctness gain requires migrating actual readers and writers; no wrapper-only claim"; }
 part gain1 : GainSpec { attribute :>> key = "nested-session"; attribute :>> avoided = "Global serialization across independent contexts"; attribute :>> added = "Per-context effect lane, parent/child lineage and private expander state"; attribute :>> condition = "Actual independent ready work must exceed coordination cost; parent/child effects remain ordered"; }
 part gain2 : GainSpec { attribute :>> key = "cache-handoff"; attribute :>> avoided = "Reexecuting admitted pure macro work merely to recover acknowledgement"; attribute :>> added = "Event-index lookup, result custody and private syntax reconstruction"; attribute :>> condition = "Saved repeated work exceeds lookup/materialization/retention; arbitrary macro replay remains unqualified"; }
 part def RefinementSpec { attribute key : String; attribute qntScope : String; attribute leanScope : String; attribute sourceDuty : String; }
 part refinement0 : RefinementSpec { attribute :>> key = "commit"; attribute :>> qntScope = "prepareEvent;buildRegistry;buildIndex;publishBundle"; attribute :>> leanScope = "wholeBundle;baseReject;fenceReject"; attribute :>> sourceDuty = "Actual roots/GC/atomic handle publication must refine one state replacement"; }
 part refinement1 : RefinementSpec { attribute :>> key = "retry"; attribute :>> qntScope = "lookupExisting;retryLookup"; attribute :>> leanScope = "existingFirst;payloadConflict"; attribute :>> sourceDuty = "Exact stored receipt and canonical payload equivalence; no fabricated current-generation reply"; }
 part refinement2 : RefinementSpec { attribute :>> key = "nested"; attribute :>> qntScope = "enterChild;leaveChild;resumeBefore"; attribute :>> leanScope = "distinctOccurrences;lookupUnchanged"; attribute :>> sourceDuty = "Parser/expander PC, branch activation and actual effect order relation"; }
 part refinement3 : RefinementSpec { attribute :>> key = "custody"; attribute :>> qntScope = "abortCandidate;loseAck;finishDelivery"; attribute :>> leanScope = "retainedRoots;abortUnpublished;costPositive"; attribute :>> sourceDuty = "Continuation/native pins, failure outcome and root retirement plus work/span/memory"; }
 part def GateSpec { attribute key : String; attribute qualified : Boolean; attribute condition : String; }
 part gate0 : GateSpec { attribute :>> key = "all-consumers"; attribute :>> qualified = false; attribute :>> condition = "All five roots and direct/indirect parsing/writing consumers migrated"; }
 part gate1 : GateSpec { attribute :>> key = "bundle-source"; attribute :>> qualified = false; attribute :>> condition = "Actual immutable graph, symbol and registry/event/receipt simulation"; }
 part gate2 : GateSpec { attribute :>> key = "publish-memory"; attribute :>> qualified = false; attribute :>> condition = "Fencing/base linearization and stable GC-aware C publication proven"; }
 part gate3 : GateSpec { attribute :>> key = "event-lineage"; attribute :>> qualified = false; attribute :>> condition = "Exact nested and continuation PC/activation identity source refinement"; }
 part gate4 : GateSpec { attribute :>> key = "failure-custody"; attribute :>> qualified = false; attribute :>> condition = "Exceptions, unknown owner and multishot/native root lifetime closed"; }
 part gate5 : GateSpec { attribute :>> key = "retirement"; attribute :>> qualified = false; attribute :>> condition = "No second mutable global registry/handler/target authority remains"; }
 part gate6 : GateSpec { attribute :>> key = "platform"; attribute :>> qualified = false; attribute :>> condition = "Host attestation, runtime/native qualification and measured benefit remain separate"; }
 attribute workspaceCount : Integer = 2;
 attribute actualAdmitted : Boolean = false;
 part history : GambitAssuranceRouting::ModelNeed { ref part :>> owner = GambitBuildAssurance::planner.component; attribute :>> obligationId = "AC-H"; attribute :>> kind = "interleaving"; attribute :>> subjectPath = "models/build/registry_atomic_commit.qnt"; attribute :>> subjectScope = "registry_atomic_commit:Test$"; attribute :>> premise = "Conditional whole-bundle publication; actual lineage and GC/native closure remain open"; }
 part induction : GambitAssuranceRouting::ModelNeed { ref part :>> owner = GambitBuildAssurance::planner.component; attribute :>> obligationId = "AC-I"; attribute :>> kind = "induction"; attribute :>> subjectPath = "models/build/RegistryAtomicCommit.lean"; attribute :>> subjectScope = "RegistryAtomicCommit:wholeBundle;existingFirst;payloadConflict;baseReject;fenceReject;distinctOccurrences;lookupUnchanged;retainedRoots;abortUnpublished;costPositive"; attribute :>> premise = "Conditional whole-bundle publication; actual lineage and GC/native closure remain open"; }
 part source : GambitAssuranceRouting::ModelNeed { ref part :>> owner = GambitBuildAssurance::planner.component; attribute :>> obligationId = "AC-S"; attribute :>> kind = "source-refinement"; attribute :>> subjectPath = "dev/architecture/toolchain/registry-atomic-commit-design.org"; attribute :>> subjectScope = "AC-S:source"; attribute :>> premise = "Conditional whole-bundle publication; actual lineage and GC/native closure remain open"; }
 part platform : GambitAssuranceRouting::ModelNeed { ref part :>> owner = GambitBuildAssurance::planner.component; attribute :>> obligationId = "AC-E"; attribute :>> kind = "environment-refinement"; attribute :>> subjectPath = "dev/architecture/toolchain/registry-atomic-commit-design.org"; attribute :>> subjectScope = "AC-E:platform"; attribute :>> premise = "Conditional whole-bundle publication; actual lineage and GC/native closure remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = OrderedRegistryDelivery::source; }
}
