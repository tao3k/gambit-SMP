package DeviceCleanupWait {
 private import ScalarValues::*;
 part def Contract { attribute key : String; attribute anchor : String; attribute actionName : String; attribute lemmaName : String; attribute duty : String; attribute status : String; }
 part contract0 : Contract { attribute :>> key = "cursor"; attribute :>> anchor = "os_io.c:1625-1666,9920-9961; os_setup.c:203-221"; attribute :>> actionName = "qualifyRetry"; attribute :>> lemmaName = "retrySamePhase"; attribute :>> duty = "Resume only operation-qualified current phase; never re-enter detached device cleanup or infer kernel completion from CLOSED"; attribute :>> status = "adapter required"; }
 part contract1 : Contract { attribute :>> key = "wait-context"; attribute :>> anchor = "os_io.c:951-1004,11764-11828"; attribute :>> actionName = "prepareWait"; attribute :>> lemmaName = "generationMustMatch"; attribute :>> duty = "Rooted cursor, descriptor generation, native pin, desired interest and owner epoch survive wait/GC; FDSET borrow ends before dispatch"; attribute :>> status = "new managed record"; }
 part contract2 : Contract { attribute :>> key = "lost-wake"; attribute :>> anchor = "setup.c:86-90; os_io.c:1472-1549"; attribute :>> actionName = "arm"; attribute :>> lemmaName = "armCheckSafe"; attribute :>> duty = "Arm then recheck durable request/ready state; notification errors need a qualified level-channel guarantee; readiness survives interrupt"; attribute :>> status = "native wake proof open"; }
 part contract3 : Contract { attribute :>> key = "participant"; attribute :>> anchor = "setup.c:1049-1149; _kernel.scm:1448-1471"; attribute :>> actionName = "beginGc"; attribute :>> lemmaName = "rosterEveryParticipant"; attribute :>> duty = "Return from select is not service_sync_op; attach roots, join both old members, finish loop/NOOP and reload latest epoch"; attribute :>> status = "prior tree refinement required"; }
 part contract4 : Contract { attribute :>> key = "unknown"; attribute :>> anchor = "os_io.c:1603-1622,1640-1666; os_setup.c:203-221"; attribute :>> actionName = "unknownClose"; attribute :>> lemmaName = "unknownBlocksExit"; attribute :>> duty = "Separate retryable partial, consumed error and unknown native effects; unresolved outcomes retain owner and VM custody"; attribute :>> status = "profile dependent"; }
 part contract5 : Contract { attribute :>> key = "derived-credit"; attribute :>> anchor = "os_io.c:1886-1933,2011-2037,2299,2410"; attribute :>> actionName = "reserveChild"; attribute :>> lemmaName = "reserveConserves"; attribute :>> duty = "Reserve child before escape; lost enqueue keeps credit; independent child may outlive source but blocks VM cleanup"; attribute :>> status = "Windows branches conditional"; }
 part contract6 : Contract { attribute :>> key = "storage-commit"; attribute :>> anchor = "mem.c:684-699,4432-4450; setup.c:4572-4605"; attribute :>> actionName = "moveStorage"; attribute :>> lemmaName = "commitScanner"; attribute :>> duty = "Canonical RC/still/scan/census handoff at complete wait-free checkpoint; no live borrowed PSTATE pointers may migrate"; attribute :>> status = "source and memory order open"; }
 part contract7 : Contract { attribute :>> key = "vm-permit"; attribute :>> anchor = "setup.c:932-978; os_io.c:11808-11952; mem.c:4938-4966"; attribute :>> actionName = "cleanupVm"; attribute :>> lemmaName = "childBlocksVm"; attribute :>> duty = "Processor exit needs affinity/wait/roster closure; VM cleanup additionally requires every descendant/outcome/root/service lease drained"; attribute :>> status = "separate permits"; }
 part def Gain { attribute key : String; attribute avoided : String; attribute added : String; attribute condition : String; }
 part gain0 : Gain { attribute :>> key = "critical-path"; attribute :>> avoided = "Potentially blocking close removed from collective GC for qualified profiles"; attribute :>> added = "Capture, wait enrollment, root publication and owner dispatch"; attribute :>> condition = "Removed collective waiting must exceed added critical-path coordination; no numeric speedup established"; }
 part gain1 : Gain { attribute :>> key = "resume"; attribute :>> avoided = "Avoid repeated RD/WR work and duplicate wrapper release on retry"; attribute :>> added = "Cursor plus native-validity/outcome and desired-interest fields"; attribute :>> condition = "O(1) state per wait; only proven resumable operations may repeat current phase"; }
 part gain2 : Gain { attribute :>> key = "sharing"; attribute :>> avoided = "One managed wait/root/epoch protocol serves I/O, cleanup and FFI owners"; attribute :>> added = "Per-wait leases, tagged results and shared synchronization"; attribute :>> condition = "Reuse only if ownership and sync-op participation contracts coincide; a generic thread pool does not suffice"; }
 part gain3 : Gain { attribute :>> key = "language"; attribute :>> avoided = "Modern C retains Gambit C portability and generated adapters"; attribute :>> added = "C atomics, tagged structs, explicit guards and root schemas"; attribute :>> condition = "Zig cannot remove lifetime, wakeup, affinity or closure proof obligations; no mandatory Zig benefit demonstrated"; }
 part def Gate { attribute key : String; attribute qualified : Boolean; attribute duty : String; }
 part gate0 : Gate { attribute :>> key = "profile-coverage"; attribute :>> qualified = false; attribute :>> duty = "All virtual-close branches and aliases classified; retry/interest policy source-qualified"; }
 part gate1 : Gate { attribute :>> key = "wake-channel"; attribute :>> qualified = false; attribute :>> duty = "Ignored write errors, full pipe and platform memory ordering have a valid no-lost-wakeup refinement"; }
 part gate2 : Gate { attribute :>> key = "old-roster"; attribute :>> qualified = false; attribute :>> duty = "Every pending operation and resize round keeps both old participants serviceable"; }
 part gate3 : Gate { attribute :>> key = "root-adapter"; attribute :>> qualified = false; attribute :>> duty = "GC relocates all WaitContext, RC/still and result cells including nonzero processor"; }
 part gate4 : Gate { attribute :>> key = "source-replacement"; attribute :>> qualified = false; attribute :>> duty = "Stateful close adapter, root checkpoint and staged destruction remain unimplemented"; }
 part gate5 : Gate { attribute :>> key = "global-closure"; attribute :>> qualified = false; attribute :>> duty = "Child producers, thread affinity, outcome roots and module-global service leases fully closed"; }
 part gate6 : Gate { attribute :>> key = "platform"; attribute :>> qualified = false; attribute :>> duty = "Actual Darwin config/OpenSSL/OS close outcome, inherited attestation and C memory model unresolved"; }
 part history : GambitAssuranceRouting::ModelNeed { ref part :>> owner = GambitBuildAssurance::planner.component; attribute :>> obligationId = "DCW-H"; attribute :>> kind = "interleaving"; attribute :>> subjectPath = "models/build/device_cleanup_wait.qnt"; attribute :>> subjectScope = "safe: bounded cursor, durable wake, two old members and derived task"; attribute :>> premise = "Conditional formal study, source/platform refinement not granted"; }
 part induction : GambitAssuranceRouting::ModelNeed { ref part :>> owner = GambitBuildAssurance::planner.component; attribute :>> obligationId = "DCW-I"; attribute :>> kind = "induction"; attribute :>> subjectPath = "models/build/DeviceCleanupWait.lean"; attribute :>> subjectScope = "wake step conditions and debt transition induction; no whole source simulation"; attribute :>> premise = "Conditional formal study, source/platform refinement not granted"; }
 part source : GambitAssuranceRouting::ModelNeed { ref part :>> owner = GambitBuildAssurance::planner.component; attribute :>> obligationId = "DCW-S"; attribute :>> kind = "source-refinement"; attribute :>> subjectPath = "dev/architecture/toolchain/device-cleanup-wait-design.org"; attribute :>> subjectScope = "actual device wait / scheduler / GC / close profiles"; attribute :>> premise = "Conditional formal study, source/platform refinement not granted"; }
 part platform : GambitAssuranceRouting::ModelNeed { ref part :>> owner = GambitBuildAssurance::planner.component; attribute :>> obligationId = "DCW-E"; attribute :>> kind = "environment-refinement"; attribute :>> subjectPath = "dev/architecture/toolchain/device-cleanup-wait-design.org"; attribute :>> subjectScope = "Darwin wakeup, native outcome and C memory order"; attribute :>> premise = "Conditional formal study, source/platform refinement not granted"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = ForeignCleanupClosure::source; }
 part def ContractDependency { ref part dependent : Contract; ref part prerequisite : Contract; attribute reason : String; }
 part edge0 : ContractDependency { ref part :>> dependent = contract1; ref part :>> prerequisite = contract0; attribute :>> reason = "Wait captures exact close cursor"; }
 part edge1 : ContractDependency { ref part :>> dependent = contract1; ref part :>> prerequisite = contract4; attribute :>> reason = "Native outcome controls admissible resume"; }
 part edge2 : ContractDependency { ref part :>> dependent = contract2; ref part :>> prerequisite = contract1; attribute :>> reason = "Arm requires pinned complete context"; }
 part edge3 : ContractDependency { ref part :>> dependent = contract3; ref part :>> prerequisite = contract2; attribute :>> reason = "Wake reaches serviceable old owner"; }
 part edge4 : ContractDependency { ref part :>> dependent = contract3; ref part :>> prerequisite = contract1; attribute :>> reason = "Roots and borrow release precede GC"; }
 part edge5 : ContractDependency { ref part :>> dependent = contract6; ref part :>> prerequisite = contract1; attribute :>> reason = "No PSTATE borrow crosses transfer"; }
 part edge6 : ContractDependency { ref part :>> dependent = contract7; ref part :>> prerequisite = contract6; attribute :>> reason = "Storage scanner/census handoff acknowledged"; }
 part edge7 : ContractDependency { ref part :>> dependent = contract7; ref part :>> prerequisite = contract5; attribute :>> reason = "All child work accounted and drained for VM"; }
 part edge8 : ContractDependency { ref part :>> dependent = contract7; ref part :>> prerequisite = contract4; attribute :>> reason = "Unknown native effects block retirement"; }
 part edge9 : ContractDependency { ref part :>> dependent = contract7; ref part :>> prerequisite = contract3; attribute :>> reason = "Loop closure and old roster receipt precede exit"; }
}
