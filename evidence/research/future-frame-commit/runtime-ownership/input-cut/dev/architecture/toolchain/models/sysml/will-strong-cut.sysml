package WillStrongCut {
 private import ScalarValues::*;
 part def CallerSpec { attribute key : String; attribute anchor : String; attribute condition : String; }
 part caller0 : CallerSpec { attribute :>> key = "shared-registration"; attribute :>> anchor = "gambit.h.in:6014-6021; _thread.scm:690-739,1461-1504"; attribute :>> condition = "Distinct wills can register in current PSTATE lists with same VM testator; shared container cleared after publication; exact native root liveness remains a premise"; }
 part caller1 : CallerSpec { attribute :>> key = "strong-closure"; attribute :>> anchor = "setup.c:1028-1029,1068-1105,1132-1198; mem.c:4039-4063,6843-6864,7014-7016"; attribute :>> condition = "Sync dispatch runs collector per PSTATE; rooted wills mark noncapturing actions while testator stays weak; strong barrier precedes concurrent local weak functions"; }
 part caller2 : CallerSpec { attribute :>> key = "late-classifier"; attribute :>> anchor = "mem.c:3990-3998,4997-5046"; attribute :>> condition = "UNMARKED reads current header/mark; local classifier finishes before its own weak preservation, not before every other processor preservation"; }
 part caller3 : CallerSpec { attribute :>> key = "early-publisher"; attribute :>> anchor = "mem.c:3578-3609,3640-3646,5068-5099,6896-6900"; attribute :>> condition = "One processor may weak-mark shared testator before other classifies; completed-copy replay avoids relying on unfinished payload publication"; }
 part caller4 : CallerSpec { attribute :>> key = "semantics-and-platform"; attribute :>> anchor = "doc/gambit.txi:9289-9316; gambit.h.in:11014-11066"; attribute :>> condition = "Manual grounds strong reachability and resurrection; source witness is conditional intended-memory control flow, not configured native reproduction or C memory-model proof"; }
 part def ProtocolSpec { attribute key : String; attribute anchor : String; attribute condition : String; }
 part protocol0 : ProtocolSpec { attribute :>> key = "input-witness"; attribute :>> anchor = "gambit.h.in:6014-6021; _thread.scm:694-704,1461-1504"; attribute :>> condition = "Same VM, two distinct lists/wills and one allocated testator; root wills but not testator/action captures; helper source and temporary root retirement must qualify"; }
 part protocol1 : ProtocolSpec { attribute :>> key = "source-interference"; attribute :>> anchor = "mem.c:5046,5088-5099,7016-7023"; attribute :>> condition = "P0 classify -> publish and finish testator marking -> P1 classify sees marked; valid source-model steps can omit P1 from this epoch selection"; }
 part protocol2 : ProtocolSpec { attribute :>> key = "decision-cut"; attribute :>> anchor = "proposed modern C phase split; mem.c:4997-5105"; attribute :>> condition = "Freeze all domains; classify after certified global strong closure and before weak mutation; reuse existing strong/weak barrier only if its prerequisites refine"; }
 part protocol3 : ProtocolSpec { attribute :>> key = "weak-publication"; attribute :>> anchor = "mem.c:6896-6902; proposed cut guard"; attribute :>> condition = "Weak publish allowed only after global decision receipt; preserve all testator/copy/scan work and existing list ordering; atomic reads alone do not repair semantics"; }
 part protocol4 : ProtocolSpec { attribute :>> key = "semantic-repair"; attribute :>> anchor = "doc/gambit.txi:9289-9316; proposed epoch semantics"; attribute :>> condition = "Make selection independent of weak preservation order for fixed strong snapshot; changes observable callback/resurrection timing; not a transparent list relocation optimization"; }
 part def RouteSpec { attribute key : String; attribute anchor : String; attribute qntAction : String; attribute leanLemma : String; attribute condition : String; }
 part route0 : RouteSpec { attribute :>> key = "registration"; attribute :>> anchor = "gambit.h.in:6014-6021; _thread.scm:694-704"; attribute :>> qntAction = "register"; attribute :>> leanLemma = "immediateNever"; attribute :>> condition = "Actual registration records distinct PSTATE ownership; same testator identity and valid same-VM root preconditions required"; }
 part route1 : RouteSpec { attribute :>> key = "classification"; attribute :>> anchor = "mem.c:3990-3998,5011-5026"; attribute :>> qntAction = "classify"; attribute :>> leanLemma = "preWeakStable"; attribute :>> condition = "Current UNMARKED differs after a weak mark; retain strong-snapshot result before preservation starts"; }
 part route2 : RouteSpec { attribute :>> key = "coverage"; attribute :>> anchor = "mem.c:5046,6898; proposed all-domain cut"; attribute :>> qntAction = "sealCut"; attribute :>> leanLemma = "outstandingBlocksCut"; attribute :>> condition = "Exact all-domain coverage plus matching epoch is prerequisite; processor count alone is insufficient for retained VM domains"; }
 part route3 : RouteSpec { attribute :>> key = "publication"; attribute :>> anchor = "mem.c:3578-3609,3640-3646,5068-5099"; attribute :>> qntAction = "publishWeak"; attribute :>> leanLemma = "movableObservationChanges"; attribute :>> condition = "Guard every weak testator publisher, not just first processor; preserve distinct unfinished-copy and still-scan obligations"; }
 part route4 : RouteSpec { attribute :>> key = "completion"; attribute :>> anchor = "mem.c:6686-6690,6898-6902,7023"; attribute :>> qntAction = "complete"; attribute :>> leanLemma = "copyDebtBlocks"; attribute :>> condition = "Global classification does not imply weak work completion; wait for all copy/scan custody before later phases"; }
 part def GainSpec { attribute key : String; attribute avoided : String; attribute added : String; attribute condition : String; }
 part gain0 : GainSpec { attribute :>> key = "semantic-determinism"; attribute :>> avoided = "Selection differences caused solely by weak preservation racing a late classifier"; attribute :>> added = "Global decision receipt and fixed cohort lifetime; barrier reuse conditional on strong-closure proof; callbacks may run earlier"; attribute :>> condition = "Correctness/semantic repair is primary; no automatic positive CPU-work saving against a correct baseline"; }
 part gain1 : GainSpec { attribute :>> key = "phase-separation"; attribute :>> avoided = "Repeated ambiguous classification and creator affinity in future VM weak domains"; attribute :>> added = "One classification walk retained; separate nonallocating decision phase, then existing preserve/rebuild work"; attribute :>> condition = "Classification remains O(W); zero or one additional barrier depending on certified reuse; skew and receipt bookkeeping still count"; }
 part gain2 : GainSpec { attribute :>> key = "bounded-retention"; attribute :>> avoided = "Avoidable missed selection may delay action or permit resurrection to suppress later selection"; attribute :>> added = "Earlier dispatch and its resource/continuation costs; retention still depends on action outcome"; attribute :>> condition = "No fixed bytes/latency benefit; compare equivalent epoch semantics, not faster execution of an incorrect outcome"; }
 part def RefinementSpec { attribute key : String; attribute qntScope : String; attribute leanScope : String; attribute sourceDuty : String; }
 part refinement0 : RefinementSpec { attribute :>> key = "inputs"; attribute :>> qntScope = "register;strongClose"; attribute :>> leanScope = "immediateNever;strongNever"; attribute :>> sourceDuty = "Prove two actual PSTATE registrations share canonical object; noncapturing actions, dead temporary aliases, rooted wills and full strong closure"; }
 part refinement1 : RefinementSpec { attribute :>> key = "witness"; attribute :>> qntScope = "classify;publishWeak;finishCopy;drainStill"; attribute :>> leanScope = "movableObservationChanges;stillObservationChanges"; attribute :>> sourceDuty = "Refine existing no-intermediate-barrier control flow and header/mark observation; source SC witness remains separate from native/C11 execution qualification"; }
 part refinement2 : RefinementSpec { attribute :>> key = "cut"; attribute :>> qntScope = "classify;sealCut;publishWeak"; attribute :>> leanScope = "outstandingBlocksCut;validCutIncludes;selectedMembership;orderIndependent;preWeakStable;staleRejected"; attribute :>> sourceDuty = "Exact phase membership, disjoint owner lists, release/acquire phase publication and all weak producers gated; no callback or allocation inside classifier"; }
 part refinement3 : RefinementSpec { attribute :>> key = "finish"; attribute :>> qntScope = "finishCopy;drainStill;complete"; attribute :>> leanScope = "copyDebtBlocks;netBenefit"; attribute :>> sourceDuty = "Real queue/copy/in-flight work, resize membership, target VM weak domains and action/resurrection behavior require source and platform refinement"; }
 part def GateSpec { attribute key : String; attribute qualified : Boolean; attribute condition : String; }
 part gate0 : GateSpec { attribute :>> key = "producer-closure"; attribute :>> qualified = false; attribute :>> condition = "Complete shared-object publication, writer closure and generated root/temporary retirement evidence for a concrete native program"; }
 part gate1 : GateSpec { attribute :>> key = "vm-ownership"; attribute :>> qualified = false; attribute :>> condition = "Current two-processor witness extended to retained VM domains with exact stable ownership and canonical testator identity"; }
 part gate2 : GateSpec { attribute :>> key = "gc-seal"; attribute :>> qualified = false; attribute :>> condition = "All decision domains classified before every weak mutation; C happens-before and selected atomic/header representation qualified"; }
 part gate3 : GateSpec { attribute :>> key = "scan-coverage"; attribute :>> qualified = false; attribute :>> condition = "Actual forwarding, will tags, weak publishers, copy/scan termination and empty-domain acknowledgements refined"; }
 part gate4 : GateSpec { attribute :>> key = "retirement"; attribute :>> qualified = false; attribute :>> condition = "Resurrection, explicit calls, exception/continuation contexts and shutdown preserve chosen epoch semantics"; }
 part gate5 : GateSpec { attribute :>> key = "source-replacement"; attribute :>> qualified = false; attribute :>> condition = "Fused local classify-and-preserve retired only after all call sites use shared phase authority"; }
 part gate6 : GateSpec { attribute :>> key = "platform"; attribute :>> qualified = false; attribute :>> condition = "Configured SMP/ABI, exact generated roots, C memory model, host attestation and native reproduction remain open"; }
 attribute workspaceCount : Integer = 2;
 attribute actualAdmitted : Boolean = false;
 part history : GambitAssuranceRouting::ModelNeed { ref part :>> owner = GambitBuildAssurance::planner.component; attribute :>> obligationId = "WS-H"; attribute :>> kind = "interleaving"; attribute :>> subjectPath = "models/build/will_strong_cut.qnt"; attribute :>> subjectScope = "will_strong_cut:Test$"; attribute :>> premise = "Source-seam counterexample and conditional modern C decision cut; native and C memory-model qualification remain open"; }
 part induction : GambitAssuranceRouting::ModelNeed { ref part :>> owner = GambitBuildAssurance::planner.component; attribute :>> obligationId = "WS-I"; attribute :>> kind = "induction"; attribute :>> subjectPath = "models/build/WillStrongCut.lean"; attribute :>> subjectScope = "WillStrongCut:movableObservationChanges;stillObservationChanges;immediateNever;strongNever;outstandingBlocksCut;validCutIncludes;selectedMembership;orderIndependent;preWeakStable;staleRejected;copyDebtBlocks;netBenefit"; attribute :>> premise = "Source-seam counterexample and conditional modern C decision cut; native and C memory-model qualification remain open"; }
 part source : GambitAssuranceRouting::ModelNeed { ref part :>> owner = GambitBuildAssurance::planner.component; attribute :>> obligationId = "WS-S"; attribute :>> kind = "source-refinement"; attribute :>> subjectPath = "dev/architecture/toolchain/will-strong-cut-design.org"; attribute :>> subjectScope = "WS-S:source"; attribute :>> premise = "Source-seam counterexample and conditional modern C decision cut; native and C memory-model qualification remain open"; }
 part platform : GambitAssuranceRouting::ModelNeed { ref part :>> owner = GambitBuildAssurance::planner.component; attribute :>> obligationId = "WS-E"; attribute :>> kind = "environment-refinement"; attribute :>> subjectPath = "dev/architecture/toolchain/will-strong-cut-design.org"; attribute :>> subjectScope = "WS-E:platform"; attribute :>> premise = "Source-seam counterexample and conditional modern C decision cut; native and C memory-model qualification remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = WillDomainMigration::source; }
}
