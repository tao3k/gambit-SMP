package NativeWakeChannel {
 private import ScalarValues::*;
 part def Contract { attribute key : String; attribute anchor : String; attribute actionName : String; attribute lemmaName : String; attribute duty : String; attribute status : String; }
 part contract0 : Contract { attribute :>> key = "derived-credit"; attribute :>> anchor = "setup.c:66-106,283,392,1147; os_setup.c:3037-3056"; attribute :>> actionName = "publish"; attribute :>> lemmaName = "publicationConserves"; attribute :>> duty = "Requests own durable identities independently of pipe bytes; notification retries never republish semantic work"; attribute :>> status = "new shared authority"; }
 part contract1 : Contract { attribute :>> key = "full"; attribute :>> anchor = "os_io.c:1472-1495,1543; os_setup.c:424-485"; attribute :>> actionName = "writeFull"; attribute :>> lemmaName = "fullRetainsWake"; attribute :>> duty = "Full-channel coalescing requires pinned endpoints, unique owner drain and mandatory pending recheck after drain"; attribute :>> status = "kernel/profile premise"; }
 part contract2 : Contract { attribute :>> key = "eintr"; attribute :>> anchor = "os_io.c:1543; os_setup.c:203-221"; attribute :>> actionName = "writeEintr"; attribute :>> lemmaName = "eintrRetainsOwner"; attribute :>> duty = "Interrupted notification retains generation pin and delivery credit; retry same wake right or use qualified rescue"; attribute :>> status = "write adapter required"; }
 part contract3 : Contract { attribute :>> key = "storage-commit"; attribute :>> anchor = "os_io.c:11780-11828; os_setup.c:468-486"; attribute :>> actionName = "acquire"; attribute :>> lemmaName = "takePinRetainsGeneration"; attribute :>> duty = "Acquire endpoint plus generation under lifecycle gate; both descriptors remain alive through syscall and response settlement"; attribute :>> status = "no check-then-pin race"; }
 part contract4 : Contract { attribute :>> key = "arm"; attribute :>> anchor = "os_io.c:973-1004,1472-1528; _thread.scm:2530-2562"; attribute :>> actionName = "block"; attribute :>> lemmaName = "pendingBlocksSleep"; attribute :>> duty = "Arm and recheck durable pending under owner gate; drain does not clear request identity; finite wait bounds missed notification detection conditionally"; attribute :>> status = "new native wait contract"; }
 part contract5 : Contract { attribute :>> key = "failure"; attribute :>> anchor = "os_io.c:1543; os_time.c:987-996; os_tty.c:8700-8713"; attribute :>> actionName = "writeHard"; attribute :>> lemmaName = "failureRetainsCustody"; attribute :>> duty = "Hard/unknown notification keeps producer or rescue custody; signal lane uses prepinned lifetime and quiescence instead of mutex acquisition"; attribute :>> status = "signal lane refinement open"; }
 part contract6 : Contract { attribute :>> key = "participant"; attribute :>> anchor = "setup.c:1049-1149; _kernel.scm:1448-1471"; attribute :>> actionName = "enterCollective"; attribute :>> lemmaName = "rosterEveryParticipant"; attribute :>> duty = "Return from OS wait then release borrow, publish roots and join old roster; acknowledge only selected request snapshot"; attribute :>> status = "prior sync-op contract"; }
 part contract7 : Contract { attribute :>> key = "retirement"; attribute :>> anchor = "os_io.c:11808-11828; setup.c:932-978; gambit.h.in:11327-11340"; attribute :>> actionName = "closeEndpoints"; attribute :>> lemmaName = "pinBlocksClose"; attribute :>> duty = "Withdraw admission, drain producer/wait/signal users, settle request and prior roster receipts, then close; uncertain close quarantines generation"; attribute :>> status = "staged destruction"; }
 part def Gain { attribute key : String; attribute avoided : String; attribute added : String; attribute condition : String; }
 part gain0 : Gain { attribute :>> key = "coalescing"; attribute :>> avoided = "B notification bytes need not encode N semantic requests"; attribute :>> added = "Durable request ledger and post-drain recheck"; attribute :>> condition = "For N requests an already-full channel may add zero bytes; request multiplicity is preserved by semantic ledger, not byte count"; }
 part gain1 : Gain { attribute :>> key = "latency"; attribute :>> avoided = "Avoid indefinite old-roster stall from a lost notification under admitted fallback"; attribute :>> added = "Native wait timeout/recheck and scheduling overhead"; attribute :>> condition = "Conditional detection bound T plus scheduling delay; not measured latency or arbitrary OS progress guarantee"; }
 part gain2 : Gain { attribute :>> key = "lifetime"; attribute :>> avoided = "Avoid fd-generation ABA, premature endpoint close and duplicate semantic submission"; attribute :>> added = "Producer/wait pins, signal-generation fence and close journal"; attribute :>> condition = "O(P+W+S) control records plus payload roots; retained unknown close may quarantine VM services"; }
 part gain3 : Gain { attribute :>> key = "language"; attribute :>> avoided = "One modern C wake authority can serve cleanup, FFI waits and scheduler"; attribute :>> added = "Typed outcomes, control gate, lock-free signal ingress where qualified"; attribute :>> condition = "Zig cannot remove synchronization, signal ABI, root or retirement obligations; extra language value not established"; }
 part def Gate { attribute key : String; attribute qualified : Boolean; attribute duty : String; }
 part gate0 : Gate { attribute :>> key = "native-write"; attribute :>> qualified = false; attribute :>> duty = "Exact Darwin pipe/socketpair semantics, return classification and signal interruption refined"; }
 part gate1 : Gate { attribute :>> key = "memory-order"; attribute :>> qualified = false; attribute :>> duty = "All participating accesses migrated together; volatile plus fence is not a C11 proof; weak-memory/source simulation open"; }
 part gate2 : Gate { attribute :>> key = "signal-lifetime"; attribute :>> qualified = false; attribute :>> duty = "Signal-safe immutable endpoint, required lock-free atomics, route withdrawal and all-thread handler grace period qualified"; }
 part gate3 : Gate { attribute :>> key = "generation-pin"; attribute :>> qualified = false; attribute :>> duty = "Raw fd aliases, dup/close paths and PSTATE reuse all obey endpoint gate"; }
 part gate4 : Gate { attribute :>> key = "finite-fallback"; attribute :>> qualified = false; attribute :>> duty = "Actual monotonic native timeout and scheduler fairness support detection; unqualified infinite waits refused"; }
 part gate5 : Gate { attribute :>> key = "old-roster"; attribute :>> qualified = false; attribute :>> duty = "Root handoff, every participant, request selection/NOOP and resize deferral refined"; }
 part gate6 : Gate { attribute :>> key = "retirement"; attribute :>> qualified = false; attribute :>> duty = "Sender/wait/signal users, unknown close, VM/global services and inherited attestation remain unqualified"; }
 part history : GambitAssuranceRouting::ModelNeed { ref part :>> owner = GambitBuildAssurance::planner.component; attribute :>> obligationId = "NWC-H"; attribute :>> kind = "interleaving"; attribute :>> subjectPath = "models/build/native_wake_channel.qnt"; attribute :>> subjectScope = "safe: two thread producers, one prepinned signal, one channel generation and two old members"; attribute :>> premise = "Conditional research: semantic custody is separate from notification delivery and progress"; }
 part induction : GambitAssuranceRouting::ModelNeed { ref part :>> owner = GambitBuildAssurance::planner.component; attribute :>> obligationId = "NWC-I"; attribute :>> kind = "induction"; attribute :>> subjectPath = "models/build/NativeWakeChannel.lean"; attribute :>> subjectScope = "notification debt induction, conditional wake ownership, pin/generation and SC-order lemmas"; attribute :>> premise = "Conditional research: semantic custody is separate from notification delivery and progress"; }
 part source : GambitAssuranceRouting::ModelNeed { ref part :>> owner = GambitBuildAssurance::planner.component; attribute :>> obligationId = "NWC-S"; attribute :>> kind = "source-refinement"; attribute :>> subjectPath = "dev/architecture/toolchain/native-wake-channel-design.org"; attribute :>> subjectScope = "actual writer/drain/close/signal paths and source refinement"; attribute :>> premise = "Conditional research: semantic custody is separate from notification delivery and progress"; }
 part platform : GambitAssuranceRouting::ModelNeed { ref part :>> owner = GambitBuildAssurance::planner.component; attribute :>> obligationId = "NWC-E"; attribute :>> kind = "environment-refinement"; attribute :>> subjectPath = "dev/architecture/toolchain/native-wake-channel-design.org"; attribute :>> subjectScope = "Darwin kernel outcomes, C11 synchronization and signal grace period"; attribute :>> premise = "Conditional research: semantic custody is separate from notification delivery and progress"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = DeviceCleanupWait::source; }
 part def ContractDependency { ref part dependent : Contract; ref part prerequisite : Contract; attribute reason : String; }
 part edge0 : ContractDependency { ref part :>> dependent = contract1; ref part :>> prerequisite = contract0; attribute :>> reason = "Bytes are not semantic request debt"; }
 part edge1 : ContractDependency { ref part :>> dependent = contract1; ref part :>> prerequisite = contract3; attribute :>> reason = "Full-channel witness requires pinned lifetime"; }
 part edge2 : ContractDependency { ref part :>> dependent = contract2; ref part :>> prerequisite = contract3; attribute :>> reason = "Retry retains exact endpoint generation"; }
 part edge3 : ContractDependency { ref part :>> dependent = contract4; ref part :>> prerequisite = contract0; attribute :>> reason = "Recheck sees published semantic requests"; }
 part edge4 : ContractDependency { ref part :>> dependent = contract4; ref part :>> prerequisite = contract1; attribute :>> reason = "Drain is followed by durable recheck"; }
 part edge5 : ContractDependency { ref part :>> dependent = contract5; ref part :>> prerequisite = contract3; attribute :>> reason = "Failure retains endpoint lifetime"; }
 part edge6 : ContractDependency { ref part :>> dependent = contract6; ref part :>> prerequisite = contract4; attribute :>> reason = "Wake reaches rooted old owner"; }
 part edge7 : ContractDependency { ref part :>> dependent = contract7; ref part :>> prerequisite = contract3; attribute :>> reason = "Pins drain before descriptor close"; }
 part edge8 : ContractDependency { ref part :>> dependent = contract7; ref part :>> prerequisite = contract5; attribute :>> reason = "Signal grace and rescue responsibility settled"; }
 part edge9 : ContractDependency { ref part :>> dependent = contract7; ref part :>> prerequisite = contract6; attribute :>> reason = "Old roster receipt precedes retirement"; }
}
