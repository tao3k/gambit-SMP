package RootProducerCensus {
 private import ScalarValues::*;
 part def CallerSpec { attribute key : String; attribute anchor : String; attribute condition : String; }
 part caller0 : CallerSpec { attribute :>> key = "rc-owner"; attribute :>> anchor = "mem.c:277,306,723-825,3969-3986,6845-6850"; attribute :>> condition = "Registration binds to current PSTATE rc_head, but strong scan invokes mark_rc only on processor zero; nonzero RC with a unique movable payload cannot be admitted by current closure evidence"; }
 part caller1 : CallerSpec { attribute :>> key = "callback-entry"; attribute :>> anchor = "c_intf.c:6511-6561; gambit.h.in:10043-10059; os_dyn.c:744-769"; attribute :>> condition = "Explicit proc_or_false is not materialized before marker allocation; TODO remains; implicit closure path relies on architecture-gated RC and non-thread-local c_closure_self"; }
 part caller2 : CallerSpec { attribute :>> key = "still-root"; attribute :>> anchor = "mem.c:1490-1496,1647,1730-1737,4210-4247,6798-6805; tcltk.scm:297-337"; attribute :>> condition = "Every participating processor seeds nonzero-refcount still objects during setup; Tcl vector starts with external protection independently of its RC payload"; }
 part caller3 : CallerSpec { attribute :>> key = "local-drain"; attribute :>> anchor = "mem.c:3504-3663,3667-3813,4196-4204,4235-4383,6682-6767"; attribute :>> condition = "A counted owner remains responsible for synchronous copy, inline tail, alloc cursor, popped still node and dequeued chunk until descendants and cursor advances settle"; }
 part caller4 : CallerSpec { attribute :>> key = "gc-entry"; attribute :>> anchor = "setup.c:1022-1029,1065-1105; mem.c:3458-3459,7002-7023"; attribute :>> condition = "Sync-op dispatch and setup barriers establish source rendezvous seams; they do not themselves close arbitrary external root mutation or prove generated register maps"; }
 part def ProtocolSpec { attribute key : String; attribute anchor : String; attribute condition : String; }
 part protocol0 : ProtocolSpec { attribute :>> key = "manifest"; attribute :>> anchor = "mem.c:6511-6664,6798-6864"; attribute :>> condition = "Enumerate ten root families plus callback admission and weak-phase exclusions; exact physical slot completeness and supported configuration remain separate obligations"; }
 part protocol1 : ProtocolSpec { attribute :>> key = "writer-close"; attribute :>> anchor = "mem.c:723-825; setup.c:5900-5922"; attribute :>> condition = "Close new register/write/read/unlink/exit admission, drain accepted operations without holding GC-required locks, then freeze root membership and payload versions; current API does not implement this protocol"; }
 part protocol2 : ProtocolSpec { attribute :>> key = "stable-scan"; attribute :>> anchor = "mem.c:3981-3984,6511-6664"; attribute :>> condition = "Scanner records stable owner, epoch and payload version; a value read lease alone cannot prevent set_data_rc or unlink; stale snapshot never issues a receipt"; }
 part protocol3 : ProtocolSpec { attribute :>> key = "idle-custody"; attribute :>> anchor = "mem.c:6682-6767"; attribute :>> condition = "idle decrements only after own root producers and all private/published/scanner/derived responsibilities settle; active credit transfers before a thief scans"; }
 part protocol4 : ProtocolSpec { attribute :>> key = "receipt"; attribute :>> anchor = "mem.c:6864,7016"; attribute :>> condition = "Full root census plus same-epoch stable scans and no outstanding owner duties permit a conditional closure receipt; peer-return and storage retirement remain separate"; }
 part def RouteSpec { attribute key : String; attribute anchor : String; attribute qntAction : String; attribute leanLemma : String; attribute condition : String; }
 part route0 : RouteSpec { attribute :>> key = "registration"; attribute :>> anchor = "mem.c:723-825"; attribute :>> qntAction = "admitWrite"; attribute :>> leanLemma = "freezeDrainsLeases"; attribute :>> condition = "Accepted writers retain a lease until commit or abort; freeze requires closed admission and empty accepted set; a writer awaiting GC blocks freeze without a scan-ready handoff"; }
 part route1 : RouteSpec { attribute :>> key = "custody"; attribute :>> anchor = "mem.c:6717-6727"; attribute :>> qntAction = "dequeue"; attribute :>> leanLemma = "transferPreserves"; attribute :>> condition = "Receiver must already have active credit and source loses queue custody only on accepted dequeue"; }
 part route2 : RouteSpec { attribute :>> key = "coverage"; attribute :>> anchor = "mem.c:6511-6664,6845-6864"; attribute :>> qntAction = "scanFamily"; attribute :>> leanLemma = "scanPreserves"; attribute :>> condition = "Every modeled root family needs a fresh scan; family aggregation is not a native slot-map proof"; }
 part route3 : RouteSpec { attribute :>> key = "publication"; attribute :>> anchor = "mem.c:3602-3624,3663,4324-4334"; attribute :>> qntAction = "commitCursor"; attribute :>> leanLemma = "zeroClosesDebts"; attribute :>> condition = "Copy completion, inline tail, cursor commit and scanner work cannot disappear at idle; model debt is ghost state"; }
 part route4 : RouteSpec { attribute :>> key = "retirement"; attribute :>> anchor = "mem.c:6864,7016"; attribute :>> qntAction = "issueReceipt"; attribute :>> leanLemma = "incompleteManifestBlocks"; attribute :>> condition = "Source-shaped nonzero-RC omission may terminate accounted work but cannot issue root-complete receipt"; }
 part def GainSpec { attribute key : String; attribute avoided : String; attribute added : String; attribute condition : String; }
 part gain0 : GainSpec { attribute :>> key = "root-scan"; attribute :>> avoided = "Reuse current register/saved/cache/frame walkers and still seed traversal"; attribute :>> added = "RootDomain manifest and ownership/admission protocol; exact maps and cleanup ordering"; attribute :>> condition = "No additional graph traversal is required merely for the receipt; added census bookkeeping and changed RC coverage are real"; }
 part gain1 : GainSpec { attribute :>> key = "credit"; attribute :>> avoided = "Avoid per-object publication atomics for synchronous owner-covered paths"; attribute :>> added = "Seven ghost duty classes with real idle/exit discipline; detached work needs durable credit"; attribute :>> condition = "Existing worker count may cover work but cannot cover omitted roots or uncontrolled FFI writers"; }
 part gain2 : GainSpec { attribute :>> key = "rc-coverage"; attribute :>> avoided = "Retire processor-zero-only RC scan authority once every registered domain is owned"; attribute :>> added = "Scan all registered payload slots and synchronize register/write/unlink; retain still external roots"; attribute :>> condition = "Additional RC scan cost is proportional to roots previously omitted; this is correctness cost, not a performance regression benchmark"; }
 part def RefinementSpec { attribute key : String; attribute qntScope : String; attribute leanScope : String; attribute sourceDuty : String; }
 part refinement0 : RefinementSpec { attribute :>> key = "roots"; attribute :>> qntScope = "admitWrite;commitWrite;abortWrite;needsGC;closeAdmission;freeze;scanFamily;closeProducer"; attribute :>> leanScope = "freezeDrainsLeases;waitingWriterPreventsFreeze;scanPreserves;idleNeedsOwnRoots;rcOmissionBlocks;committedWriteInvalidates"; attribute :>> sourceDuty = "Prove physical slot census, stable domain ownership and root-map spill coverage, then linearize registration/writes/removal against freeze; current RC API lacks these guards"; }
 part refinement1 : RefinementSpec { attribute :>> key = "work"; attribute :>> qntScope = "startCopy;finishPayload;finishTail;commitCursor;beginPublish;commitPublish;scanPrivate;dequeue;discover;drainDerived;finishScan"; attribute :>> leanScope = "zeroClosesDebts;transferPreserves"; attribute :>> sourceDuty = "Refine seven nonempty duty classes to arbitrary copy/frame/chunk tasks with multiplicity; no duty can clear while another task in the same abstract class remains"; }
 part refinement2 : RefinementSpec { attribute :>> key = "callback"; attribute :>> qntScope = "protectArgument;allocateMarker"; attribute :>> leanScope = "markerBeforeAllocation"; attribute :>> sourceDuty = "Protect explicit proc before allocating marker and keep closure/RC lease until re-reading movable payload; qualify implicit trampoline only on supported architectures"; }
 part refinement3 : RefinementSpec { attribute :>> key = "receipt"; attribute :>> qntScope = "idle;issueReceipt"; attribute :>> leanScope = "incompleteManifestBlocks;netBenefit"; attribute :>> sourceDuty = "Count exactness and all-scanned input must compose with previous work-closure model; no full simulation or C memory-model proof is claimed"; }
 part def PriorSpec { attribute key : String; attribute path : String; attribute invariant : String; attribute qntAction : String; attribute leanLemma : String; attribute condition : String; }
 part prior0 : PriorSpec { attribute :>> key = "strong-receipt"; attribute :>> path = "models/build/strong_closure_receipt.qnt"; attribute :>> invariant = "safe"; attribute :>> qntAction = "idle"; attribute :>> leanLemma = "zeroClosesDebts"; attribute :>> condition = "Previous rootCoverage Boolean is refined into explicit root-family membership, writer leases and fresh scan observations; product refinement remains open"; }
 part prior1 : PriorSpec { attribute :>> key = "scan-count"; attribute :>> path = "models/gambit/gc_scan_termination.qnt"; attribute :>> invariant = "safe"; attribute :>> qntAction = "closeProducer"; attribute :>> leanLemma = "idleNeedsOwnRoots"; attribute :>> condition = "Counted producer assumption now requires current source root owner coverage and cannot erase nonzero RC or marker gaps"; }
 part prior2 : PriorSpec { attribute :>> key = "work-closure"; attribute :>> path = "models/gambit/gc_work_closure.qnt"; attribute :>> invariant = "terminationSafe"; attribute :>> qntAction = "finishScan"; attribute :>> leanLemma = "zeroClosesDebts"; attribute :>> condition = "Existing canonical object graph remains a separate payload-closure model; this study checks root admission and idle duties, not actual object bytes"; }
 part def GateSpec { attribute key : String; attribute qualified : Boolean; attribute condition : String; }
 part gate0 : GateSpec { attribute :>> key = "producer-closure"; attribute :>> qualified = false; attribute :>> condition = "Entry census is closed for inspected in-tree dispatch; arbitrary FFI aliases, native stack roots and generated maps are not a full root certificate"; }
 part gate1 : GateSpec { attribute :>> key = "vm-ownership"; attribute :>> qualified = false; attribute :>> condition = "Nonzero RC registration/scan asymmetry and exit cleanup require explicit VM domain membership and storage handoff"; }
 part gate2 : GateSpec { attribute :>> key = "gc-seal"; attribute :>> qualified = false; attribute :>> condition = "Private synchronous call-return order is established structurally; arbitrary task coverage, multiplicity and exceptional paths still need full source simulation"; }
 part gate3 : GateSpec { attribute :>> key = "scan-coverage"; attribute :>> qualified = false; attribute :>> condition = "Families aggregate real slots; per-point GVM spills, frame descriptors, PAIR tails and C configurations remain unqualified"; }
 part gate4 : GateSpec { attribute :>> key = "retirement"; attribute :>> qualified = false; attribute :>> condition = "Accepted writers/readers, callback marker, RC unlink/free and processor cleanup must drain without lock cycles; writer awaiting its own GC needs pre-GC scan-ready handoff"; }
 part gate5 : GateSpec { attribute :>> key = "source-replacement"; attribute :>> qualified = false; attribute :>> condition = "New RootDomain admission, preallocation root materialization and all-owner RC scan are proposed changes, not current runtime features"; }
 part gate6 : GateSpec { attribute :>> key = "platform"; attribute :>> qualified = false; attribute :>> condition = "Current plain RC links/data/refcounts and legacy FIFO synchronization need C happens-before qualification; inherited host attestation remains unresolved"; }
 part def CensusSpec { attribute qntAction : String; attribute leanLemma : String; attribute key : String; attribute anchor : String; attribute condition : String; attribute status : String; }
 part census0 : CensusSpec { attribute :>> qntAction = "scanFamily"; attribute :>> leanLemma = "scanPreserves"; attribute :>> key = "vm-object"; attribute :>> anchor = "mem.c:6573-6587,6847"; attribute :>> condition = "processor-zero VM object body; root ownership stable until strong phase closes"; attribute :>> status = "entry-closed; slot-layout-open"; }
 part census1 : CensusSpec { attribute :>> qntAction = "scanFamily"; attribute :>> leanLemma = "scanPreserves"; attribute :>> key = "symbols-keywords"; attribute :>> anchor = "mem.c:6651-6664,6848"; attribute :>> condition = "processor-zero symbol/key table roots; table bodies use object scan semantics"; attribute :>> status = "entry-closed; external-writers-open"; }
 part census2 : CensusSpec { attribute :>> qntAction = "scanFamily"; attribute :>> leanLemma = "scanPreserves"; attribute :>> key = "globals"; attribute :>> anchor = "mem.c:6591-6647,6852"; attribute :>> condition = "all processors partition SINGLE_VM sublists or per-VM global slots using floor endpoints; fixed n and np required"; attribute :>> status = "entry-closed; mutation-and-snapshot-open"; }
 part census3 : CensusSpec { attribute :>> qntAction = "scanFamily"; attribute :>> leanLemma = "scanPreserves"; attribute :>> key = "continuation-denv"; attribute :>> anchor = "mem.c:3817-3965,6854,4096-4099,4145"; attribute :>> condition = "each processor live stack with frame GC map plus break-frame captured chain; denv is a traced object edge, not a separate arbitrary C root"; attribute :>> status = "entry-closed; generated-map-open"; }
 part census4 : CensusSpec { attribute :>> qntAction = "scanFamily"; attribute :>> leanLemma = "scanPreserves"; attribute :>> key = "registers"; attribute :>> anchor = "mem.c:6511-6522,6856; gambit.h.in:7057-8058"; attribute :>> condition = "each processor ps->r array; compiler must spill actual live machine values before synchronized GC"; attribute :>> status = "entry-closed; spill-completeness-open"; }
 part census5 : CensusSpec { attribute :>> qntAction = "scanFamily"; attribute :>> leanLemma = "scanPreserves"; attribute :>> key = "saved"; attribute :>> anchor = "mem.c:6526-6537,6858; gambit.h.in:8059-8083"; attribute :>> condition = "each processor saved array; explicit SAVE macros retain temporary Scheme arguments across allocating calls"; attribute :>> status = "entry-closed; caller-coverage-open"; }
 part census6 : CensusSpec { attribute :>> qntAction = "scanFamily"; attribute :>> leanLemma = "scanPreserves"; attribute :>> key = "type-cache"; attribute :>> anchor = "mem.c:6541-6552,6860"; attribute :>> condition = "each processor type_cache array"; attribute :>> status = "entry-closed; all-writers-open"; }
 part census7 : CensusSpec { attribute :>> qntAction = "scanFamily"; attribute :>> leanLemma = "scanPreserves"; attribute :>> key = "processor-object"; attribute :>> anchor = "mem.c:6556-6569,6862"; attribute :>> condition = "each processor Scheme object body, including threaded language state reachable through its fields"; attribute :>> status = "entry-closed; layout-open"; }
 part census8 : CensusSpec { attribute :>> qntAction = "scanFamily"; attribute :>> leanLemma = "scanPreserves"; attribute :>> key = "external-still"; attribute :>> anchor = "mem.c:164-175,4210-4247,6800"; attribute :>> condition = "each processor setup traverses still chain and seeds objects with nonzero external refcount; descendants are scanned under active credit"; attribute :>> status = "entry-closed; lifetime-and-raw-writes-open"; }
 part census9 : CensusSpec { attribute :>> qntAction = "scanFamily"; attribute :>> leanLemma = "scanPreserves"; attribute :>> key = "rc-payload"; attribute :>> anchor = "mem.c:277,306,723-825,3969-3986,6845-6850"; attribute :>> condition = "registered h->data is a root slot; registration is per PSTATE but only processor zero currently walks its RC chain"; attribute :>> status = "structural-gap; nonzero-profile-rejected"; }
 part census10 : CensusSpec { attribute :>> qntAction = "protectArgument"; attribute :>> leanLemma = "markerBeforeAllocation"; attribute :>> key = "ffi-temporary"; attribute :>> anchor = "c_intf.c:6511-6561; os_dyn.c:639-672,744-769; tcltk.scm:150,193-194,316-326"; attribute :>> condition = "Explicit marker proc needs a root before allocating; implicit closure relies on RC and c_closure_self; Tcl still vector already has external protection"; attribute :>> status = "admission-gap; no-native-defect-claim"; }
 part census11 : CensusSpec { attribute :>> qntAction = "issueReceipt"; attribute :>> leanLemma = "incompleteManifestBlocks"; attribute :>> key = "weak-exclusion"; attribute :>> anchor = "mem.c:4035-4085,5046-5103,6872-6907"; attribute :>> condition = "Will testators and weak table edges follow weak policy; do not add them as strong roots to make coverage look complete; reachable actions follow strong scan policy"; attribute :>> status = "policy-separated; cross-worker-global-cut-open"; }
 part def SettleSpec { attribute qntAction : String; attribute leanLemma : String; attribute key : String; attribute anchor : String; attribute condition : String; attribute status : String; }
 part settle0 : SettleSpec { attribute :>> qntAction = "finishPayload"; attribute :>> leanLemma = "zeroClosesDebts"; attribute :>> key = "copy"; attribute :>> anchor = "mem.c:3578-3611,3667-3813"; attribute :>> condition = "Forwarding visibility does not discharge payload initialization; copying call returns before caller can idle"; attribute :>> status = "call-order-closed; layout-refinement-open"; }
 part settle1 : SettleSpec { attribute :>> qntAction = "finishTail"; attribute :>> leanLemma = "zeroClosesDebts"; attribute :>> key = "tail"; attribute :>> anchor = "mem.c:3602-3624,4196-4204"; attribute :>> condition = "PAIR first field follows inline tail, remaining field follows body scan; tail completion cannot be inferred from only scan_and_advance"; attribute :>> status = "call-order-closed; exact-tail-proof-open"; }
 part settle2 : SettleSpec { attribute :>> qntAction = "commitCursor"; attribute :>> leanLemma = "zeroClosesDebts"; attribute :>> key = "cursor"; attribute :>> anchor = "mem.c:3663,3808,4324-4334"; attribute :>> condition = "Local alloc cursor is committed before control returns; incomplete-chunk scan compares against current alloc_heap_ptr"; attribute :>> status = "call-order-closed; full-path-proof-open"; }
 part settle3 : SettleSpec { attribute :>> qntAction = "commitPublish"; attribute :>> leanLemma = "transferPreserves"; attribute :>> key = "publication"; attribute :>> anchor = "mem.c:3251-3305,4348-4368"; attribute :>> condition = "Body/end marker/link precede published tail; active producer covers synchronous call; independent producers require explicit credit"; attribute :>> status = "ordering-seams-closed; C-memory-order-open"; }
 part settle4 : SettleSpec { attribute :>> qntAction = "finishScan"; attribute :>> leanLemma = "zeroClosesDebts"; attribute :>> key = "scanner"; attribute :>> anchor = "mem.c:4243-4247,4252-4271,6717-6727"; attribute :>> condition = "Popped still node and dequeued chunk remain in live native scanner frames; recursive children settle before next idle attempt"; attribute :>> status = "call-order-closed; native-unwind-open"; }
 part settle5 : SettleSpec { attribute :>> qntAction = "drainDerived"; attribute :>> leanLemma = "zeroClosesDebts"; attribute :>> key = "still-derived"; attribute :>> anchor = "mem.c:3633-3645,6686-6690"; attribute :>> condition = "Movable scanning may enqueue still objects, so still/movable local loop repeats until no still work remains"; attribute :>> status = "fixed-point-loop-closed; producer-census-open"; }
 part settle6 : SettleSpec { attribute :>> qntAction = "idle"; attribute :>> leanLemma = "zeroClosesDebts"; attribute :>> key = "idle"; attribute :>> anchor = "mem.c:6738-6767"; attribute :>> condition = "Under termination mutex, decrement only after local drain/steal; waiter seeing zero returns without reacquiring; nonzero wake reacquires first"; attribute :>> status = "control-flow-closed; count-coverage-open"; }
 attribute workspaceCount : Integer = 2;
 attribute familyCount : Integer = 12;
 attribute actualAdmitted : Boolean = false;
 part history : GambitAssuranceRouting::ModelNeed { ref part :>> owner = GambitBuildAssurance::planner.component; attribute :>> obligationId = "RPC-H"; attribute :>> kind = "interleaving"; attribute :>> subjectPath = "models/build/root_producer_census.qnt"; attribute :>> subjectScope = "root_producer_census:Test$"; attribute :>> premise = "Root-family census and idle duty research only; source simulation, native correctness and host admission remain open"; }
 part induction : GambitAssuranceRouting::ModelNeed { ref part :>> owner = GambitBuildAssurance::planner.component; attribute :>> obligationId = "RPC-I"; attribute :>> kind = "induction"; attribute :>> subjectPath = "models/build/RootProducerCensus.lean"; attribute :>> subjectScope = "RootProducerCensus:scanPreserves;idleNeedsOwnRoots;rcOmissionBlocks;committedWriteInvalidates;freezeDrainsLeases;waitingWriterPreventsFreeze;zeroClosesDebts;transferPreserves;incompleteManifestBlocks;markerBeforeAllocation;netBenefit"; attribute :>> premise = "Root-family census and idle duty research only; source simulation, native correctness and host admission remain open"; }
 part source : GambitAssuranceRouting::ModelNeed { ref part :>> owner = GambitBuildAssurance::planner.component; attribute :>> obligationId = "RPC-S"; attribute :>> kind = "source-refinement"; attribute :>> subjectPath = "dev/architecture/toolchain/root-producer-census-design.org"; attribute :>> subjectScope = "RPC-S:source"; attribute :>> premise = "Root-family census and idle duty research only; source simulation, native correctness and host admission remain open"; }
 part platform : GambitAssuranceRouting::ModelNeed { ref part :>> owner = GambitBuildAssurance::planner.component; attribute :>> obligationId = "RPC-E"; attribute :>> kind = "environment-refinement"; attribute :>> subjectPath = "dev/architecture/toolchain/root-producer-census-design.org"; attribute :>> subjectScope = "RPC-E:platform"; attribute :>> premise = "Root-family census and idle duty research only; source simulation, native correctness and host admission remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = StrongClosureReceipt::source; }
}
