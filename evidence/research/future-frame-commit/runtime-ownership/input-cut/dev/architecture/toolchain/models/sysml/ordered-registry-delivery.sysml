package OrderedRegistryDelivery {
 private import ScalarValues::*;
 part def CallerSpec { attribute key : String; attribute anchor : String; attribute condition : String; }
 part caller0 : CallerSpec { attribute :>> key = "top-level"; attribute :>> anchor = "_ptree1.scm:659-739"; attribute :>> condition = "Expand current macro, insert its returned form before remaining forms; add-macro and add-declarations complete before recursion"; }
 part caller1 : CallerSpec { attribute :>> key = "body-definitions"; attribute :>> anchor = "_ptree1.scm:1489-1568"; attribute :>> condition = "Leading definition scan expands macros in order; after first nondefinition it defers forms with their environment"; }
 part caller2 : CallerSpec { attribute :>> key = "expression"; attribute :>> anchor = "_ptree1.scm:949-951,1004-1012"; attribute :>> condition = "Expression macro expands recursively; expander return is not proof that all arbitrary effects are cacheable"; }
 part caller3 : CallerSpec { attribute :>> key = "macro-install"; attribute :>> anchor = "_ptree1.scm:2931-2962; _host.scm:852-853"; attribute :>> condition = "Evaluating expander definition may itself have effects; installation and invocation are separate event occurrences"; }
 part caller4 : CallerSpec { attribute :>> key = "gerbil-user"; attribute :>> anchor = "gerbil/expander/core.ss:430-490; compiler/driver.ss:134-136"; attribute :>> condition = "Gerbil iter transformer uses binding/marks/phase context before generated Scheme reaches Gambit; do not merge the two macro engines"; }
 part def DeliverySpec { attribute key : String; attribute anchor : String; attribute condition : String; }
 part delivery0 : DeliverySpec { attribute :>> key = "identity"; attribute :>> anchor = "_env.scm:296-314; proposed service"; attribute :>> condition = "EventId includes semantic invocation/activation, ordinal and owner domain; retry of one event retains identity; new invocation is not a duplicate"; }
 part delivery1 : DeliverySpec { attribute :>> key = "commit"; attribute :>> anchor = "_env.scm:296-314; proposed service"; attribute :>> condition = "Managed registry root transition and immutable event receipt commit under one authority; current helpers have no such ledger"; }
 part delivery2 : DeliverySpec { attribute :>> key = "unknown"; attribute :>> anchor = "proposed service"; attribute :>> condition = "Lost acknowledgement retrieves exact committed receipt; unavailable authoritative state means retain custody and block automatic effect replay"; }
 part delivery3 : DeliverySpec { attribute :>> key = "exception-prefix"; attribute :>> anchor = "_utils.scm:426-434,506-507; _ptree1.scm:754-765"; attribute :>> condition = "Preserve completed registration prefix on error; existing handler/scope restoration is not a registry transaction rollback"; }
 part delivery4 : DeliverySpec { attribute :>> key = "continuation"; attribute :>> anchor = "_ptree1.scm:760-765,1563-1568; gerbil/expander/core.ss:484-490"; attribute :>> condition = "Transport retry is not semantic continuation replay; new legitimate activation may register again; root/unknown holders must drain explicitly"; }
 part def RouteSpec { attribute key : String; attribute anchor : String; attribute qntAction : String; attribute leanLemma : String; attribute condition : String; }
 part route0 : RouteSpec { attribute :>> key = "deduplicated-delivery"; attribute :>> anchor = "_env.scm:296-314; proposed seam"; attribute :>> qntAction = "retryDelivery"; attribute :>> leanLemma = "commitIdempotent"; attribute :>> condition = "Duplicate delivery of same semantic EventId leaves registry unchanged and returns same receipt"; }
 part route1 : RouteSpec { attribute :>> key = "distinct-occurrence"; attribute :>> anchor = "_env.scm:296-314; _ptree1.scm:1004-1012"; attribute :>> qntAction = "prepareEffect"; attribute :>> leanLemma = "equalPayloadDistinct"; attribute :>> condition = "Equal names/payloads in distinct real occurrences remain separate ordered registrations"; }
 part route2 : RouteSpec { attribute :>> key = "parse-boundary"; attribute :>> anchor = "_ptree1.scm:664-739,1501-1549"; attribute :>> qntAction = "parseNext"; attribute :>> leanLemma = "parseGeneration"; attribute :>> condition = "Later form sees registry after all preceding committed effects; cached output alone is not that receipt"; }
 part route3 : RouteSpec { attribute :>> key = "failure-prefix"; attribute :>> anchor = "_utils.scm:426-434,506-507"; attribute :>> qntAction = "failMacro"; attribute :>> leanLemma = "failureRetainsPrefix"; attribute :>> condition = "Failure does not erase committed prefix or unknown delivery responsibility"; }
 part route4 : RouteSpec { attribute :>> key = "custody"; attribute :>> anchor = "_ptree1.scm:754-765,1557-1568; proposed seam"; attribute :>> qntAction = "drain"; attribute :>> leanLemma = "holdersBlockDrain"; attribute :>> condition = "Unknown delivery and retained continuation keep result/root custody until resolved"; }
 part def GainSpec { attribute key : String; attribute avoided : String; attribute added : String; attribute condition : String; }
 part gain0 : GainSpec { attribute :>> key = "transport-retry"; attribute :>> avoided = "Repeated registration after acknowledgement loss in managed delivery"; attribute :>> added = "Event ledger, identity, retained receipt and authoritative resolution"; attribute :>> condition = "Existing raw helper calls cannot gain this property without replacing actual write authority"; }
 part gain1 : GainSpec { attribute :>> key = "pure-query-reuse"; attribute :>> avoided = "Repeated pure expansion/parsing/downstream work under equivalent qualified inputs"; attribute :>> added = "Dynamic effect boundary, lexical identity reconstruction, keys and ledger validation"; attribute :>> condition = "Only effect-closed observer-equivalent work can be skipped; arbitrary macro effects deny receipt"; }
 part gain2 : GainSpec { attribute :>> key = "ordered-context-parallelism"; attribute :>> avoided = "Serialization across independent contexts"; attribute :>> added = "Per-context ordered effect lanes and shared immutable inputs"; attribute :>> condition = "Within-context effect order stays serial; speed depends on independent ready work rather than core count"; }
 part def RefinementSpec { attribute key : String; attribute qntScope : String; attribute leanScope : String; attribute sourceDuty : String; }
 part refinement0 : RefinementSpec { attribute :>> key = "event"; attribute :>> qntScope = "prepareEffect;commitEffect;retryDelivery"; attribute :>> leanScope = "commitIdempotent;commitOrder;equalPayloadDistinct"; attribute :>> sourceDuty = "Bind actual registry write and ledger atomically; no generic exactly-once macro claim"; }
 part refinement1 : RefinementSpec { attribute :>> key = "parser"; attribute :>> qntScope = "returnMacro;parseNext"; attribute :>> leanScope = "parseGeneration;receiptGeneration"; attribute :>> sourceDuty = "Actual expansion queue, declaration category semantics and subsequent read simulation"; }
 part refinement2 : RefinementSpec { attribute :>> key = "unwind"; attribute :>> qntScope = "failMacro;resolveFailure;resumeActivation;drain"; attribute :>> leanScope = "failureRetainsPrefix;holdersBlockDrain"; attribute :>> sourceDuty = "Exception observer, semantic activation identity, root/multishot continuation lifetime"; }
 part refinement3 : RefinementSpec { attribute :>> key = "value"; attribute :>> qntScope = "cacheAttach"; attribute :>> leanScope = "costPositive"; attribute :>> sourceDuty = "Effect replay equivalence, demand and work/span/memory; no native or timing evidence"; }
 part def GateSpec { attribute key : String; attribute qualified : Boolean; attribute condition : String; }
 part gate0 : GateSpec { attribute :>> key = "effect-closure"; attribute :>> qualified = false; attribute :>> condition = "All actual macro eval/call effects, binding and native reachability admitted"; }
 part gate1 : GateSpec { attribute :>> key = "atomic-owner"; attribute :>> qualified = false; attribute :>> condition = "Registry transition and EventId/receipt journal share a truthful authoritative commit"; }
 part gate2 : GateSpec { attribute :>> key = "source-order"; attribute :>> qualified = false; attribute :>> condition = "Full parser queue, nested scopes and deferred body forms refine event order"; }
 part gate3 : GateSpec { attribute :>> key = "cache-observer"; attribute :>> qualified = false; attribute :>> condition = "Macro result/source/marks/diagnostics/effects and context reconstruction equivalent"; }
 part gate4 : GateSpec { attribute :>> key = "continuation"; attribute :>> qualified = false; attribute :>> condition = "Semantic activation versus transport retry, exception/root/unknown holders source refinement"; }
 part gate5 : GateSpec { attribute :>> key = "retirement"; attribute :>> qualified = false; attribute :>> condition = "All direct/indirect registry writers and real consumers migrate; no second global authority"; }
 part gate6 : GateSpec { attribute :>> key = "platform"; attribute :>> qualified = false; attribute :>> condition = "Native synchronization, GC/FFI, host registration and measured performance remain unqualified"; }
 attribute workspaceCount : Integer = 2;
 attribute actualAdmitted : Boolean = false;
 part history : GambitAssuranceRouting::ModelNeed { ref part :>> owner = GambitBuildAssurance::planner.component; attribute :>> obligationId = "OD-H"; attribute :>> kind = "interleaving"; attribute :>> subjectPath = "models/build/ordered_registry_delivery.qnt"; attribute :>> subjectScope = "ordered_registry_delivery:Test$"; attribute :>> premise = "Conditional delivery/order proof; actual effects and continuation/native closure remain open"; }
 part induction : GambitAssuranceRouting::ModelNeed { ref part :>> owner = GambitBuildAssurance::planner.component; attribute :>> obligationId = "OD-I"; attribute :>> kind = "induction"; attribute :>> subjectPath = "models/build/OrderedRegistryDelivery.lean"; attribute :>> subjectScope = "OrderedRegistryDelivery:commitIdempotent;commitOrder;equalPayloadDistinct;parseGeneration;receiptGeneration;failureRetainsPrefix;holdersBlockDrain;costPositive"; attribute :>> premise = "Conditional delivery/order proof; actual effects and continuation/native closure remain open"; }
 part source : GambitAssuranceRouting::ModelNeed { ref part :>> owner = GambitBuildAssurance::planner.component; attribute :>> obligationId = "OD-S"; attribute :>> kind = "source-refinement"; attribute :>> subjectPath = "dev/architecture/toolchain/ordered-registry-delivery-design.org"; attribute :>> subjectScope = "OD-S:source"; attribute :>> premise = "Conditional delivery/order proof; actual effects and continuation/native closure remain open"; }
 part platform : GambitAssuranceRouting::ModelNeed { ref part :>> owner = GambitBuildAssurance::planner.component; attribute :>> obligationId = "OD-E"; attribute :>> kind = "environment-refinement"; attribute :>> subjectPath = "dev/architecture/toolchain/ordered-registry-delivery-design.org"; attribute :>> subjectScope = "OD-E:platform"; attribute :>> premise = "Conditional delivery/order proof; actual effects and continuation/native closure remain open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = StableCopyPublication::source; }
}
