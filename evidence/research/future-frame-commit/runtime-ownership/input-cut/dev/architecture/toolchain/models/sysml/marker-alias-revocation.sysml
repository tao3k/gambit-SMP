package MarkerAliasRevocation {
 private import ScalarValues::*;
 part def Contract { attribute key : String; attribute anchor : String; attribute actionName : String; attribute lemmaName : String; attribute guardName : String; attribute duty : String; attribute status : String; }
 part contract0 : Contract { attribute :>> key = "derived-credit"; attribute :>> anchor = "mem.c:4210-4248,4432-4451"; attribute :>> actionName = "retireRoots"; attribute :>> lemmaName = "retirementNeedsCallerDone"; attribute :>> guardName = "s.callerDone"; attribute :>> duty = "Independent GC root and arena pin survive unknown aliases, auditor and physical caller; accounting alone never permits retirement"; attribute :>> status = "shared root/arena infrastructure required"; }
 part contract1 : Contract { attribute :>> key = "execution-owner"; attribute :>> anchor = "setup.c:3339-3349; _kernel.scm:3463-3501"; attribute :>> actionName = "closeWriters"; attribute :>> lemmaName = "closingDoesNotDrain"; attribute :>> guardName = "s.session"; attribute :>> duty = "Close same-generation alias writer admission; existing continuation references are not native credits or automatic drain acknowledgements"; attribute :>> status = "gate must be introduced around actual mutation authority"; }
 part contract2 : Contract { attribute :>> key = "writer-closure"; attribute :>> anchor = "_kernel.scm:2411-2417,3342-3366,3415-3461; _ptree2.scm:2850-2876"; attribute :>> actionName = "admitClosedProfile"; attribute :>> lemmaName = "extraCreditDefeatsInference"; attribute :>> guardName = "not(s.rawEscape)"; attribute :>> duty = "Classify frame/FFI aliases before exposure; opaque native writers and deserialized authority reject strict count audit"; attribute :>> status = "bounded source composition, not universal alias proof"; }
 part contract3 : Contract { attribute :>> key = "storage-commit"; attribute :>> anchor = "mem.c:4432-4451,4928-4935"; attribute :>> actionName = "reclaim"; attribute :>> lemmaName = "joinDoesNotTransferArena"; attribute :>> guardName = "s.rootGrace"; attribute :>> duty = "Transfer arena and scanner ownership before old cleanup; no count or generation directory substitutes for storage custody"; attribute :>> status = "parent storage proof remains open"; }
 part contract4 : Contract { attribute :>> key = "audit-receipt"; attribute :>> anchor = "_kernel.c:29681-29695; mem.c:1475-1480"; attribute :>> actionName = "certifyAudit"; attribute :>> lemmaName = "receiptNeedsEpoch"; attribute :>> guardName = "qualified"; attribute :>> duty = "Receipt binds marker generation, writer epoch, root/GC cut and closure policy; lease covers read through mutation and recording"; attribute :>> status = "current source has no epoch-qualified receipt"; }
 part contract5 : Contract { attribute :>> key = "auditor-transfer"; attribute :>> anchor = "setup.c:979; os_thread.c:546-556"; attribute :>> actionName = "completeRevoke"; attribute :>> lemmaName = "revocationNeedsDrain"; attribute :>> guardName = "not(s.auditLease)"; attribute :>> duty = "Revocation blocks new use but does not stop an in-flight C instruction; drain exact audit lease before invalidating then reopening"; attribute :>> status = "unknown auditor keeps guardian custody"; }
 part contract6 : Contract { attribute :>> key = "single-drop"; attribute :>> anchor = "c_intf.c:6555-6562; mem.c:1461-1480"; attribute :>> actionName = "auditDrop"; attribute :>> lemmaName = "dropPreserves"; attribute :>> guardName = "not(s.revoking)"; attribute :>> duty = "A stale read never permits decrement; retain exclusivity across read invalidation decrement and result publication"; attribute :>> status = "interruption requires new cut and fresh observation"; }
 part contract7 : Contract { attribute :>> key = "gc-cut"; attribute :>> anchor = "mem.c:4210-4248; _io.scm:11690-11726"; attribute :>> actionName = "beginGcCut"; attribute :>> lemmaName = "exclusiveAuditExcludesScan"; attribute :>> guardName = "writersDrained"; attribute :>> duty = "GC sees marker via independent root; frame explosion adds reachability not native count; root epoch stays stable under audit"; attribute :>> status = "GC drain and root lock cannot wait cyclically"; }
 part def Gain { attribute key : String; attribute avoided : String; attribute added : String; attribute condition : String; }
 part gain0 : Gain { attribute :>> key = "continuation-capability"; attribute :>> avoided = "Preserve repeated Scheme restoration without replaying native cleanup or hiding logical frame slots"; attribute :>> added = "Classify exposure; private marker profile or generation-scoped managed handle"; attribute :>> condition = "Raw reflective frame access remains available only with audit refusal or an authority-aware boundary"; }
 part gain1 : Gain { attribute :>> key = "ffi-managed-sharing"; attribute :>> avoided = "Share one admission and root protocol across native conversions and callback adapters"; attribute :>> added = "Each retained native alias needs updated root, lifetime and writer lease; bypass rejects audit"; attribute :>> condition = "Fewer independent protocols only if actual FFI and generic count writers migrate; scheme-object alone is insufficient"; }
 part gain2 : Gain { attribute :>> key = "revocable-audit"; attribute :>> avoided = "Reuse exact one-credit count inference in truly closed profiles"; attribute :>> added = "Two drain barriers, epoch stamp, audit lease and unknown guardian retention"; attribute :>> condition = "Reopening waits for auditor cessation; balanced foreign writes still fail strict provenance"; }
 part gain3 : Gain { attribute :>> key = "modern-c-paper-amplification"; attribute :>> avoided = "Turn PVM logical frames and bidirectional target negotiation into generated frame/root/exposure contracts"; attribute :>> added = "Shared schema, source refinement and collector handoff support"; attribute :>> condition = "Paper motivates interface structure; no historical performance multiplier or Zig-specific saving transferred"; }
 part def Gate { attribute key : String; attribute qualified : Boolean; attribute duty : String; }
 part gate0 : Gate { attribute :>> key = "reference-writer-closure"; attribute :>> qualified = false; attribute :>> duty = "Generic C, Scheme primitive, exported function-table and raw native alias writers are closed or marker profile is rejected; census cannot certify this universally"; }
 part gate1 : Gate { attribute :>> key = "stop-and-visibility"; attribute :>> qualified = false; attribute :>> duty = "Exact old writer and every auditor cessation, admitted join result, happens-before, no late leased writer; current shrink ignores join error"; }
 part gate2 : Gate { attribute :>> key = "arena-handoff"; attribute :>> qualified = false; attribute :>> duty = "Still list, scanner/sweep and capacity census transfer before cleanup_pstate/free_still_objs; root registration alone is insufficient"; }
 part gate3 : Gate { attribute :>> key = "audit-qualification"; attribute :>> qualified = false; attribute :>> duty = "Known one-credit baseline, independent root pin without still increment, stable generation, excluded raw aliases, no corrupt/torn state"; }
 part gate4 : Gate { attribute :>> key = "auditor-retirement"; attribute :>> qualified = false; attribute :>> duty = "No overlap or stale observation after audit helper exit; read leases and root/session guardian outlive unknown outcomes"; }
 part gate5 : Gate { attribute :>> key = "c11-source-refinement"; attribute :>> qualified = false; attribute :>> duty = "Gate close/drain, ordinary-field quiescence, collector exclusion and native join semantics are mapped to concrete instructions"; }
 part gate6 : Gate { attribute :>> key = "darwin-native"; attribute :>> qualified = false; attribute :>> duty = "Static SDK macro parity only; installed pthread/GC/SMP object and full source/native registration remain open"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Nine literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "MAR-H"; attribute :>> kind = "interleaving"; attribute :>> subjectPath = "models/build/marker_alias_revocation.qnt"; attribute :>> subjectScope = "safe: alias provenance, close and late-writer drain, exclusive epoch receipt, revocation and audit drain, unknown custody"; attribute :>> premise = "No-abandonment cleanup, VM root-domain coverage and directory lifetime are premises, not implemented facilities; current native profile remains unqualified"; }
 part induction : GambitAssuranceRouting::ModelNeed { ref part :>> owner = GambitBuildAssurance::planner.component; attribute :>> obligationId = "MAR-I"; attribute :>> kind = "induction"; attribute :>> subjectPath = "models/build/MarkerAliasRevocation.lean"; attribute :>> subjectScope = "count induction plus typed lease step/history preservation; revocation blocks use, reopen requires drained auditor; not full QNT simulation"; attribute :>> premise = "No-abandonment cleanup, VM root-domain coverage and directory lifetime are premises, not implemented facilities; current native profile remains unqualified"; }
 part source : GambitAssuranceRouting::ModelNeed { ref part :>> owner = GambitBuildAssurance::planner.component; attribute :>> obligationId = "MAR-S"; attribute :>> kind = "source-refinement"; attribute :>> subjectPath = "dev/architecture/toolchain/marker-alias-revocation-design.org"; attribute :>> subjectScope = "marker stack slot to continuation/frame aliases and raw scheme-object FFI; generated descriptor decode, API writers and unknown opaque escapes"; attribute :>> premise = "No-abandonment cleanup, VM root-domain coverage and directory lifetime are premises, not implemented facilities; current native profile remains unqualified"; }
 part platform : GambitAssuranceRouting::ModelNeed { ref part :>> owner = GambitBuildAssurance::planner.component; attribute :>> obligationId = "MAR-E"; attribute :>> kind = "environment-refinement"; attribute :>> subjectPath = "dev/architecture/toolchain/marker-alias-revocation-design.org"; attribute :>> subjectScope = "C11 combined admission state, final writer release sequence, exclusive audit lease, revocation drain and stale epoch rejection; native object match open"; attribute :>> premise = "No-abandonment cleanup, VM root-domain coverage and directory lifetime are premises, not implemented facilities; current native profile remains unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = MarkerAuditQuiescence::source; }
 part def ContractDependency { ref part dependent : Contract; ref part prerequisite : Contract; attribute reason : String; }
 part edge0 : ContractDependency { ref part :>> dependent = contract2; ref part :>> prerequisite = contract1; attribute :>> reason = "Close admission before writer-profile closure receipt"; }
 part edge1 : ContractDependency { ref part :>> dependent = contract7; ref part :>> prerequisite = contract1; attribute :>> reason = "Drain pre-admitted writers before collector cut"; }
 part edge2 : ContractDependency { ref part :>> dependent = contract4; ref part :>> prerequisite = contract2; attribute :>> reason = "Count inference needs complete writer/credit provenance"; }
 part edge3 : ContractDependency { ref part :>> dependent = contract4; ref part :>> prerequisite = contract7; attribute :>> reason = "Audit receipt includes collector and root storage cut"; }
 part edge4 : ContractDependency { ref part :>> dependent = contract5; ref part :>> prerequisite = contract4; attribute :>> reason = "Revocation applies to identity-specific audit authority; drain precedes reopening"; }
 part edge5 : ContractDependency { ref part :>> dependent = contract6; ref part :>> prerequisite = contract4; attribute :>> reason = "Only qualified exact-credit observation permits missing decrement"; }
 part edge6 : ContractDependency { ref part :>> dependent = contract0; ref part :>> prerequisite = contract6; attribute :>> reason = "Accounting settlement precedes physical root retirement"; }
 part edge7 : ContractDependency { ref part :>> dependent = contract0; ref part :>> prerequisite = contract5; attribute :>> reason = "No unresolved auditor lease at retirement"; }
 part edge8 : ContractDependency { ref part :>> dependent = contract3; ref part :>> prerequisite = contract0; attribute :>> reason = "Storage reclaim follows caller and root retirement"; }
 part edge9 : ContractDependency { ref part :>> dependent = contract4; ref part :>> prerequisite = contract1; attribute :>> reason = "Closed gate and successful cessation precede qualification"; }
 part def MemoryEdge { attribute key : String; attribute writer : String; attribute publication : String; attribute reader : String; attribute observation : String; attribute lifetime : String; }
 part memory0 : MemoryEdge { attribute :>> key = "close-admission"; attribute :>> writer = "stable VM directory closes native writer generation"; attribute :>> publication = "SC gate transition; candidate acq_rel CAS"; attribute :>> reader = "old and late requesting writers"; attribute :>> observation = "acquire same closed generation; no unchecked increment after separate open test"; attribute :>> lifetime = "raw bypass aliases must be excluded by admitted profile"; }
 part memory1 : MemoryEdge { attribute :>> key = "writer-drain"; attribute :>> writer = "last admitted writer completes ordinary count/body accesses"; attribute :>> publication = "release write-lease decrement"; attribute :>> reader = "collector/audit coordinator"; attribute :>> observation = "acquire drained same gate after close; preserve reads-from chain"; attribute :>> lifetime = "counter zero is meaningful only with closed admission and complete writer set"; }
 part memory2 : MemoryEdge { attribute :>> key = "join-result"; attribute :>> writer = "OS thread termination and exact join result"; attribute :>> publication = "platform termination synchronization; capture native return code"; attribute :>> reader = "guardian"; attribute :>> observation = "successful matching join; errors/unknown retain lease and custody"; attribute :>> lifetime = "native thread death alone does not transfer arena or roots"; }
 part memory3 : MemoryEdge { attribute :>> key = "arena-transfer"; attribute :>> writer = "old storage owner publishes retained still-list/accounting handoff"; attribute :>> publication = "release immutable StorageHandoffReceipt"; attribute :>> reader = "target VM storage/scanner owner"; attribute :>> observation = "acquire same generation before old cleanup"; attribute :>> lifetime = "old free_still_objs cannot run on transferred retained chain"; }
 part memory4 : MemoryEdge { attribute :>> key = "gc-cut"; attribute :>> writer = "coordinator parks producers and scanner/auditor in disjoint phases"; attribute :>> publication = "release epoch/root snapshot and matching acknowledgement"; attribute :>> reader = "collector then exclusive auditor"; attribute :>> observation = "acquire complete cut; no global root lock across GC wait"; attribute :>> lifetime = "count-zero marker remains ordinary root-reachable"; }
 part memory5 : MemoryEdge { attribute :>> key = "audit-read"; attribute :>> writer = "exclusive auditor with proven native credit baseline"; attribute :>> publication = "fresh plain count and marker reads under same writer epoch and exclusive audit lease"; attribute :>> reader = "same auditor"; attribute :>> observation = "fresh observation under active lease only"; attribute :>> lifetime = "no atomic cast on mixed plain fields; no extra native still reference for audit pin"; }
 part memory6 : MemoryEdge { attribute :>> key = "audit-write"; attribute :>> writer = "exclusive auditor performs missing invalidation/drop"; attribute :>> publication = "plain writes then release accounting receipt"; attribute :>> reader = "query/custodian"; attribute :>> observation = "acquire same audit/marker generation"; attribute :>> lifetime = "if auditor exits before receipt, keep roots and establish a fresh cut before reread"; }
 part memory7 : MemoryEdge { attribute :>> key = "replacement"; attribute :>> writer = "prior auditor exits, then guardian confirms cessation and visibility"; attribute :>> publication = "revoking CAS blocks claims; exact audit drain then invalidates receipt and observation before opening writer epoch"; attribute :>> reader = "next auditor"; attribute :>> observation = "acquire drain acknowledgement; next writer epoch cannot reuse old receipt; replacement audit needs fresh root/GC cut"; attribute :>> lifetime = "lost response is not cessation; no helper overlap"; }
 part memory8 : MemoryEdge { attribute :>> key = "retirement"; attribute :>> writer = "physical caller and reader/root grace obligations settle"; attribute :>> publication = "release Done/root-domain retirement"; attribute :>> reader = "VM guardian"; attribute :>> observation = "acquire complete retirement receipt"; attribute :>> lifetime = "no free based on count zero, invalid marker, join or audit accounting alone"; }
 part def WriterRoute { attribute key : String; attribute kind : String; attribute anchor : String; attribute target : String; attribute admission : String; attribute status : String; }
 part writer0 : WriterRoute { attribute :>> key = "marker-frame"; attribute :>> kind = "retained alias"; attribute :>> anchor = "setup.c:3339-3349; _kernel.c:29693"; attribute :>> target = "marker logical slot 2"; attribute :>> admission = "source descriptor fs5 and map3; FRAME_SPACE(2)=FRAME_SPACE(5)=8"; attribute :>> status = "source decode only; installed object not matched"; }
 part writer1 : WriterRoute { attribute :>> key = "continuation-ref"; attribute :>> kind = "reflective read"; attribute :>> anchor = "_kernel.scm:3145-3152,3463-3510,3725-3727"; attribute :>> target = "raw object from stack or heap frame"; attribute :>> admission = "same marker identity on eligible current frame; no implicit credit"; attribute :>> status = "capture reachability conditional on matching frame and control path"; }
 part writer2 : WriterRoute { attribute :>> key = "frame-ref"; attribute :>> kind = "reflective read and write"; attribute :>> anchor = "_kernel.scm:3342-3366,3415-3461"; attribute :>> target = "frame slot object and replacement"; attribute :>> admission = "classify read aliases separately from authority/slot mutation"; attribute :>> status = "unmediated mutation invalidates provenance"; }
 part writer3 : WriterRoute { attribute :>> key = "frame-explode"; attribute :>> kind = "derived alias container"; attribute :>> anchor = "_io.scm:11690-11718"; attribute :>> target = "live frame fields in vector"; attribute :>> admission = "bit1 includes slot2; vector wrapper copy is not deep marker copy"; attribute :>> status = "body mutation and later writers require mediation"; }
 part writer4 : WriterRoute { attribute :>> key = "serialized-frame"; attribute :>> kind = "reconstructed identity"; attribute :>> anchor = "_io.scm:12123-12127,13789-13792"; attribute :>> target = "frame or continuation rebuilt from fields"; attribute :>> admission = "never inherit original native credit or audit authority"; attribute :>> status = "refuse original-marker receipt for reconstructed values"; }
 part writer5 : WriterRoute { attribute :>> key = "scheme-primitives"; attribute :>> kind = "generic arithmetic writer"; attribute :>> anchor = "_kernel.scm:2411-2417; mem.c:1447-1467"; attribute :>> target = "any supplied still object"; attribute :>> admission = "admit managed writer lease or refuse private audit"; attribute :>> status = "actual direct API route; no marker subtype filter"; }
 part writer6 : WriterRoute { attribute :>> key = "ffi-argument"; attribute :>> kind = "identity-preserving boundary"; attribute :>> anchor = "_ptree2.scm:2780-2876; gambit.h.in:10063-10066,10400-10403"; attribute :>> target = "scheme-object argument"; attribute :>> admission = "register root and alias class before raw exposure"; attribute :>> status = "conversion does not establish borrow or mutation lease"; }
 part writer7 : WriterRoute { attribute :>> key = "native-exports"; attribute :>> kind = "generic C API writer"; attribute :>> anchor = "setup.c:5931-5944; gambit.h.in:13294-13302"; attribute :>> target = "arbitrary encoded still object"; attribute :>> admission = "function table and raw C imports must be closed or rejected"; attribute :>> status = "raw pointer arithmetic not covered by named API census"; }
 part writer8 : WriterRoute { attribute :>> key = "native-counter-caller"; attribute :>> kind = "real generic caller"; attribute :>> anchor = "examples/pthread/mylib.scm:24-31"; attribute :>> target = "counter scheme-object with explicit inc and dec"; attribute :>> admission = "counter witness confirms unfiltered composition; not actual marker call"; attribute :>> status = "do not claim observed marker count mutation"; }
 part writer9 : WriterRoute { attribute :>> key = "marker-owner-drop"; attribute :>> kind = "original native writer"; attribute :>> anchor = "setup.c:3395-3420; c_intf.c:6555-6562"; attribute :>> target = "marker invalidation and decrement"; attribute :>> admission = "owner lease and exact physical exit must drain"; attribute :>> status = "multi-shot Scheme restore is not repeatable native credit"; }
 part writer10 : WriterRoute { attribute :>> key = "generic-release"; attribute :>> kind = "indirect decrement writer"; attribute :>> anchor = "mem.c:1730-1737"; attribute :>> target = "allocated still object"; attribute :>> admission = "close conversion cleanup and release_scmobj aliases"; attribute :>> status = "raw native alias or unknown cleanup forces refusal"; }
 part def AuditPolicy { attribute key : String; attribute identity : String; attribute roots : String; attribute executor : String; }
 part policy0 : AuditPolicy { attribute :>> key = "epoch-qualified-private-marker"; attribute :>> identity = "marker generation plus writer epoch plus root/GC epoch and closure stamp"; attribute :>> roots = "independent scanned root and VM arena pin; not an extra still credit"; attribute :>> executor = "revoke blocks future use; exact auditor drain precedes new writer epoch; unknown retains guardian"; }

 part def PaperAdvantage { attribute key : String; attribute paper : String; attribute section : String; attribute anchor : String; attribute contractKey : String; attribute obligation : String; attribute benefit : String; attribute refutation : String; }
 part paper0 : PaperAdvantage { attribute :>> key = "logical-frame"; attribute :>> paper = "https://www.iro.umontreal.ca/~feeley/papers/FeeleyMillerLFP90.pdf"; attribute :>> section = "2,2.3"; attribute :>> anchor = "setup.c:3339-3349; _kernel.c:29693; _kernel.scm:3485,3501"; attribute :>> contractKey = "writer-closure"; attribute :>> obligation = "MAR-S"; attribute :>> benefit = "One generated frame coordinate and root/exposure description serves all consumers"; attribute :>> refutation = "Fail if accessor and live map disagree or layout must be independently maintained"; }
 part paper1 : PaperAdvantage { attribute :>> key = "bidirectional-target"; attribute :>> paper = "https://www.iro.umontreal.ca/~feeley/papers/FeeleyMillerLFP90.pdf"; attribute :>> section = "2"; attribute :>> anchor = "dev/architecture/runtime/execution/studies/shared-runtime-contract-evidence.org:64"; attribute :>> contractKey = "audit-receipt"; attribute :>> obligation = "MAR-S"; attribute :>> benefit = "Negotiate representation and obligations at semantic-native boundary instead of recovering them from C text"; attribute :>> refutation = "Fail if required lifetime information is absent from semantic output; not a claim current target API already supplies it"; }
 part paper2 : PaperAdvantage { attribute :>> key = "storage-classes"; attribute :>> paper = "https://www.iro.umontreal.ca/~feeley/papers/FeeleyMillerLFP90.pdf"; attribute :>> section = "2.1"; attribute :>> anchor = "_kernel.scm:3415-3501; _ptree2.scm:2850-2876"; attribute :>> contractKey = "execution-owner"; attribute :>> obligation = "MAR-S"; attribute :>> benefit = "Keep closed-profile alias reasoning until explicit reflection or native escape"; attribute :>> refutation = "Fail if unclassified writable alias receives private-marker audit permission"; }
 part paper3 : PaperAdvantage { attribute :>> key = "measurement-feedback"; attribute :>> paper = "https://www.iro.umontreal.ca/~feeley/papers/FeeleyMillerLFP90.pdf"; attribute :>> section = "abstract"; attribute :>> anchor = "dev/architecture/toolchain/marker-alias-revocation-design.org::marker-alias-benefit-bound"; attribute :>> contractKey = "derived-credit"; attribute :>> obligation = "MAR-S"; attribute :>> benefit = "Choose representation using removed work versus coordination and retained-storage cost"; attribute :>> refutation = "Fail if added coordination and unknown retention exceed saved support/work; paper timing is not current evidence"; }
}
