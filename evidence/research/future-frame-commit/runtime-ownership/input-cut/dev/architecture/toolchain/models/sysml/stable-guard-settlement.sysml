package StableGuardSettlement {
 private import ScalarValues::*;
 part def Contract { attribute key : String; attribute anchor : String; attribute actionName : String; attribute lemmaName : String; attribute guardName : String; attribute duty : String; attribute status : String; }
 part contract0 : Contract { attribute :>> key = "derived-credit"; attribute :>> anchor = "mem.c:684-699; setup.c:3384-3420; gambit.h.in:10376-10398"; attribute :>> actionName = "retireGuard"; attribute :>> lemmaName = "rootsOutliveDone"; attribute :>> guardName = "s.closing[i]"; attribute :>> duty = "Close acquisition directory, drain read leases, acquire exact Done receipt, retire root registration, then release session after last restoration debt"; attribute :>> status = "proposed stable registry and closed admission required"; }
 part contract1 : Contract { attribute :>> key = "execution-owner"; attribute :>> anchor = "c_intf.c:6511-6533; mem.c:1487-1497,1647-1648"; attribute :>> actionName = "reserve"; attribute :>> lemmaName = "reserveSafe"; attribute :>> guardName = "s.p[i]==0"; attribute :>> duty = "Reserve no-GC stable slot and protect input under caller root fence before any marker allocation; failure retains caller ownership"; attribute :>> status = "new caller-root to guard-root handoff"; }
 part contract2 : Contract { attribute :>> key = "root-publication"; attribute :>> anchor = "mem.c:306,723-739,3969-3987,6845-6849"; attribute :>> actionName = "publishGuard"; attribute :>> lemmaName = "registerBeforePublish"; attribute :>> guardName = "s.registered[i]"; attribute :>> duty = "Publish immutable descriptor only after VM-wide scanned mutable root slots are registered; nonzero processor cannot assume current RC list provides coverage"; attribute :>> status = "VM root scanning adapter remains open"; }
 part contract3 : Contract { attribute :>> key = "storage-commit"; attribute :>> anchor = "setup.c:781-804; mem.c:684-699; _kernel.scm:1020-1065"; attribute :>> actionName = "retireVm"; attribute :>> lemmaName = "vmExcludesHandles"; attribute :>> guardName = "not(A.exists"; attribute :>> duty = "VM cleanup excludes live guards, exported continuation handles and invocation leases; storage and old-roster duties remain parent obligations"; attribute :>> status = "source and native shutdown closure open"; }
 part contract4 : Contract { attribute :>> key = "marker-acquire"; attribute :>> anchor = "c_intf.c:6524-6546; mem.c:1647-1684,1778-1814; os_dyn.c:744-787,1056-1059"; attribute :>> actionName = "allocateSuccess"; attribute :>> lemmaName = "acquiredIsNotFailure"; attribute :>> guardName = "s.published[i]"; attribute :>> duty = "Reload relocated proc from registered root; publish fully initialized marker with one still reference without another safepoint; allocation failure owns no marker"; attribute :>> status = "marker construction API must change"; }
 part contract5 : Contract { attribute :>> key = "abnormal-takeover"; attribute :>> anchor = "setup.c:3384-3418; gambit.h.in:9981-9988,10043-10059"; attribute :>> actionName = "claimCleanup"; attribute :>> lemmaName = "claimInstallsExecutor"; attribute :>> guardName = "s.executor[i]==-1"; attribute :>> duty = "Normal tail and admitted exceptional custodian compete for same generation-aware cleanup state; winner pins session and owns nonabandonable cleanup segment"; attribute :>> status = "foreign skips outside admitted catcher remain rejected"; }
 part contract6 : Contract { attribute :>> key = "single-drop"; attribute :>> anchor = "c_intf.c:6555-6562; mem.c:1447-1467"; attribute :>> actionName = "dropStill"; attribute :>> lemmaName = "oneDrop"; attribute :>> guardName = "s.drops[i]==0"; attribute :>> duty = "Invalidate marker then decrement exactly one owned still reference; no reentry, GC, native throw or executor takeover in this segment"; attribute :>> status = "unknown in-progress state cannot be retried"; }
 part contract7 : Contract { attribute :>> key = "completion-receipt"; attribute :>> anchor = "gambit.h.in:10376-10398; _ptree2.scm:2902-3012"; attribute :>> actionName = "publishDone"; attribute :>> lemmaName = "finishKeepsRoots"; attribute :>> guardName = "not(s.debt[i])"; attribute :>> duty = "Publish Done only after cleanup and restoration complete; query lost acknowledgement using exact activation and settlement identities; do not replay kill"; attribute :>> status = "root/session retirement remains separate"; }
 part def Gain { attribute key : String; attribute avoided : String; attribute added : String; attribute condition : String; }
 part gain0 : Gain { attribute :>> key = "complete-marker-custody"; attribute :>> avoided = "Prevent lost or duplicate decrement on accepted normal and abnormal exits"; attribute :>> added = "One guard plus mutable root-slot registration per active activation and generation-aware settlement"; attribute :>> condition = "Safety is conditional on no-abandonment cleanup and complete exceptional landing coverage"; }
 part gain1 : Gain { attribute :>> key = "registration-sharing"; attribute :>> avoided = "Amortize reserved slab and scanned root-domain setup across necessary service components"; attribute :>> added = "Still one per-activation slot lifecycle, publication, cleanup claim and receipt; bounded pool exhaustion must reject before allocation"; attribute :>> condition = "Shared support saves setup duplication only; O(A+H+I+R+T) metadata and retained unresolved roots remain"; }
 part gain2 : Gain { attribute :>> key = "retire-duplicate-tail-policy"; attribute :>> avoided = "Replace separate normal/abnormal marker ownership policy with one generated guard description"; attribute :>> added = "Keep existing conversion cleanup and semantic catcher/fp/PSR0 restore duties"; attribute :>> condition = "Old kill sites retire only after every path routes through same marker token; no double accounting"; }
 part gain3 : Gain { attribute :>> key = "modern-c-net-benefit"; attribute :>> avoided = "Reuse Scheme emitter, C ABI and existing still/scanning semantics"; attribute :>> added = "C11 publication, GC adapter, generation directory and no-abandonment qualification are necessary in C and Zig"; attribute :>> condition = "Positive work balance requires actually removed repeated support or setup cost to exceed added checks; Zig-specific savings unproved"; }
 part def Gate { attribute key : String; attribute qualified : Boolean; attribute duty : String; }
 part gate0 : Gate { attribute :>> key = "gc-root-domain"; attribute :>> qualified = false; attribute :>> duty = "VM-wide roots are scanned on every relevant processor and updated under moving GC before next use; existing RC registration is not this proof"; }
 part gate1 : Gate { attribute :>> key = "no-abandonment"; attribute :>> qualified = false; attribute :>> duty = "No allocation, safepoint, callback, native throw, cancellation or asynchronous longjmp between still decrement and Done publication"; }
 part gate2 : Gate { attribute :>> key = "all-escape-coverage"; attribute :>> qualified = false; attribute :>> duty = "All normal, exceptional, converted and native/foreign exits reach a custodian; marker slot acquisition/result cannot be lost"; }
 part gate3 : Gate { attribute :>> key = "retirement-directory"; attribute :>> qualified = false; attribute :>> duty = "Closed generation-aware admission, drained readers, stable tombstone and no-wrap identity before slot or VM storage reuse"; }
 part gate4 : Gate { attribute :>> key = "continuation-session"; attribute :>> qualified = false; attribute :>> duty = "Fresh invocation roots and current processor acquired independently; exported handle retirement and parent roster/storage duties qualified"; }
 part gate5 : Gate { attribute :>> key = "c11-refinement"; attribute :>> qualified = false; attribute :>> duty = "C11 release/acquire reads-from and atomic CAS orders, mutable root synchronization and collector exclusion proved against implementation"; }
 part gate6 : Gate { attribute :>> key = "darwin-native"; attribute :>> qualified = false; attribute :>> duty = "Only declared SDK profile and literal macro parity; effective argv, SMP object and inherited host attestation remain unresolved"; }
 part def Profile { attribute key : String; attribute driver : String; attribute header : String; attribute compiler : String; attribute declaredMode : String; attribute macroParity : String; attribute sourceMatch : Boolean; attribute status : String; }
 part profile0 : Profile { attribute :>> key = "installed-darwin-source"; attribute :>> driver = "/opt/homebrew/Cellar/gerbil-scheme@0.19/0.19.20261009110849.1cfb032.patch618d76f9eb72/1cfb032/bin/gambuild-C"; attribute :>> header = "/opt/homebrew/Cellar/gerbil-scheme@0.19/0.19.20261009110849.1cfb032.patch618d76f9eb72/1cfb032/include/gambit.h"; attribute :>> compiler = "/opt/homebrew/bin/gcc-16"; attribute :>> declaredMode = "C; SINGLE_HOST; INLINE_JUMPS; TRUST_C_TCO; header default SINGLE_THREADED_VMS"; attribute :>> macroParity = "Nine literal macro spans match template; effective branch and object relation remain open"; attribute :>> sourceMatch = false; attribute :>> status = "static installed declarations; no effective argv or SMP object match"; }
 part history : GambitAssuranceRouting::ModelNeed { ref part :>> owner = GambitBuildAssurance::planner.component; attribute :>> obligationId = "SGS-H"; attribute :>> kind = "interleaving"; attribute :>> subjectPath = "models/build/stable_guard_settlement.qnt"; attribute :>> subjectScope = "safe: registration, allocation outcome, relocated roots, cleanup claim, one still decrement, unknown receipt, nested and multi-shot custody"; attribute :>> premise = "No-abandonment cleanup, VM root-domain coverage and directory lifetime are premises, not implemented facilities; current native profile remains unqualified"; }
 part induction : GambitAssuranceRouting::ModelNeed { ref part :>> owner = GambitBuildAssurance::planner.component; attribute :>> obligationId = "SGS-I"; attribute :>> kind = "induction"; attribute :>> subjectPath = "models/build/StableGuardSettlement.lean"; attribute :>> subjectScope = "guard root/owner and one-drop invariant preserved along guarded traces; failure, unknown acknowledgement and publication identity obligations"; attribute :>> premise = "No-abandonment cleanup, VM root-domain coverage and directory lifetime are premises, not implemented facilities; current native profile remains unqualified"; }
 part source : GambitAssuranceRouting::ModelNeed { ref part :>> owner = GambitBuildAssurance::planner.component; attribute :>> obligationId = "SGS-S"; attribute :>> kind = "source-refinement"; attribute :>> subjectPath = "dev/architecture/toolchain/stable-guard-settlement-design.org"; attribute :>> subjectScope = "current marker allocator, still reference decrement, per-processor RC and scanner consumers; proposed stable guard/root integration"; attribute :>> premise = "No-abandonment cleanup, VM root-domain coverage and directory lifetime are premises, not implemented facilities; current native profile remains unqualified"; }
 part platform : GambitAssuranceRouting::ModelNeed { ref part :>> owner = GambitBuildAssurance::planner.component; attribute :>> obligationId = "SGS-E"; attribute :>> kind = "environment-refinement"; attribute :>> subjectPath = "dev/architecture/toolchain/stable-guard-settlement-design.org"; attribute :>> subjectScope = "C11 publication, cleanup exclusion, root retirement and effective Darwin/generated SMP artifact refinement"; attribute :>> premise = "No-abandonment cleanup, VM root-domain coverage and directory lifetime are premises, not implemented facilities; current native profile remains unqualified"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = OuterCompletionLanding::source; }
 part def ContractDependency { ref part dependent : Contract; ref part prerequisite : Contract; attribute reason : String; }
 part edge0 : ContractDependency { ref part :>> dependent = contract2; ref part :>> prerequisite = contract1; attribute :>> reason = "Caller-root fence and stable slot precede root-domain publication"; }
 part edge1 : ContractDependency { ref part :>> dependent = contract4; ref part :>> prerequisite = contract2; attribute :>> reason = "No allocating marker construction before scanned root publication"; }
 part edge2 : ContractDependency { ref part :>> dependent = contract5; ref part :>> prerequisite = contract4; attribute :>> reason = "Acquisition outcome is recorded before cleanup ownership is selected"; }
 part edge3 : ContractDependency { ref part :>> dependent = contract6; ref part :>> prerequisite = contract5; attribute :>> reason = "One cleanup winner exclusively owns non-idempotent decrement"; }
 part edge4 : ContractDependency { ref part :>> dependent = contract7; ref part :>> prerequisite = contract6; attribute :>> reason = "Done follows recorded cleanup progress and caller restoration"; }
 part edge5 : ContractDependency { ref part :>> dependent = contract0; ref part :>> prerequisite = contract7; attribute :>> reason = "Root retirement follows exact completion receipt and reader drain"; }
 part edge6 : ContractDependency { ref part :>> dependent = contract3; ref part :>> prerequisite = contract0; attribute :>> reason = "VM retirement excludes live native guard registrations"; }
 part edge7 : ContractDependency { ref part :>> dependent = contract5; ref part :>> prerequisite = contract2; attribute :>> reason = "Exceptional custodian reads registered descriptor through acquire"; }
 part edge8 : ContractDependency { ref part :>> dependent = contract7; ref part :>> prerequisite = contract5; attribute :>> reason = "Only the same pinned executor can finalize Done"; }
 part edge9 : ContractDependency { ref part :>> dependent = contract0; ref part :>> prerequisite = contract2; attribute :>> reason = "Root directory remains live through closed acquisition and quiescence"; }
 part def MemoryEdge { attribute key : String; attribute writer : String; attribute publication : String; attribute reader : String; attribute observation : String; attribute lifetime : String; }
 part memory0 : MemoryEdge { attribute :>> key = "descriptor"; attribute :>> writer = "owner initializes immutable identity and slot descriptors"; attribute :>> publication = "release store Published"; attribute :>> reader = "admitted registry reader"; attribute :>> observation = "acquire exact Published identity"; attribute :>> lifetime = "directory and record retained until closed admission and readers drain"; }
 part memory1 : MemoryEdge { attribute :>> key = "cleanup-claim"; attribute :>> writer = "same owner native tail or admitted exceptional custodian"; attribute :>> publication = "CAS Pending to Cleaning: acq_rel success"; attribute :>> reader = "losing contender or receipt query"; attribute :>> observation = "acquire failure/load; failure order never release/acq_rel"; attribute :>> lifetime = "executor pin prevents slot/session retirement; loser does not access mutable marker"; }
 part memory2 : MemoryEdge { attribute :>> key = "done"; attribute :>> writer = "sole cleanup executor after still decrement and restoration"; attribute :>> publication = "release store Done receipt"; attribute :>> reader = "query or final custodian"; attribute :>> observation = "acquire reads same Done transaction"; attribute :>> lifetime = "Done does not retire root domain or session"; }
 part memory3 : MemoryEdge { attribute :>> key = "directory"; attribute :>> writer = "stable directory serializes closed bit and pin admission"; attribute :>> publication = "SC baseline gate CAS; candidate acq_rel"; attribute :>> reader = "lookup acquires pin before record dereference"; attribute :>> observation = "SC baseline; candidate acquire on successful same-generation admission"; attribute :>> lifetime = "close gate before final zero; no unconditional fetch-add from bare pointer"; }
 part memory4 : MemoryEdge { attribute :>> key = "last-reader"; attribute :>> writer = "borrower finishes record reads"; attribute :>> publication = "release decrement on closed-or-open gate word"; attribute :>> reader = "closer after closing admission"; attribute :>> observation = "acquire observation of drained same gate generation"; attribute :>> lifetime = "retain directory storage and prevent counter wrap; RMW chain mapping open"; }
 part memory5 : MemoryEdge { attribute :>> key = "root-scan"; attribute :>> writer = "mutator parks and publishes root-slot state; collector relocates at GC epoch"; attribute :>> publication = "existing/modernized epoch synchronization; SC baseline"; attribute :>> reader = "collector then resumed owner"; attribute :>> observation = "matching epoch acknowledgements, not an isolated atomic pointer"; attribute :>> lifetime = "ordinary slot writes require scanner exclusion; do not hold lease lock while waiting for GC"; }
 part memory6 : MemoryEdge { attribute :>> key = "marker-drop"; attribute :>> writer = "unique owner under collector exclusion"; attribute :>> publication = "plain invalidation and decrement sequenced before release Done"; attribute :>> reader = "future collector or marker reader"; attribute :>> observation = "GC epoch exclusion plus acquire completion where applicable"; attribute :>> lifetime = "no callback, GC, reentry, throw, cancellation or executor replacement in critical segment"; }
 part memory7 : MemoryEdge { attribute :>> key = "acquisition"; attribute :>> writer = "owner stores initialized marker, processor tag and owned credit"; attribute :>> publication = "release publish Acquired after no-throw commit tail"; attribute :>> reader = "admitted exceptional custodian"; attribute :>> observation = "acquire same activation and token identity"; attribute :>> lifetime = "registered slots precede allocation; unknown private result retains session"; }
}
