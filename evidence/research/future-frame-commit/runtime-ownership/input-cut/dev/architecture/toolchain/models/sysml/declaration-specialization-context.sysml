package DeclarationSpecializationContext {
 private import ScalarValues::*;
 part def ViewSpec { attribute key : String; attribute anchor : String; attribute sharing : String; attribute condition : String; }
 part view0 : ViewSpec { attribute :>> key = "construct"; attribute :>> anchor = "_env.scm:64-80,102-111,318-343"; attribute :>> sharing = "env-frame inherits declaration head; env-declare conses one head; env-decl-set builds a new vector"; attribute :>> condition = "Persistent spine is reusable only if declaration records and named payload lists are writer-closed"; }
 part view1 : ViewSpec { attribute :>> key = "batch-order"; attribute :>> anchor = "_ptree1.scm:2868-2873; _env.scm:335-343"; attribute :>> sharing = "add-declarations visits source order and prepends each transformed record"; attribute :>> condition = "Later textual declarations are earlier lookup candidates; do not preserve textual list without reversal"; }
 part view2 : ViewSpec { attribute :>> key = "scope-restore"; attribute :>> anchor = "_ptree1.scm:754-765,1557-1568"; attribute :>> sharing = "CPS saves declaration head and restores it into the returned env"; attribute :>> condition = "Restore declaration projection only; preserve bindings/macros/other returned environment fields"; }
 part view3 : ViewSpec { attribute :>> key = "shared-mutable"; attribute :>> anchor = "_env.scm:94-130"; attribute :>> sharing = "Functional env setters share variables cell, externals, parent and other fields"; attribute :>> condition = "Do not use persistent declaration head as proof that whole env is immutable or session-independent"; }
 part view4 : ViewSpec { attribute :>> key = "payload-alias"; attribute :>> anchor = "_env.scm:327-331; _ptree1.scm:543-614,2769-2873; _ptree2.scm:218,433-454; _prims.scm:3083,3211,5485"; attribute :>> sharing = "Stock transform validates bool/integer/symbol payloads and extract-names allocates a fresh list; env-declare itself accepts arbitrary records"; attribute :>> condition = "Include parser/optimizer/primitive derived declarations and their admitted writers; classify payload aliases, raw stores and FFI; syntactic nonuse is not closure"; }
 part view5 : ViewSpec { attribute :>> key = "read-view"; attribute :>> anchor = "_env.scm:335-343; _ptree1.scm:574-575; _back.scm:579-580"; attribute :>> sharing = "first matching named/universal declaration, safe default true, arithmetic default generic"; attribute :>> condition = "Root one related immutable/leased view across complete specialization chain; keep primitive-name identity"; }
 part def CallerSpec { attribute key : String; attribute anchor : String; attribute environment : String; attribute contract : String; }
 part caller0 : CallerSpec { attribute :>> key = "app-helper"; attribute :>> anchor = "_ptree1.scm:333-378"; attribute :>> environment = "Primitive resolution can use operand node-env; specialization receives app node-env"; attribute :>> contract = "Carry resolution and selection views separately; replacing both with current global env is unsound"; }
 part caller1 : CallerSpec { attribute :>> key = "parser-validation"; attribute :>> anchor = "_ptree1.scm:1101,1137"; attribute :>> environment = "app->specialized-proc participates in parse-time checks"; attribute :>> contract = "Diagnostics and rejected calls belong to observer; late GVM-only migration misses this user"; }
 part caller2 : CallerSpec { attribute :>> key = "epc"; attribute :>> anchor = "_ptree2.scm:187-205,325-340"; attribute :>> environment = "Calls specialize-proc with operand node-env; rebuilt nodes can use app node-env"; attribute :>> contract = "Do not normalize different caller environment choices into one unlabeled view"; }
 part caller3 : CallerSpec { attribute :>> key = "branch-rewrite"; attribute :>> anchor = "_ptree2.scm:1116,1442,1503"; attribute :>> environment = "Direct specialize-app uses transformed argument nodes and app env; predicate users compare helper objects"; attribute :>> contract = "Preserve constant/void abstraction and context-local canonical helper identities"; }
 part caller4 : CallerSpec { attribute :>> key = "gvm-and-analysis"; attribute :>> anchor = "_front.scm:2079,3226,3839,3854"; attribute :>> environment = "Calls app helper for switch extraction, call emission, triviality and boolean analysis"; attribute :>> contract = "Migrate result consumers, inline predicates and ** helper slots in the same context domain"; }
 part caller5 : CallerSpec { attribute :>> key = "fixed-point"; attribute :>> anchor = "_ptree1.scm:367-378"; attribute :>> environment = "Initial arity check precedes repeated provider calls until eq? self"; attribute :>> contract = "Transport every step and termination identity; no arbitrary one-step replacement, timeout success or invented per-step arity check"; }
 part def GainSpec { attribute key : String; attribute avoided : String; attribute added : String; attribute condition : String; }
 part gain0 : GainSpec { attribute :>> key = "persistent-view"; attribute :>> avoided = "Repeated declaration-list reconstruction and whole-env copying that would otherwise occur"; attribute :>> added = "View fingerprint, roots/read leases and recursive payload admission"; attribute :>> condition = "Existing persistent updates are baseline; only genuinely repeated work counts"; }
 part gain1 : GainSpec { attribute :>> key = "query-reuse"; attribute :>> avoided = "Repeated specialization and downstream work under identical admitted views"; attribute :>> added = "Keys include caller mode, resolution/selection views, private primitive graph, argument abstraction and observer"; attribute :>> condition = "Expected saved work exceeds key/validation/materialization; raw addresses are not persistent cache keys"; }
 part gain2 : GainSpec { attribute :>> key = "parallel-context"; attribute :>> avoided = "Global declaration/primitive/helper serialization after ownership migration"; attribute :>> added = "Private bindings, helper map, pinned views and roots for full chains"; attribute :>> condition = "Removed span exceeds new overhead; no unsafe sharing of mutable env or implicit gain from core count"; }
 part def RefinementSpec { attribute key : String; attribute qntScope : String; attribute leanScope : String; attribute sourceDuty : String; }
 part refinement0 : RefinementSpec { attribute :>> key = "persistent-scope"; attribute :>> qntScope = "enterScope;addBinding;restoreDecl"; attribute :>> leanScope = "restoreKeepsBinding;batchOrder"; attribute :>> sourceDuty = "Full declaration payload alias closure and actual transform-declaration semantics"; }
 part refinement1 : RefinementSpec { attribute :>> key = "caller-binding"; attribute :>> qntScope = "beginCall;walkStep"; attribute :>> leanScope = "walkTransport;helperIdentity"; attribute :>> sourceDuty = "Caller-specific resolution/selection env and argument abstraction refine source operations"; }
 part refinement2 : RefinementSpec { attribute :>> key = "view-custody"; attribute :>> qntScope = "pinView;releaseView"; attribute :>> leanScope = "headOverride;otherNameStable"; attribute :>> sourceDuty = "Root/read-lease/epoch mechanism truthfully prevents source view mutation and stale restoration"; }
 part refinement3 : RefinementSpec { attribute :>> key = "termination-benefit"; attribute :>> qntScope = "walkStep;finish"; attribute :>> leanScope = "fixedPointTransport;costPositive"; attribute :>> sourceDuty = "Original terminating chain relation plus source/exception/GC and actual work/span evidence"; }
 part def GateSpec { attribute key : String; attribute qualified : Boolean; attribute condition : String; }
 part gate0 : GateSpec { attribute :>> key = "view-closure"; attribute :>> qualified = false; attribute :>> condition = "Declaration spine and record/named payload writer closure proven"; }
 part gate1 : GateSpec { attribute :>> key = "caller-views"; attribute :>> qualified = false; attribute :>> condition = "All real caller resolution/selection views and args preserved"; }
 part gate2 : GateSpec { attribute :>> key = "chain-transport"; attribute :>> qualified = false; attribute :>> condition = "Full valid specialization sequence and original termination relation proven"; }
 part gate3 : GateSpec { attribute :>> key = "helper-domain"; attribute :>> qualified = false; attribute :>> condition = "Private primitive table and ** helper comparisons share one injective identity domain"; }
 part gate4 : GateSpec { attribute :>> key = "observer"; attribute :>> qualified = false; attribute :>> condition = "Identity, generated origin and actual parse/optimizer/emitter diagnostics preserved"; }
 part gate5 : GateSpec { attribute :>> key = "retirement"; attribute :>> qualified = false; attribute :>> condition = "All relevant producer/caller/consumer paths migrated; SP-S remains prerequisite"; }
 part gate6 : GateSpec { attribute :>> key = "platform"; attribute :>> qualified = false; attribute :>> condition = "Native root/GC/FFI/SMP and observed work/span/memory remain unqualified"; }
 attribute workspaceCount : Integer = 2;
 attribute actualAdmitted : Boolean = false;
 part history : GambitAssuranceRouting::ModelNeed { ref part :>> owner = GambitBuildAssurance::planner.component; attribute :>> obligationId = "DC-H"; attribute :>> kind = "interleaving"; attribute :>> subjectPath = "models/build/declaration_specialization_context.qnt"; attribute :>> subjectScope = "declaration_specialization_context:Test$"; attribute :>> premise = "Conditional persistent-view, caller and specialization-chain transport; source/platform closure open"; }
 part induction : GambitAssuranceRouting::ModelNeed { ref part :>> owner = GambitBuildAssurance::planner.component; attribute :>> obligationId = "DC-I"; attribute :>> kind = "induction"; attribute :>> subjectPath = "models/build/DeclarationSpecializationContext.lean"; attribute :>> subjectScope = "DeclarationSpecializationContext:walkTransport;fixedPointTransport;helperIdentity;restoreKeepsBinding;batchOrder;headOverride;otherNameStable;costPositive"; attribute :>> premise = "Conditional persistent-view, caller and specialization-chain transport; source/platform closure open"; }
 part source : GambitAssuranceRouting::ModelNeed { ref part :>> owner = GambitBuildAssurance::planner.component; attribute :>> obligationId = "DC-S"; attribute :>> kind = "source-refinement"; attribute :>> subjectPath = "dev/architecture/toolchain/declaration-specialization-context-design.org"; attribute :>> subjectScope = "DC-S:source"; attribute :>> premise = "Conditional persistent-view, caller and specialization-chain transport; source/platform closure open"; }
 part platform : GambitAssuranceRouting::ModelNeed { ref part :>> owner = GambitBuildAssurance::planner.component; attribute :>> obligationId = "DC-E"; attribute :>> kind = "environment-refinement"; attribute :>> subjectPath = "dev/architecture/toolchain/declaration-specialization-context-design.org"; attribute :>> subjectScope = "DC-E:platform"; attribute :>> premise = "Conditional persistent-view, caller and specialization-chain transport; source/platform closure open"; }
 part dependency0 : GambitAssuranceRouting::NeedDependency { ref part :>> dependent = source; ref part :>> prerequisite = history; }
 part dependency1 : GambitAssuranceRouting::NeedDependency { ref part :>> dependent = source; ref part :>> prerequisite = induction; }
 part dependency2 : GambitAssuranceRouting::NeedDependency { ref part :>> dependent = source; ref part :>> prerequisite = platform; }
 part dependency3 : GambitAssuranceRouting::NeedDependency { ref part :>> dependent = source; ref part :>> prerequisite = SpecializerProviderSemantics::source; }
}
