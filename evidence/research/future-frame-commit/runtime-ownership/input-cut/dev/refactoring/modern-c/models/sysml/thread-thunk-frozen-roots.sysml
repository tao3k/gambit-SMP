package GambitThreadThunkFrozenRoots { private import ScalarValues::*;
part def Route { attribute key:String; attribute sourcePath:String; attribute needle:String; attribute obligation:String; }
part route0:Route { attribute :>> key="resize-request-copy"; attribute :>> sourcePath="vendor/gambit/lib/setup.c"; attribute :>> needle="sop.arg[0] = thunk;"; attribute :>> obligation="Raw sync request word is not automatically a moving root; use a rooted startup handle"; }
part route1:Route { attribute :>> key="resize-collection"; attribute :>> sourcePath="vendor/gambit/lib/setup.c"; attribute :>> needle="if (___garbage_collect_pstate (___ps, 0))"; attribute :>> obligation="Capacity GC can precede thread payload publication"; }
part route2:Route { attribute :>> key="thread-payload-publish"; attribute :>> sourcePath="vendor/gambit/lib/setup.c"; attribute :>> needle="t->data_scmobj = thunk;"; attribute :>> obligation="Initialize VM-owned rooted startup record before thread launch"; }
part route3:Route { attribute :>> key="startup-local-copy"; attribute :>> sourcePath="vendor/gambit/lib/setup.c"; attribute :>> needle="___SCMOBJ thunk = self->data_scmobj;"; attribute :>> obligation="Raw local precedes startup sync; root handles must survive and be resolved after sync"; }
part route4:Route { attribute :>> key="startup-sync"; attribute :>> sourcePath="vendor/gambit/lib/setup.c"; attribute :>> needle="execute_sync_op_loop (___PSP &sop, 0);"; attribute :>> obligation="Loop can execute real sync operations including GC rather than only a no-op"; }
part route5:Route { attribute :>> key="sync-dispatch-gc"; attribute :>> sourcePath="vendor/gambit/lib/setup.c"; attribute :>> needle="case OP_GARBAGE_COLLECT:"; attribute :>> obligation="Actual collective dispatcher reaches garbage_collect_pstate"; }
part route6:Route { attribute :>> key="roster-count-cut"; attribute :>> sourcePath="vendor/gambit/lib/setup.c"; attribute :>> needle="if (sop.op == OP_SET_PROCESSOR_COUNT)"; attribute :>> obligation="Existing barrier algorithm depends on processor_count; pending roots must not be invented GC workers"; }
part route7:Route { attribute :>> key="frozen-root-view"; attribute :>> sourcePath="vendor/gambit/lib/mem.c"; attribute :>> needle="participant->context = ___ps->context;"; attribute :>> obligation="Freeze snapshots exact context and root provider membership"; }
part route8:Route { attribute :>> key="context-root-scan"; attribute :>> sourcePath="vendor/gambit/lib/mem.c"; attribute :>> needle="mark_execution_roots (work,"; attribute :>> obligation="Current scan reaches frozen execution context; pending startup directory is proposed additional source"; }
part route9:Route { attribute :>> key="worker-view-drain"; attribute :>> sourcePath="vendor/gambit/lib/mem.c"; attribute :>> needle="BARRIER(); /* no worker may retain a stopped root view past this cut */"; attribute :>> obligation="Source retirement waits for old scanner leases and restored phase"; }
part route10:Route { attribute :>> key="thread-create-call"; attribute :>> sourcePath="vendor/gambit/lib/os_thread.c"; attribute :>> needle="if (pthread_create (&thread_id,"; attribute :>> obligation="Successful platform creation and service acknowledgement are different observations"; }
part route11:Route { attribute :>> key="thread-common-success"; attribute :>> sourcePath="vendor/gambit/lib/os_thread.c"; attribute :>> needle="___HIDDEN ___SCMOBJ thread_init_common"; attribute :>> obligation="Current helper returns NO_ERR; do not invent a post-creation helper failure"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule5; ref part :>> counterpart=GambitRuntimeComposition::blueprintModule3; attribute :>> key="rooted-resize-request"; attribute :>> owner="control/roots"; attribute :>> actionName="registerStartup launch syncCollect"; attribute :>> invariant="Thunks travel as VM-owned root handles across collective request and OS launch"; attribute :>> gap="Raw sync words thread payload and copied locals need real caller migration"; }
part contract1:Contract { ref part :>> accountable=GambitRuntimeComposition::blueprintModule3; ref part :>> counterpart=GambitRuntimeComposition::blueprintModule2; attribute :>> key="pending-start-roots"; attribute :>> owner="roots/execution"; attribute :>> actionName="activate releaseSource"; attribute :>> invariant="Pending startup roots are scanned independently of whether their execution thread is ready"; attribute :>> gap="No current pending startup root directory or GC consumer is established"; }
part contract2:Contract { ref part :>> accountable=GambitRuntimeComposition::blueprintModule4; ref part :>> counterpart=GambitRuntimeComposition::blueprintModule3; attribute :>> key="frozen-manifest"; attribute :>> owner="collector/roots"; attribute :>> actionName="stage freeze scan restore"; attribute :>> invariant="Frozen manifest is immutable; late arrivals are staged and retain source roots"; attribute :>> gap="Actual root provider union assignment and backend publication remain open"; }
part contract3:Contract { ref part :>> accountable=GambitRuntimeComposition::blueprintModule3; ref part :>> counterpart=GambitRuntimeComposition::blueprintModule7; attribute :>> key="persistent-next-round"; attribute :>> owner="roots/release"; attribute :>> actionName="activate queryReceipt releaseSource"; attribute :>> invariant="Receipt certifies persistent future membership not merely current scan or queued acceptance"; attribute :>> gap="Source release only in running phase after old scan leases drain"; }
part contract4:Contract { ref part :>> accountable=GambitRuntimeComposition::blueprintModule7; ref part :>> counterpart=GambitRuntimeComposition::blueprintModule5; attribute :>> key="startup-failure-custody"; attribute :>> owner="release/control"; attribute :>> actionName="launchUnknown resolveLaunch rejectCreate"; attribute :>> invariant="Known rejection retains parent; unknown service result retains parent and startup record"; attribute :>> gap="Platform reject is not an ambiguous started thread; actual cancellation and stop closure open"; }
part contract5:Contract { ref part :>> accountable=GambitRuntimeComposition::blueprintModule8; ref part :>> counterpart=GambitRuntimeComposition::blueprintModule0; attribute :>> key="typed-evidence"; attribute :>> owner="build/semantic"; attribute :>> actionName="activate restore releaseSource"; attribute :>> invariant="Actual selected IR expressions and exact receipt scope bind model evidence"; attribute :>> gap="Full composition startup-to-root-manifest and C11 source bridge remain unproved"; }
part def Obligation { attribute key:String; attribute status:String; attribute scope:String; attribute counterexample:String; }
part obligation0:Obligation { attribute :>> key="frozen-round-admission"; attribute :>> status="bounded-checked"; attribute :>> scope="One root provider two GC rounds source-target registration and late admission"; attribute :>> counterexample="Queued registration is not current or future root coverage"; }
part obligation1:Obligation { attribute :>> key="startup-root-handle"; attribute :>> status="bounded-checked"; attribute :>> scope="One startup parent pending root OS entry and sync collection"; attribute :>> counterexample="Old local can be stale after sync even while root handle remains valid"; }
part obligation2:Obligation { attribute :>> key="release-guard"; attribute :>> status="conditional-proved"; attribute :>> scope="Frozen phase missing future membership and unknown receipt block source release"; attribute :>> counterexample="Receipt validity must persist until target retirement"; }
part obligation3:Obligation { attribute :>> key="scan-drain-order"; attribute :>> status="conditional-proved"; attribute :>> scope="Old worker last use precedes restored phase and source release given HB embedding"; attribute :>> counterexample="Event ordering is not a C11 execution proof"; }
part obligation4:Obligation { attribute :>> key="actual-ir"; attribute :>> status="conditional-proved"; attribute :>> scope="Actual activate restore releaseSource guard/update meaning"; attribute :>> counterexample="Parser and restricted emitter remain trusted"; }
part obligation5:Obligation { attribute :>> key="runtime-composition"; attribute :>> status="open"; attribute :>> scope="Actual sync operation handle pending root manifest all source users and two-model relation"; attribute :>> counterexample="Neither root lifetime nor OS creation certifies participant readiness"; }
part obligation6:Obligation { attribute :>> key="json-domain"; attribute :>> status="partially-proved"; attribute :>> scope="91 checked reference rows finite environment and guard mutation refusal"; attribute :>> counterexample="Actual compiler root-map extraction remains open"; }
part def Gain { attribute key:String; attribute avoided:String; attribute added:String; attribute condition:String; }
part gain0:Gain { attribute :>> key="no-raw-thunk-copies"; attribute :>> avoided="Repeated protection rules for raw thunk copies in sync payload thread payload and ___run"; attribute :>> added="One persistent rooted startup handle resolution and generated entry-root contract"; attribute :>> condition="Every managed request and caller resolves handle under correct collector access"; }
part gain1:Gain { attribute :>> key="pending-roots-not-workers"; attribute :>> avoided="Making root coverage depend on execution thread startup readiness"; attribute :>> added="VM pending-root directory plus A root locations per pending startup"; attribute :>> condition="Collector can enumerate data providers independently of closed worker roster"; }
part gain2:Gain { attribute :>> key="persistent-membership"; attribute :>> avoided="Keeping duplicate source registration after target coverage is known"; attribute :>> added="Registration receipt and old scan-lease drain; short overlap may scan twice"; attribute :>> condition="Future-round membership preserved; command/source ownership is a separate obligation"; }
part gain3:Gain { attribute :>> key="defer-frozen-arrivals"; attribute :>> avoided="Expensive rescanning or reopening a finished round for every late registration"; attribute :>> added="Queue metadata and retain existing source until running-phase admission"; attribute :>> condition="Source remains visible to current GC; no unrooted foreign raw object admission"; }
part gain4:Gain { attribute :>> key="modern-c-system"; attribute :>> avoided="A second language is unnecessary for typed root requests and snapshot contracts"; attribute :>> added="Modern C ownership maps atomic publication and cohort lifecycle proof"; attribute :>> condition="Zig benefit must be independently shown; none follows from these root obligations"; }
part def Binding { attribute key:String; attribute qntAction:String; attribute leanLemma:String; attribute refinement:String; attribute guardLemma:String; attribute updateLemma:String; }
part binding0:Binding { attribute :>> key="guard"; attribute :>> qntAction="activate"; attribute :>> leanLemma="unstagedRejectsActivation"; attribute :>> refinement="Selected actual expression certified; runtime source relation remains open"; attribute :>> guardLemma="activateGuardMeaning"; attribute :>> updateLemma="activateNextMeaning"; }
part binding1:Binding { attribute :>> key="roots"; attribute :>> qntAction="restore"; attribute :>> leanLemma="scannerBlocksRestore"; attribute :>> refinement="Selected actual expression certified; runtime source relation remains open"; attribute :>> guardLemma="restoreGuardMeaning"; attribute :>> updateLemma="restoreNextMeaning"; }
part binding2:Binding { attribute :>> key="release"; attribute :>> qntAction="releaseSource"; attribute :>> leanLemma="noFutureRejectsRelease"; attribute :>> refinement="Selected actual expression certified; runtime source relation remains open"; attribute :>> guardLemma="releaseSourceGuardMeaning"; attribute :>> updateLemma="releaseSourceNextMeaning"; }
part def Flow { attribute fromNode:String; attribute toNode:String; attribute reason:String; }
part flow0:Flow { attribute :>> fromNode="c0"; attribute :>> toNode="c1"; attribute :>> reason="Register pending roots before launch"; }
part flow1:Flow { attribute :>> fromNode="c1"; attribute :>> toNode="c2"; attribute :>> reason="Freeze active root providers independently of worker readiness"; }
part flow2:Flow { attribute :>> fromNode="c2"; attribute :>> toNode="c3"; attribute :>> reason="Restored admission certifies future membership"; }
part flow3:Flow { attribute :>> fromNode="c3"; attribute :>> toNode="c4"; attribute :>> reason="Only known ownership can retire creator source"; }
part flow4:Flow { attribute :>> fromNode="c0"; attribute :>> toNode="o1"; attribute :>> reason="Thread local reload after sync"; }
part flow5:Flow { attribute :>> fromNode="c1"; attribute :>> toNode="o0"; attribute :>> reason="Persistent pending-root enumeration"; }
part flow6:Flow { attribute :>> fromNode="c2"; attribute :>> toNode="o0"; attribute :>> reason="Late stage cannot change frozen manifest"; }
part flow7:Flow { attribute :>> fromNode="c3"; attribute :>> toNode="o2"; attribute :>> reason="Future coverage and phase guard"; }
part flow8:Flow { attribute :>> fromNode="c2"; attribute :>> toNode="o3"; attribute :>> reason="Old scan views drain before restore"; }
part flow9:Flow { attribute :>> fromNode="c5"; attribute :>> toNode="o4"; attribute :>> reason="Actual typed action meanings"; }
part flow10:Flow { attribute :>> fromNode="c5"; attribute :>> toNode="o6"; attribute :>> reason="Finite JSON lookup evidence"; }
part flow11:Flow { attribute :>> fromNode="c4"; attribute :>> toNode="o1"; attribute :>> reason="Unknown launch retains source"; }
part history:GambitAssuranceRouting::ModelNeed { ref part :>> owner=GambitBuildAssurance::planner.component; attribute :>> obligationId="TF-H"; attribute :>> kind="interleaving"; attribute :>> subjectPath="dev/refactoring/modern-c/models/quint/frozen_bundle_admission.qnt"; attribute :>> subjectScope="One root provider two frozen GC rounds persistent future coverage and scan lease drain"; attribute :>> premise="Bounded models and restricted algebra only; no runtime implementation or native acceptance"; }
part shards:GambitAssuranceRouting::ModelNeed { ref part :>> owner=GambitBuildAssurance::planner.component; attribute :>> obligationId="TF-B"; attribute :>> kind="interleaving"; attribute :>> subjectPath="dev/refactoring/modern-c/models/quint/thread_thunk_root.qnt"; attribute :>> subjectScope="VM pending startup root handle survives OS launch sync collection and ambiguous service reply"; attribute :>> premise="Bounded models and restricted algebra only; no runtime implementation or native acceptance"; }
part induction:GambitAssuranceRouting::ModelNeed { ref part :>> owner=GambitBuildAssurance::planner.component; attribute :>> obligationId="TF-I"; attribute :>> kind="induction"; attribute :>> subjectPath="dev/refactoring/modern-c/models/lean/ThreadThunkFrozenRoots.lean"; attribute :>> subjectScope="Admission and release guard exclusions coverage preservation and conditional ordering"; attribute :>> premise="Bounded models and restricted algebra only; no runtime implementation or native acceptance"; }
part expression:GambitAssuranceRouting::ModelNeed { ref part :>> owner=GambitBuildAssurance::planner.component; attribute :>> obligationId="TF-X"; attribute :>> kind="induction"; attribute :>> subjectPath="dev/refactoring/modern-c/models/lean/ThreadThunkFrozenAst.lean"; attribute :>> subjectScope="Actual activate restore releaseSource expressions and finite reference environment"; attribute :>> premise="Bounded models and restricted algebra only; no runtime implementation or native acceptance"; }
part source:GambitAssuranceRouting::ModelNeed { ref part :>> owner=GambitBuildAssurance::planner.component; attribute :>> obligationId="TF-S"; attribute :>> kind="source-refinement"; attribute :>> subjectPath="dev/refactoring/modern-c/thread-thunk-frozen-roots-design.org"; attribute :>> subjectScope="Raw sync request startup handle pending directory and complete caller relation OPEN"; attribute :>> premise="Bounded models and restricted algebra only; no runtime implementation or native acceptance"; }
part platform:GambitAssuranceRouting::ModelNeed { ref part :>> owner=GambitBuildAssurance::planner.component; attribute :>> obligationId="TF-E"; attribute :>> kind="environment-refinement"; attribute :>> subjectPath="dev/refactoring/modern-c/thread-thunk-frozen-roots-design.org"; attribute :>> subjectScope="C11 frozen manifests backend barriers platform create and scan view reclamation OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitIngressCarrierTransfer::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; attribute sourcePath:String; attribute needle:String; }
part endorsement0:Endorsement { attribute :>> roleName="semantic"; attribute :>> scope="Startup handle remains rooted across sync and marker allocation"; attribute :>> issuer="Startup root and execution context owner"; attribute :>> sourcePath="vendor/gambit/lib/setup.c"; attribute :>> needle="___SCMOBJ thunk = self->data_scmobj;"; }
part endorsement1:Endorsement { attribute :>> roleName="foreign"; attribute :>> scope="OS launch outcome service reply and creator-child lifetime settled"; attribute :>> issuer="Thread lifecycle adapter owner"; attribute :>> sourcePath="vendor/gambit/lib/os_thread.c"; attribute :>> needle="if (pthread_create (&thread_id,"; }
part endorsement2:Endorsement { attribute :>> roleName="resident"; attribute :>> scope="Frozen provider views drained persistent registry covers next round"; attribute :>> issuer="VM root directory and collector coordinator"; attribute :>> sourcePath="vendor/gambit/lib/mem.c"; attribute :>> needle="BARRIER(); /* no worker may retain a stopped root view past this cut */"; }
part flow12:Flow { attribute :>> fromNode="o4"; attribute :>> toNode="o5"; attribute :>> reason="Selected meaning is not full simulation"; }
part flow13:Flow { attribute :>> fromNode="c1"; attribute :>> toNode="o5"; attribute :>> reason="New pending-root consumer needs actual source refinement"; }
part flow14:Flow { attribute :>> fromNode="c3"; attribute :>> toNode="c5"; attribute :>> reason="Receipt identity and evidence scope"; }
part flow15:Flow { attribute :>> fromNode="c4"; attribute :>> toNode="o5"; attribute :>> reason="Actual launch cancellation stop and join obligations"; }
}
