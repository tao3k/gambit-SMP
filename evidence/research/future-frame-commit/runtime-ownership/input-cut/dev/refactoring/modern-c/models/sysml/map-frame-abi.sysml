package GambitMapFrameAbi { private import ScalarValues::*;
part def SourceLink { attribute key:String; attribute sourcePath:String; attribute sourceNeedle:String; attribute consumer:String; attribute obligation:String; attribute actionName:String; attribute guardName:String; attribute lemmaName:String; attribute boundary:String; }
part def FrameWitness { attribute key:String; attribute sourcePath:String; attribute labelIndex:Integer; attribute storedFs:Integer; attribute linkSlot:Integer; attribute mask:Integer; attribute liveSlots:String; attribute useSite:String; }
part def AbiImpact { attribute key:String; attribute trigger:String; attribute semantic:String; attribute native:String; attribute runtime:String; attribute retirement:String; }
part def Refinement { attribute key:String; attribute qualified:Boolean; attribute lemma:String; attribute premise:String; attribute gap:String; }
part def Gain { attribute key:String; attribute avoided:String; attribute added:String; attribute condition:String; }
part def Gate { attribute key:String; attribute qualified:Boolean; attribute duty:String; }

ref part owner0=GambitRuntimeComposition::blueprintModule0;
ref part owner1=GambitRuntimeComposition::blueprintModule1;
ref part owner2=GambitRuntimeComposition::blueprintModule2;
ref part owner3=GambitRuntimeComposition::blueprintModule3;
ref part owner4=GambitRuntimeComposition::blueprintModule4;
ref part owner5=GambitRuntimeComposition::blueprintModule5;
ref part owner6=GambitRuntimeComposition::blueprintModule6;
ref part owner7=GambitRuntimeComposition::blueprintModule7;
ref part owner8=GambitRuntimeComposition::blueprintModule8;
part source0:SourceLink { attribute :>> key="scheme-frame-producer"; attribute :>> sourcePath="vendor/gambit/gsc/_t-c-2.scm"; attribute :>> sourceNeedle="(define (targ-gen-label-return*"; attribute :>> consumer="GC/control/native"; attribute :>> obligation="Per-successor liveness, return variable and internal saved-register closure"; attribute :>> actionName="emit"; attribute :>> guardName="true"; attribute :>> lemmaName="forwardSimulation"; attribute :>> boundary="Source-to-QNT guard/update semantics and Scheme output identity remain open"; }
part source1:SourceLink { attribute :>> key="frame-freeze"; attribute :>> sourcePath="vendor/gambit/gsc/_t-c-3.scm"; attribute :>> sourceNeedle="(define (targ-make-frame-spec"; attribute :>> consumer="C descriptor emitter"; attribute :>> obligation="Validate kind/fs/link/map and preserve stored versus actual frame sizes"; attribute :>> actionName="emit"; attribute :>> guardName="true"; attribute :>> lemmaName="forwardSimulation"; attribute :>> boundary="Existing constructor reused; not claimed as new implementation"; }
part source2:SourceLink { attribute :>> key="descriptor-emission"; attribute :>> sourcePath="vendor/gambit/gsc/_t-c-1.scm"; attribute :>> sourceNeedle="(targ-frame-spec-stored-fs info)"; attribute :>> consumer="module label and OFD tables"; attribute :>> obligation="Emit exact constructor result; no reinterpretation or new implicit layout"; attribute :>> actionName="compile"; attribute :>> guardName="s.emitted"; attribute :>> lemmaName="forwardSimulation"; attribute :>> boundary="No re-generation or installed-object provenance proven"; }
part source3:SourceLink { attribute :>> key="stored-map-labels"; attribute :>> sourcePath="vendor/gambit/lib/_std.c"; attribute :>> sourceNeedle=",___DEF_LBL_INTRO(___H_map,"; attribute :>> consumer="all map frame consumers"; attribute :>> obligation="L2 normal(5,0,7), L4 normal(5,0,9); actual internal descriptors remain distinct"; attribute :>> actionName="capture"; attribute :>> guardName="not(s.captured)"; attribute :>> lemmaName="forwardSimulation"; attribute :>> boundary="Only two normal rows enter arithmetic proof; twenty other returns not erased"; }
part source4:SourceLink { attribute :>> key="gc-frame-reader"; attribute :>> sourcePath="vendor/gambit/lib/mem.c"; attribute :>> sourceNeedle="___HIDDEN void mark_frame"; attribute :>> consumer="stack and captured frame GC"; attribute :>> obligation="Decode same slots, scan selected roots, update moving references, keep return labels alive"; attribute :>> actionName="collect"; attribute :>> guardName="s.root"; attribute :>> lemmaName="forwardSimulation"; attribute :>> boundary="Opaque root Boolean does not prove all real roots or heap relocation"; }
part source5:SourceLink { attribute :>> key="restore-reader"; attribute :>> sourcePath="vendor/gambit/lib/_kernel.scm"; attribute :>> sourceNeedle="fp += fs+1; /* get base of frame */"; attribute :>> consumer="heap frame to execution stack"; attribute :>> obligation="Copy frame fields, preserve logical values and denv/wind, reload roots before execution"; attribute :>> actionName="reload"; attribute :>> guardName="not(s.running)"; attribute :>> lemmaName="forwardSimulation"; attribute :>> boundary="No complete concrete frame-value transfer or dynamic-wind simulation"; }
part source6:SourceLink { attribute :>> key="multishot-caller"; attribute :>> sourcePath="vendor/gambit/lib/_thread.scm"; attribute :>> sourceNeedle="(define-prim (##continuation-graft-aux"; attribute :>> consumer="repeatable saved continuation"; attribute :>> obligation="Each shot has fresh execution/native activation and shared Scheme identities"; attribute :>> actionName="resume"; attribute :>> guardName="s.loaded==s.epoch"; attribute :>> lemmaName="forwardSimulation"; attribute :>> boundary="Three abstract invocations do not compute real map outputs or arbitrary shots"; }
part source7:SourceLink { attribute :>> key="module-fixup"; attribute :>> sourcePath="vendor/gambit/lib/setup.c"; attribute :>> sourceNeedle="___HIDDEN ___SCMOBJ setup_module_fixup"; attribute :>> consumer="installed descriptor/code cohort"; attribute :>> obligation="Validate semantic frame ABI and bind exact labels/OFD tables before entering module"; attribute :>> actionName="bind"; attribute :>> guardName="s.native"; attribute :>> lemmaName="forwardSimulation"; attribute :>> boundary="Current version/sizeof checks do not certify frame-wire semantics"; }
part source8:SourceLink { attribute :>> key="artifact-driver"; attribute :>> sourcePath="../gerbil-gambit-bootstrap-audit/src/gerbil/compiler/driver.ss"; attribute :>> sourceNeedle="(def (compile-scm-file"; attribute :>> consumer="Gerbil stage query and native jobs"; attribute :>> obligation="ABI edit invalidates true descendants; a native tool edit cannot certify layout equivalence by itself"; attribute :>> actionName="abiEdit"; attribute :>> guardName="true"; attribute :>> lemmaName="forwardSimulation"; attribute :>> boundary="Full dynamic dependencies, snapshots and observable result encoding open"; }
part source9:SourceLink { attribute :>> key="frame-reflection"; attribute :>> sourcePath="vendor/gambit/lib/_io.scm"; attribute :>> sourceNeedle="(define-prim (##implode-frame"; attribute :>> consumer="frame mutation and deserialization"; attribute :>> obligation="Reconstruction is a writer and never recreates expired native authority"; attribute :>> actionName="returnShot"; attribute :>> guardName="s.running"; attribute :>> lemmaName="forwardSimulation"; attribute :>> boundary="Reflection/writer closure remains a source requirement outside this finite protocol"; }
part source10:SourceLink { attribute :>> key="old-cohort-retirement"; attribute :>> sourcePath="vendor/gambit/lib/os_dyn.c"; attribute :>> sourceNeedle="___cleanup_dyn_module"; attribute :>> consumer="loader, saved frames, GC and diagnostics"; attribute :>> obligation="No unload while captured return addresses/descriptors or actual native users remain"; attribute :>> actionName="releaseCaptured"; attribute :>> guardName="not(s.running)"; attribute :>> lemmaName="forwardSimulation"; attribute :>> boundary="Model release is admitted all-alias grace, not inference from caller return"; }
part witness0:FrameWitness { attribute :>> key="callback-return"; attribute :>> sourcePath="vendor/gambit/lib/_std.c"; attribute :>> labelIndex=2; attribute :>> storedFs=5; attribute :>> linkSlot=0; attribute :>> mask=7; attribute :>> liveSlots="1,2,3"; attribute :>> useSite="STK(-6) proc and STK(-5) source list after callback"; }
part witness1:FrameWitness { attribute :>> key="recursive-return"; attribute :>> sourcePath="vendor/gambit/lib/_std.c"; attribute :>> labelIndex=4; attribute :>> storedFs=5; attribute :>> linkSlot=0; attribute :>> mask=9; attribute :>> liveSlots="1,4"; attribute :>> useSite="STK(-4) saved callback result plus returned suffix before CONS"; }
part impact0:AbiImpact { attribute :>> key="liveness-content"; attribute :>> trigger="Changed map body or successor roots, unchanged wire schema"; attribute :>> semantic="Recompute affected procedure plan and semantic dependency consumers"; attribute :>> native="Re-emit/recompile changed module and true inline/dependency consumers"; attribute :>> runtime="Reuse unchanged decoder; retain old module descriptors/code for live saved frames"; attribute :>> retirement="Do not rebuild whole runtime just because a mask value changes"; }
part impact1:AbiImpact { attribute :>> key="frame-wire-schema"; attribute :>> trigger="Changed tag, bit width, slot interpretation, internal saved-register or OFD rules"; attribute :>> semantic="Reuse only a proven target-independent semantic projection"; attribute :>> native="Invalidate matching emitter/decoder/runtime/loader/native ABI cohort"; attribute :>> runtime="All readers must agree; old frames require old decoder service or proven migration, otherwise reject activation"; attribute :>> retirement="Old descriptor decoder retires only after old GC/capture/restore/label users close"; }
part impact2:AbiImpact { attribute :>> key="target-physical"; attribute :>> trigger="Changed word size, alignment, register allocation/call/root representation"; attribute :>> semantic="Target feedback can invalidate normalization, primitives and GVM; never assume frontend reuse"; attribute :>> native="Rebuild affected layout and code plus runtime ABI consumers"; attribute :>> runtime="No mixing old saved frames with incompatible collector/restore representation"; attribute :>> retirement="Portability remains parameterized; no universal cross-architecture saved continuation"; }
part impact3:AbiImpact { attribute :>> key="native-tool"; attribute :>> trigger="Compiler or service upgrade with demonstrated unchanged semantic/layout contract"; attribute :>> semantic="Keep admitted semantic and emission products"; attribute :>> native="Invalidate affected object/link recipes; ABI-changing flags reclassify as target-physical"; attribute :>> runtime="Keep installed live cohort; tool identity is not runtime compatibility proof"; attribute :>> retirement="Retire repeated frontend work only with dependency and output equivalence"; }
part impact4:AbiImpact { attribute :>> key="no-change"; attribute :>> trigger="Exact demanded projections, trace and output manifests stable"; attribute :>> semantic="Zero admitted semantic producer executions; fresh stateful instances still cost"; attribute :>> native="Reuse matching emitted/object/link products"; attribute :>> runtime="No runtime layout replacement required"; attribute :>> retirement="No timestamps or same file names as reuse authority"; }
part refine0:Refinement { attribute :>> key="initial"; attribute :>> qualified=true; attribute :>> lemma="initialSafe"; attribute :>> premise="Literal selected QState initial record and alpha image"; attribute :>> gap="QNT evaluator initialization semantics and literal-expression encoding still require external bridge"; }
part refine1:Refinement { attribute :>> key="representation"; attribute :>> qualified=true; attribute :>> lemma="safetyReflection"; attribute :>> premise="Explicit flat-QState to nested-LState alpha and relates"; attribute :>> gap="Real Scheme values, root addresses and native objects are not encoded by this relation"; }
part refine2:Refinement { attribute :>> key="guards"; attribute :>> qualified=true; attribute :>> lemma="guardCorrespondence"; attribute :>> premise="All twelve Lean Event cases including stutter"; attribute :>> gap="QNT source expression semantics to qGuard is not kernel-proved"; }
part refine3:Refinement { attribute :>> key="updates"; attribute :>> qualified=true; attribute :>> lemma="updateCorrespondence"; attribute :>> premise="All twelve Lean Event cases including stutter"; attribute :>> gap="QNT record-update semantics to qNext is not kernel-proved"; }
part refine4:Refinement { attribute :>> key="steps"; attribute :>> qualified=true; attribute :>> lemma="forwardSimulation"; attribute :>> premise="Any Lean qStep under relates has a matching lStep"; attribute :>> gap="This is a mirror-transition theorem, not a proof about the Quint tool implementation"; }
part refine5:Refinement { attribute :>> key="histories"; attribute :>> qualified=true; attribute :>> lemma="historySimulation"; attribute :>> premise="Finite arbitrary-length histories of the mirrored relations"; attribute :>> gap="Three-shot bound is an explicit QNT instance, not a Scheme restriction"; }
part refine6:Refinement { attribute :>> key="qnt-encoding"; attribute :>> qualified=false; attribute :>> lemma="open"; attribute :>> premise="Interpreter/translation relation for exact QNT guard/update/Int/Bool/stutter expressions"; attribute :>> gap="Independent expression semantics or verified translation needed; textual hashes and theorem names are insufficient"; }
part refine7:Refinement { attribute :>> key="source-and-progress"; attribute :>> qualified=false; attribute :>> lemma="open"; attribute :>> premise="Scheme map, physical GC relocation, native loader, all aliases and fair progress"; attribute :>> gap="Source simulation, full OFD/RETI, C11 and concurrency/liveness remain open"; }
part gain0:Gain { attribute :>> key="shared-frame-contract"; attribute :>> avoided="Repeated semantic/layout interpretation across emission, GC, restore and loader"; attribute :>> added="Schema completeness, descriptor space and joint migration"; attribute :>> condition="Current Scheme FrameSpec and C decoder already exist; savings must be additional real retired responsibilities"; }
part gain1:Gain { attribute :>> key="old-cohort-reuse"; attribute :>> avoided="Rebuilding/re-expanding unchanged semantic products for a layout or tool-only edit"; attribute :>> added="Exact dependency projections, validation and old code/descriptor pins"; attribute :>> condition="No speedup if changed target semantics cross the cut; old live frames may retain unbounded storage"; }
part gain2:Gain { attribute :>> key="multishot-gc"; attribute :>> avoided="Eligible repeated mature graph scans and repeated support construction"; attribute :>> added="Remembered stores, roots, per-shot restore/wind/native effects"; attribute :>> condition="Mask correctness is necessary but insufficient for generational scan exclusion; full writers and GC architecture remain open"; }
part gain3:Gain { attribute :>> key="precise-invalidation"; attribute :>> avoided="Unnecessary whole-runtime rebuild on a per-procedure root-mask edit"; attribute :>> added="Per-module/spec/codec fingerprints and consumer graph"; attribute :>> condition="Schema change still invalidates all affected readers; bytes/time and net gain unmeasured"; }
part gate0:Gate { attribute :>> key="scheme-generation"; attribute :>> qualified=false; attribute :>> duty="Reproduce exact Scheme-to-descriptor output under identified configuration"; }
part gate1:Gate { attribute :>> key="full-frame-coverage"; attribute :>> qualified=false; attribute :>> duty="Normal/internal/task, inline/OFD, saved-register and all return label roots"; }
part gate2:Gate { attribute :>> key="source-observations"; attribute :>> qualified=false; attribute :>> duty="Map values, aliases, denv, dynamic-wind, exceptions and native suffix effects"; }
part gate3:Gate { attribute :>> key="gc-runtime"; attribute :>> qualified=false; attribute :>> duty="Nonzero roots, all stores, moving GC, phase progress and capacity"; }
part gate4:Gate { attribute :>> key="old-code-grace"; attribute :>> qualified=false; attribute :>> duty="Loader, captured/saved frames, active callers, GC and native diagnostic users all close"; }
part gate5:Gate { attribute :>> key="incremental-reflection"; attribute :>> qualified=false; attribute :>> duty="Complete dynamic trace, input snapshots, phase support and consumer observation equivalence"; }
part gate6:Gate { attribute :>> key="qnt-c11-native"; attribute :>> qualified=false; attribute :>> duty="Exact QNT encoding, C11/ABI instruction refinement and unchanged native acceptance"; }
part history:GambitAssuranceRouting::ModelNeed { ref part :>> owner=GambitBuildAssurance::planner.component; attribute :>> obligationId="MF-H"; attribute :>> kind="interleaving"; attribute :>> subjectPath="dev/refactoring/modern-c/models/quint/map_frame_abi.qnt"; attribute :>> subjectScope="Three-shot, two normal map frame masks, staged ABI edits and old installed cohort pins; finite abstract protocol"; attribute :>> premise="Stored source witness is not newly generated or native; mirror proofs do not close QNT expression semantics or whole-source observations"; }
part induction:GambitAssuranceRouting::ModelNeed { ref part :>> owner=GambitBuildAssurance::planner.component; attribute :>> obligationId="MF-I"; attribute :>> kind="induction"; attribute :>> subjectPath="dev/refactoring/modern-c/models/lean/MapFrameAbi.lean"; attribute :>> subjectScope="Explicit flat/nested relation, twelve event guard/update and history simulation, safety reflection and two stored descriptor witnesses; QNT expression bridge open"; attribute :>> premise="Stored source witness is not newly generated or native; mirror proofs do not close QNT expression semantics or whole-source observations"; }
part source:GambitAssuranceRouting::ModelNeed { ref part :>> owner=GambitBuildAssurance::planner.component; attribute :>> obligationId="MF-S"; attribute :>> kind="source-refinement"; attribute :>> subjectPath="dev/refactoring/modern-c/map-frame-abi-design.org"; attribute :>> subjectScope="Scheme producer, descriptor emit/decode, real GC/restore/module consumers and clean/incremental observation reflection OPEN"; attribute :>> premise="Stored source witness is not newly generated or native; mirror proofs do not close QNT expression semantics or whole-source observations"; }
part platform:GambitAssuranceRouting::ModelNeed { ref part :>> owner=GambitBuildAssurance::planner.component; attribute :>> obligationId="MF-E"; attribute :>> kind="environment-refinement"; attribute :>> subjectPath="dev/refactoring/modern-c/map-frame-abi-design.org"; attribute :>> subjectScope="C11, effective target/configuration, moving roots, loader lifetime and native/performance acceptance OPEN"; attribute :>> premise="Stored source witness is not newly generated or native; mirror proofs do not close QNT expression semantics or whole-source observations"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitAdvantageArchitecture::source; }

part def StateField { attribute qntField:String; attribute leanField:String; attribute representation:String; }
part def EventBinding { attribute actionName:String; attribute guardName:String; attribute lemmaName:String; }
part field0:StateField { attribute :>> qntField="cb"; attribute :>> leanField="shape.cb"; attribute :>> representation="unbounded mathematical Int identity"; }
part field1:StateField { attribute :>> qntField="rc"; attribute :>> leanField="shape.rc"; attribute :>> representation="unbounded mathematical Int identity"; }
part field2:StateField { attribute :>> qntField="fs"; attribute :>> leanField="shape.fs"; attribute :>> representation="unbounded mathematical Int identity"; }
part field3:StateField { attribute :>> qntField="link"; attribute :>> leanField="shape.link"; attribute :>> representation="unbounded mathematical Int identity"; }
part field4:StateField { attribute :>> qntField="captured"; attribute :>> leanField="run.captured"; attribute :>> representation="Bool identity"; }
part field5:StateField { attribute :>> qntField="root"; attribute :>> leanField="run.root"; attribute :>> representation="Bool identity"; }
part field6:StateField { attribute :>> qntField="pin"; attribute :>> leanField="run.pin"; attribute :>> representation="Bool identity"; }
part field7:StateField { attribute :>> qntField="running"; attribute :>> leanField="run.running"; attribute :>> representation="Bool identity"; }
part field8:StateField { attribute :>> qntField="epoch"; attribute :>> leanField="run.epoch"; attribute :>> representation="unbounded mathematical Int identity"; }
part field9:StateField { attribute :>> qntField="loaded"; attribute :>> leanField="run.loaded"; attribute :>> representation="unbounded mathematical Int identity"; }
part field10:StateField { attribute :>> qntField="shots"; attribute :>> leanField="run.shots"; attribute :>> representation="unbounded mathematical Int identity"; }
part field11:StateField { attribute :>> qntField="frameAbi"; attribute :>> leanField="run.frameAbi"; attribute :>> representation="unbounded mathematical Int identity"; }
part field12:StateField { attribute :>> qntField="runtimeAbi"; attribute :>> leanField="run.runtimeAbi"; attribute :>> representation="unbounded mathematical Int identity"; }
part field13:StateField { attribute :>> qntField="abi"; attribute :>> leanField="build.abi"; attribute :>> representation="unbounded mathematical Int identity"; }
part field14:StateField { attribute :>> qntField="emitAbi"; attribute :>> leanField="build.emitAbi"; attribute :>> representation="unbounded mathematical Int identity"; }
part field15:StateField { attribute :>> qntField="objAbi"; attribute :>> leanField="build.objAbi"; attribute :>> representation="unbounded mathematical Int identity"; }
part field16:StateField { attribute :>> qntField="emitted"; attribute :>> leanField="build.emitted"; attribute :>> representation="Bool identity"; }
part field17:StateField { attribute :>> qntField="native"; attribute :>> leanField="build.native"; attribute :>> representation="Bool identity"; }
part field18:StateField { attribute :>> qntField="tool"; attribute :>> leanField="build.tool"; attribute :>> representation="unbounded mathematical Int identity"; }
part field19:StateField { attribute :>> qntField="objTool"; attribute :>> leanField="build.objTool"; attribute :>> representation="unbounded mathematical Int identity"; }
part event0:EventBinding { attribute :>> actionName="capture"; attribute :>> guardName="not(s.captured)"; attribute :>> lemmaName="forwardSimulation"; }
part event1:EventBinding { attribute :>> actionName="collect"; attribute :>> guardName="s.root"; attribute :>> lemmaName="forwardSimulation"; }
part event2:EventBinding { attribute :>> actionName="reload"; attribute :>> guardName="not(s.running)"; attribute :>> lemmaName="forwardSimulation"; }
part event3:EventBinding { attribute :>> actionName="resume"; attribute :>> guardName="s.loaded==s.epoch"; attribute :>> lemmaName="forwardSimulation"; }
part event4:EventBinding { attribute :>> actionName="returnShot"; attribute :>> guardName="s.running"; attribute :>> lemmaName="forwardSimulation"; }
part event5:EventBinding { attribute :>> actionName="abiEdit"; attribute :>> guardName="true"; attribute :>> lemmaName="forwardSimulation"; }
part event6:EventBinding { attribute :>> actionName="emit"; attribute :>> guardName="true"; attribute :>> lemmaName="forwardSimulation"; }
part event7:EventBinding { attribute :>> actionName="compile"; attribute :>> guardName="s.emitted"; attribute :>> lemmaName="forwardSimulation"; }
part event8:EventBinding { attribute :>> actionName="toolEdit"; attribute :>> guardName="true"; attribute :>> lemmaName="forwardSimulation"; }
part event9:EventBinding { attribute :>> actionName="bind"; attribute :>> guardName="s.native"; attribute :>> lemmaName="forwardSimulation"; }
part event10:EventBinding { attribute :>> actionName="releaseCaptured"; attribute :>> guardName="not(s.running)"; attribute :>> lemmaName="forwardSimulation"; }
}
