package GambitPinRosterDetachment { private import ScalarValues::*;
part def Route { attribute key:String; attribute sourcePath:String; attribute needle:String; attribute obligation:String; }
part route0:Route { attribute :>> key="vm-before-publication"; attribute :>> sourcePath="vendor/gambit/lib/setup.c"; attribute :>> needle="___write_authority_init_vmstate (___vms);"; attribute :>> obligation="Exclusive initialization exists; stable pin directory must be registered before VM publication"; }
part route1:Route { attribute :>> key="scope-contract"; attribute :>> sourcePath="vendor/gambit/lib/write_authority.h"; attribute :>> needle="All APIs require a live VM/storage borrow."; attribute :>> obligation="Existing token cannot extend VM storage lifetime"; }
part route2:Route { attribute :>> key="generation-exhaustion"; attribute :>> sourcePath="vendor/gambit/lib/write_authority.c"; attribute :>> needle="return ___WRITE_AUTHORITY_EXHAUSTED;"; attribute :>> obligation="Reject exhausted generation rather than wrap"; }
part route3:Route { attribute :>> key="last-use-authority"; attribute :>> sourcePath="vendor/gambit/lib/write_authority.c"; attribute :>> needle="Only the producer, AFTER its last actual write/borrow"; attribute :>> obligation="Failed join or catcher observation cannot release a live permit"; }
part route4:Route { attribute :>> key="join-unknown"; attribute :>> sourcePath="vendor/gambit/lib/setup.c"; attribute :>> needle="___thread_join (t); /* ignore error */"; attribute :>> obligation="Existing resize caller does not establish successful stop receipt"; }
part route5:Route { attribute :>> key="rc-storage-cleanup"; attribute :>> sourcePath="vendor/gambit/lib/mem.c"; attribute :>> needle="___HIDDEN void cleanup_rc"; attribute :>> obligation="Processor RC cleanup cannot free transferred pin or Scheme root custody"; }
part route6:Route { attribute :>> key="rc-scan"; attribute :>> sourcePath="vendor/gambit/lib/mem.c"; attribute :>> needle="mark_rc (___PSPNC);"; attribute :>> obligation="Current processor-zero scan is not VM-wide slot registration closure"; }
part route7:Route { attribute :>> key="marker-root-window"; attribute :>> sourcePath="vendor/gambit/lib/c_intf.c"; attribute :>> needle="proc_or_false may have been GC'd"; attribute :>> obligation="Root before fallible marker allocation; native token is not moving GC root"; }
part route8:Route { attribute :>> key="catcher-restore"; attribute :>> sourcePath="vendor/gambit/include/gambit.h.in"; attribute :>> needle="___ps->catcher = ___old_catcher"; attribute :>> obligation="Catcher restoration alone does not sign stable guard completion"; }
part route9:Route { attribute :>> key="tcl-real-alias"; attribute :>> sourcePath="vendor/gambit/examples/tcltk/tcltk.scm"; attribute :>> needle="___EXT(___release_scmobj) (___EXT(___data_rc)"; attribute :>> obligation="Deletion callback releases Scheme payload and RC; in-flight callback closure remains required"; }
part route10:Route { attribute :>> key="finite-environment"; attribute :>> sourcePath="dev/refactoring/modern-c/models/lean/SnapshotObserverRefinement.lean"; attribute :>> needle="theorem environmentExactDomain"; attribute :>> obligation="Reuse exact finite-domain lookup proof; parser and row origin not verified"; }
part route11:Route { attribute :>> key="json-witness"; attribute :>> sourcePath="dev/modeling/tools/typed-binding-witness.py"; attribute :>> needle="refs.append(dict(occurrence=oid,target=target"; attribute :>> obligation="Independently check 91 map rows separately from actual pin action IR"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule1; ref part :>> counterpart=GambitRuntimeComposition::blueprintModule3; attribute :>> key="pin-directory"; attribute :>> owner="native/roots"; attribute :>> actionName="register loadHandle publishPin withdraw"; attribute :>> invariant="Register before visibility; close admission then drain access and scanner leases"; attribute :>> gap="Existing write_authority has no registered GC-root slot roster"; }
part contract1:Contract { ref part :>> accountable=GambitRuntimeComposition::blueprintModule7; ref part :>> counterpart=GambitRuntimeComposition::blueprintModule6; attribute :>> key="exception-custody"; attribute :>> owner="release/foreign"; attribute :>> actionName="requestExit failJoin acceptCustody custodianClear"; attribute :>> invariant="Unknown exit retains stable guard VM borrow and root custody"; attribute :>> gap="Physical stop and no future continuation use require real caller closure"; }
part contract2:Contract { ref part :>> accountable=GambitRuntimeComposition::blueprintModule7; ref part :>> counterpart=GambitRuntimeComposition::blueprintModule0; attribute :>> key="detachment-issuer"; attribute :>> owner="release/semantic"; attribute :>> actionName="endorseSemantic endorseForeign endorseResident issue"; attribute :>> invariant="Coordinator signs only after three owner endorsements and exact generation"; attribute :>> gap="No current Gambit function issues this certificate"; }
part contract3:Contract { ref part :>> accountable=GambitRuntimeComposition::blueprintModule1; ref part :>> counterpart=GambitRuntimeComposition::blueprintModule2; attribute :>> key="generation-identity"; attribute :>> owner="native/execution"; attribute :>> actionName="recycle staleRelease"; attribute :>> invariant="Slot identity includes VM incarnation slot generation and activation; never wrap"; attribute :>> gap="TLS processor ID and marker validity do not prove activation identity"; }
part contract4:Contract { ref part :>> accountable=GambitRuntimeComposition::blueprintModule7; ref part :>> counterpart=GambitRuntimeComposition::blueprintModule8; attribute :>> key="late-observer"; attribute :>> owner="release/build"; attribute :>> actionName="admit revoke finish changeLayout freeCode"; attribute :>> invariant="Revoke new admission; old immutable view stays resident until all readers finish"; attribute :>> gap="Code release and receipt storage retirement are different permissions"; }
part contract5:Contract { ref part :>> accountable=GambitRuntimeComposition::blueprintModule8; ref part :>> counterpart=GambitRuntimeComposition::blueprintModule0; attribute :>> key="json-fidelity"; attribute :>> owner="modeling/build"; attribute :>> actionName="register publishPin withdraw buildEnv"; attribute :>> invariant="Three actual guard/update meanings and exact finite witness domain"; attribute :>> gap="JSON parser emitter field mapping and all-action simulation remain trusted/open"; }
part def Obligation { attribute key:String; attribute status:String; attribute scope:String; attribute counterexample:String; }
part obligation0:Obligation { attribute :>> key="slot-lifecycle"; attribute :>> status="bounded-checked"; attribute :>> scope="One slot two nonwrapping generations one scanner and one activation"; attribute :>> counterexample="Withdraw during access or scan; failed join treated as stop"; }
part obligation1:Obligation { attribute :>> key="detachment"; attribute :>> status="bounded-checked"; attribute :>> scope="One observer two layout generations with explicit endorsements"; attribute :>> counterexample="An old callback or Scheme reference cannot become data-only by declaration"; }
part obligation2:Obligation { attribute :>> key="tag-guards"; attribute :>> status="conditional-proved"; attribute :>> scope="Stale generation access unknown custody and scanner guards"; attribute :>> counterexample="Correct tag does not keep freed VM memory alive"; }
part obligation3:Obligation { attribute :>> key="issuer-guards"; attribute :>> status="conditional-proved"; attribute :>> scope="Missing semantic endorsement unknown result or epoch mismatch rejects certificate"; attribute :>> counterexample="No global source-level closure theorem"; }
part obligation4:Obligation { attribute :>> key="actual-guards"; attribute :>> status="conditional-proved"; attribute :>> scope="Actual register publishPin withdraw guard/update projection"; attribute :>> counterexample="Restricted emitter and JSON parser trusted"; }
part obligation5:Obligation { attribute :>> key="source-c11"; attribute :>> status="open"; attribute :>> scope="Complete callers stop receipts moving roots C11 roster/pin/scan cut"; attribute :>> counterexample="Existing full-barrier write_authority macros are not full hazard-roster proof"; }
part obligation6:Obligation { attribute :>> key="json-domain"; attribute :>> status="partially-proved"; attribute :>> scope="91-row environment with no fabricated finite-domain entries"; attribute :>> counterexample="Forged but consistent input requires independent provenance"; }
part def Gain { attribute key:String; attribute avoided:String; attribute added:String; attribute condition:String; }
part gain0:Gain { attribute :>> key="registered-scans"; attribute :>> avoided="One mandatory VM-wide lock per observer can be avoided"; attribute :>> added="P registered slots need O(P) scan plus pin publish revalidate clear"; attribute :>> condition="Reference SC design; not yet a measured contention improvement"; }
part gain1:Gain { attribute :>> key="data-only-detachment"; attribute :>> avoided="Up to retained old-code bytes C can be released before late terminal readers finish"; attribute :>> added="Copy B terminal bytes plus three endorsements and reader leases"; attribute :>> condition="C exceeds copied B plus directory and resident codec storage; every old alias excluded"; }
part gain2:Gain { attribute :>> key="generation-reuse"; attribute :>> avoided="No unbounded replay journal for eight spent native roles within one generation"; attribute :>> added="One existing word per scope; exhaustion refuses further reuse"; attribute :>> condition="Default 64 slots is admission capacity not lifetime limit; external delivery journal still necessary"; }
part gain3:Gain { attribute :>> key="unknown-custody"; attribute :>> avoided="Avoid unsafe forced clearing and repeated ambiguous cleanup effects"; attribute :>> added="Pinned unknown storage remains R bytes until qualified stop and root closure"; attribute :>> condition="No bounded-memory or eventual-progress claim for permanently stalled actors"; }
part gain4:Gain { attribute :>> key="language-decision"; attribute :>> avoided="No second implementation language required for these mechanisms"; attribute :>> added="Modern C atomics generated descriptors stable guards and semantic proof maintenance"; attribute :>> condition="Zig does not remove registration root closure or detachment endorsement obligations"; }
part def Binding { attribute key:String; attribute qntAction:String; attribute leanLemma:String; attribute refinement:String; attribute guardLemma:String; attribute updateLemma:String; }
part binding0:Binding { attribute :>> key="register"; attribute :>> qntAction="register"; attribute :>> leanLemma="closedBlocksRegister"; attribute :>> refinement="Actual typed IR guard/update certified; source refinement open"; attribute :>> guardLemma="registerGuardMeaning"; attribute :>> updateLemma="registerNextMeaning"; }
part binding1:Binding { attribute :>> key="pin"; attribute :>> qntAction="publishPin"; attribute :>> leanLemma="staleTagNoGrant"; attribute :>> refinement="Actual typed IR guard/update certified; source refinement open"; attribute :>> guardLemma="publishPinGuardMeaning"; attribute :>> updateLemma="publishPinNextMeaning"; }
part binding2:Binding { attribute :>> key="withdraw"; attribute :>> qntAction="withdraw"; attribute :>> leanLemma="scannerBlocksWithdraw"; attribute :>> refinement="Actual typed IR guard/update certified; source refinement open"; attribute :>> guardLemma="withdrawGuardMeaning"; attribute :>> updateLemma="withdrawNextMeaning"; }
part def Flow { attribute fromNode:String; attribute toNode:String; attribute reason:String; }
part flow0:Flow { attribute :>> fromNode="c0"; attribute :>> toNode="o0"; attribute :>> reason="membership lifecycle"; }
part flow1:Flow { attribute :>> fromNode="c0"; attribute :>> toNode="o4"; attribute :>> reason="actual IR projection"; }
part flow2:Flow { attribute :>> fromNode="c1"; attribute :>> toNode="o0"; attribute :>> reason="unknown custody blocks retirement"; }
part flow3:Flow { attribute :>> fromNode="c2"; attribute :>> toNode="o1"; attribute :>> reason="independent endorsements"; }
part flow4:Flow { attribute :>> fromNode="c2"; attribute :>> toNode="o5"; attribute :>> reason="actual issuers not implemented"; }
part flow5:Flow { attribute :>> fromNode="c3"; attribute :>> toNode="o2"; attribute :>> reason="stale tag rejection"; }
part flow6:Flow { attribute :>> fromNode="c3"; attribute :>> toNode="o5"; attribute :>> reason="VM storage borrow required"; }
part flow7:Flow { attribute :>> fromNode="c4"; attribute :>> toNode="o1"; attribute :>> reason="old observers survive revocation"; }
part flow8:Flow { attribute :>> fromNode="c5"; attribute :>> toNode="o6"; attribute :>> reason="finite row domain"; }
part flow9:Flow { attribute :>> fromNode="c4"; attribute :>> toNode="o5"; attribute :>> reason="all aliases before unload"; }
part flow10:Flow { attribute :>> fromNode="c1"; attribute :>> toNode="o3"; attribute :>> reason="completion guards"; }
part flow11:Flow { attribute :>> fromNode="c0"; attribute :>> toNode="o2"; attribute :>> reason="scanner lease blocks withdrawal"; }
part history:GambitAssuranceRouting::ModelNeed { ref part :>> owner=GambitBuildAssurance::planner.component; attribute :>> obligationId="PR-H"; attribute :>> kind="interleaving"; attribute :>> subjectPath="dev/refactoring/modern-c/models/quint/pin_roster_lifecycle.qnt"; attribute :>> subjectScope="Finite pin-slot lifecycle with nonwrapping generation and unknown exit custody"; attribute :>> premise="Bounded models and restricted algebra only; no runtime implementation or native acceptance"; }
part shards:GambitAssuranceRouting::ModelNeed { ref part :>> owner=GambitBuildAssurance::planner.component; attribute :>> obligationId="PR-B"; attribute :>> kind="interleaving"; attribute :>> subjectPath="dev/refactoring/modern-c/models/quint/detachment_certificate.qnt"; attribute :>> subjectScope="Detachment endorsements revocation old observers and immutable layout change"; attribute :>> premise="Bounded models and restricted algebra only; no runtime implementation or native acceptance"; }
part induction:GambitAssuranceRouting::ModelNeed { ref part :>> owner=GambitBuildAssurance::planner.component; attribute :>> obligationId="PR-I"; attribute :>> kind="induction"; attribute :>> subjectPath="dev/refactoring/modern-c/models/lean/PinRosterDetachment.lean"; attribute :>> subjectScope="Stale slot guard withdrawal exclusion certificate rejection finite domain"; attribute :>> premise="Bounded models and restricted algebra only; no runtime implementation or native acceptance"; }
part expression:GambitAssuranceRouting::ModelNeed { ref part :>> owner=GambitBuildAssurance::planner.component; attribute :>> obligationId="PR-X"; attribute :>> kind="induction"; attribute :>> subjectPath="dev/refactoring/modern-c/models/lean/PinRosterAst.lean"; attribute :>> subjectScope="Three actual pin-roster guard/update certificates and 91-row reference witness"; attribute :>> premise="Bounded models and restricted algebra only; no runtime implementation or native acceptance"; }
part source:GambitAssuranceRouting::ModelNeed { ref part :>> owner=GambitBuildAssurance::planner.component; attribute :>> obligationId="PR-S"; attribute :>> kind="source-refinement"; attribute :>> subjectPath="dev/refactoring/modern-c/pin-roster-detachment-design.org"; attribute :>> subjectScope="All slot root FFI exception and stop caller refinement OPEN"; attribute :>> premise="Bounded models and restricted algebra only; no runtime implementation or native acceptance"; }
part platform:GambitAssuranceRouting::ModelNeed { ref part :>> owner=GambitBuildAssurance::planner.component; attribute :>> obligationId="PR-E"; attribute :>> kind="environment-refinement"; attribute :>> subjectPath="dev/refactoring/modern-c/pin-roster-detachment-design.org"; attribute :>> subjectScope="C11 roster admission scan pin ordering and effective configuration OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitSnapshotObserverRefinement::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; }
part endorsement0:Endorsement { attribute :>> roleName="semantic"; attribute :>> scope="No old Scheme root continuation or return alias"; attribute :>> issuer="Scheme frame-root owner"; }
part endorsement1:Endorsement { attribute :>> roleName="foreign"; attribute :>> scope="Native ingress closed and all callbacks and destructor aliases drained"; attribute :>> issuer="FFI resource owner"; }
part endorsement2:Endorsement { attribute :>> roleName="resident"; attribute :>> scope="Terminal immutable payload with resident decoder and error paths"; attribute :>> issuer="Resident query-codec owner"; }
part flow12:Flow { attribute :>> fromNode="c0"; attribute :>> toNode="c3"; attribute :>> reason="Directory publication binds activation identity"; }
part flow13:Flow { attribute :>> fromNode="c3"; attribute :>> toNode="c1"; attribute :>> reason="Tagged guard retains exceptional custody"; }
part flow14:Flow { attribute :>> fromNode="c1"; attribute :>> toNode="c2"; attribute :>> reason="Settled custody precedes semantic detachment"; }
part flow15:Flow { attribute :>> fromNode="c2"; attribute :>> toNode="c4"; attribute :>> reason="Issued certificate controls late admission"; }
}
