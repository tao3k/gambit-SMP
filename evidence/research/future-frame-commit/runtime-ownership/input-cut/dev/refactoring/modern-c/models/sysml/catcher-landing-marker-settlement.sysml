package GambitCatcherLandingMarkerSettlement { private import ScalarValues::*;
part def Owner { attribute componentId:String; }
part controlOwner:Owner { attribute :>> componentId="control"; }
part rootsOwner:Owner { attribute :>> componentId="roots"; }
part codeOwner:Owner { attribute :>> componentId="code"; }
part def LeafRow { attribute key:String; attribute component:String; attribute actionName:String; attribute lemma:String; attribute producerAnchor:String; attribute qualification:String; attribute boundary:String; }
part leaf0:LeafRow { attribute :>> key="leaf-no-abandon"; attribute :>> component="control"; attribute :>> actionName="catcher_landing_marker_settlement.beginInnerRelease"; attribute :>> lemma="CatcherSettlement.innerGapHasCustodian"; attribute :>> producerAnchor="raw-decrement"; attribute :>> qualification="No allocation, callbacks, safepoints or non-local exits through effect and commit"; attribute :>> boundary="Source leaf body alone does not qualify compiler prologue/epilogue instrumentation or asynchronous exits"; }
part leaf1:LeafRow { attribute :>> key="leaf-writers"; attribute :>> component="control"; attribute :>> actionName="catcher_landing_marker_settlement.decrementInner"; attribute :>> lemma="CatcherSettlement.innerExactlyOnce"; attribute :>> producerAnchor="scheme-refcount-writer"; attribute :>> qualification="Exclusive ownership of this marker count and all its aliases"; attribute :>> boundary="Public native and Scheme count writers and frame reflection must be closed, mediated or refused"; }
part leaf2:LeafRow { attribute :>> key="leaf-collector"; attribute :>> component="control"; attribute :>> actionName="catcher_landing_marker_settlement.beginInnerRelease"; attribute :>> lemma="CatcherSettlement.nativeBorrowFresh"; attribute :>> producerAnchor="still-root-selection"; attribute :>> qualification="No collector reads or moving-slot writes overlap the leaf"; attribute :>> boundary="Use a qualified collective/reader-writer protocol; receipt publication alone does not synchronize GC count reads"; }
part leaf3:LeafRow { attribute :>> key="leaf-reply"; attribute :>> component="control"; attribute :>> actionName="catcher_landing_marker_settlement.queryInnerRelease"; attribute :>> lemma="CatcherSettlement.queryInnerDoesNotReplay"; attribute :>> producerAnchor="marker-kill"; attribute :>> qualification="Commit stable release ticket before restoring cancellation or delivering reply"; attribute :>> boundary="Query and new continuation activation cannot replay an already consumed reference"; }
part def SourceRow { attribute key:String; attribute path:String; attribute needle:String; attribute obligation:String; }
part source0:SourceRow { attribute :>> key="return-owner"; attribute :>> path="vendor/gambit/lib/_kernel.scm"; attribute :>> needle="/* not the same processor that created frame */"; attribute :>> obligation="owner-affinity"; }
part source1:SourceRow { attribute :>> key="return-stale"; attribute :>> path="vendor/gambit/lib/_kernel.scm"; attribute :>> needle="/* not first return */"; attribute :>> obligation="one-native-return"; }
part source2:SourceRow { attribute :>> key="return-unwind"; attribute :>> path="vendor/gambit/lib/_kernel.scm"; attribute :>> needle="___throw_error (___PSP ___FIX(___UNWIND_C_STACK));"; attribute :>> obligation="live-catcher"; }
part source3:SourceRow { attribute :>> key="call-frame"; attribute :>> path="vendor/gambit/lib/setup.c"; attribute :>> needle="___fp[-2] = stack_marker;"; attribute :>> obligation="frame-marker-coordinate"; }
part source4:SourceRow { attribute :>> key="call-catcher"; attribute :>> path="vendor/gambit/lib/setup.c"; attribute :>> needle="stack_marker != ___ps->context->fp[___FRAME_SPACE(2)-2]"; attribute :>> obligation="unwind-destination"; }
part source5:SourceRow { attribute :>> key="marker-root"; attribute :>> path="vendor/gambit/lib/c_intf.c"; attribute :>> needle="proc_or_false = *proc_root; /* reload after allocating the marker */"; attribute :>> obligation="root-reload"; }
part source6:SourceRow { attribute :>> key="marker-kill"; attribute :>> path="vendor/gambit/lib/c_intf.c"; attribute :>> needle="___VECTORELEM(marker, 0) = ___FAL; /* invalidate the C stack frame */"; attribute :>> obligation="return-invalidation"; }
part source7:SourceRow { attribute :>> key="legacy-root"; attribute :>> path="vendor/gambit/lib/c_intf.c"; attribute :>> needle="wrapper. Managed startup uses the explicit rooted endpoint above."; attribute :>> obligation="legacy-not-rooted"; }
part source8:SourceRow { attribute :>> key="catcher-local"; attribute :>> path="vendor/gambit/include/_gambit/foreign_conversion.h.in"; attribute :>> needle="___jmpbuf_struct ___jbuf, *___old_catcher = ___ps->catcher;"; attribute :>> obligation="c-stack-dynamic-extent"; }
part source9:SourceRow { attribute :>> key="catcher-restore"; attribute :>> path="vendor/gambit/include/_gambit/foreign_conversion.h.in"; attribute :>> needle="#define ___END_TRY } ___ps->catcher = ___old_catcher; }"; attribute :>> obligation="nested-catcher-restore"; }
part source10:SourceRow { attribute :>> key="continuation-closure"; attribute :>> path="vendor/gambit/lib/_thread.scm"; attribute :>> needle="(##continuation-return-aux cont val1 val2 val3 others)"; attribute :>> obligation="multi-shot-logical-control"; }
part source11:SourceRow { attribute :>> key="wind-user"; attribute :>> path="vendor/gambit/lib/_thread.scm"; attribute :>> needle="((macro-dynwind-after src))"; attribute :>> obligation="reentrant-winding"; }
part source12:SourceRow { attribute :>> key="direct-no-winding"; attribute :>> path="vendor/gambit/lib/_thread.scm"; attribute :>> needle="(define-prim ##continuation-return-no-winding"; attribute :>> obligation="cannot-use-dynamic-wind-only"; }
part source13:SourceRow { attribute :>> key="saved-roots"; attribute :>> path="vendor/gambit/lib/_mem/root-origins.inc"; attribute :>> needle="mark_array (work, context->saved, sizeof(context->saved)/sizeof(*context->saved));"; attribute :>> obligation="saved-registers"; }
part source14:SourceRow { attribute :>> key="entry-root"; attribute :>> path="vendor/gambit/lib/_mem/root-origins.inc"; attribute :>> needle="mark_array (work, &context->entry_marker, 1);"; attribute :>> obligation="context-marker-root"; }
part source15:SourceRow { attribute :>> key="rc-root"; attribute :>> path="vendor/gambit/lib/_mem/rc-roots.inc"; attribute :>> needle="context->mem.rc_head_.next"; attribute :>> obligation="context-owned-rc"; }
part source16:SourceRow { attribute :>> key="tcl-reentry"; attribute :>> path="vendor/gambit/examples/tcltk/tcltk.scm"; attribute :>> needle="___EXT(___data_rc) (___CAST(void*,client_data))"; attribute :>> obligation="raw-before-guard"; }
part source17:SourceRow { attribute :>> key="tls-status"; attribute :>> path="vendor/gambit/lib/os_thread.c"; attribute :>> needle="pthread_setspecific (___thread_mod.tls_ptr_key, ptr); /* ignore error */"; attribute :>> obligation="checked-binding-required"; }
part source18:SourceRow { attribute :>> key="thread-id"; attribute :>> path="vendor/gambit/lib/os_thread.c"; attribute :>> needle="thread->thread_id = pthread_self ();"; attribute :>> obligation="native-thread-identity"; }
part source19:SourceRow { attribute :>> key="paper-fulltext"; attribute :>> path="evidence/research/guard-thread-admission/feeley-sfp-paper.txt"; attribute :>> needle="We have not yet implemented this approa h in Gambit-C."; attribute :>> obligation="historical-proposal-not-current"; }
part source20:SourceRow { attribute :>> key="sfun-empty-body"; attribute :>> path="vendor/gambit/include/_gambit/foreign_conversion.h.in"; attribute :>> needle="#define ___BEGIN_SFUN_BODY"; attribute :>> obligation="SFUN wrapper is not itself a catcher"; }
part source21:SourceRow { attribute :>> key="sfun-cleanup-after-call"; attribute :>> path="vendor/gambit/include/_gambit/foreign_conversion.h.in"; attribute :>> needle="#define ___END_SFUN } ___EXT(___kill_sfun_stack_marker) (___marker);"; attribute :>> obligation="sequential cleanup is not total under outer unwind"; }
part source22:SourceRow { attribute :>> key="sfun-generator"; attribute :>> path="vendor/gambit/gsc/_ptree2.scm"; attribute :>> needle="c-id-prefix \"BEGIN_SFUN_BODY\" nl-str"; attribute :>> obligation="actual generated SFUN body"; }
part source23:SourceRow { attribute :>> key="cfun-conditional-catcher"; attribute :>> path="vendor/gambit/gsc/_ptree2.scm"; attribute :>> needle="(if cleanup? \"BEGIN_CFUN_BODY_CLEANUP\" \"BEGIN_CFUN_BODY\")"; attribute :>> obligation="foreign catchers depend on conversion cleanup"; }
part source24:SourceRow { attribute :>> key="cfun-catcher-macro"; attribute :>> path="vendor/gambit/include/_gambit/foreign_conversion.h.in"; attribute :>> needle="#define ___BEGIN_CFUN_BODY_CLEANUP ___W_ALL_INL ___BEGIN_TRY"; attribute :>> obligation="intermediate catcher may intercept and propagate"; }
part source25:SourceRow { attribute :>> key="error-propagation"; attribute :>> path="vendor/gambit/lib/setup.c"; attribute :>> needle="___THROW (err);"; attribute :>> obligation="throw uses current catcher"; }
part source26:SourceRow { attribute :>> key="captured-frame-decode"; attribute :>> path="vendor/gambit/lib/_mem/object-scanning.inc"; attribute :>> needle="___decode_frame_descriptor (___LABEL_DESCR_GET(actual_ra), 1)"; attribute :>> obligation="captured RETI still consumes descriptor after native exit"; }
part source27:SourceRow { attribute :>> key="context-frame-decode"; attribute :>> path="vendor/gambit/lib/_mem/continuation-roots.inc"; attribute :>> needle="acquire_frame_access(work);"; attribute :>> obligation="maintenance scanner has separate descriptor lifetime"; }
part source28:SourceRow { attribute :>> key="captured-frame-copy"; attribute :>> path="vendor/gambit/lib/_mem/continuation-roots.inc"; attribute :>> needle="___RETI_GET_FS_LINK(actual_ra,fs,link)"; attribute :>> obligation="stack to heap copy reads label metadata"; }
part source29:SourceRow { attribute :>> key="native-unload"; attribute :>> path="vendor/gambit/lib/os_dyn.c"; attribute :>> needle="dlclose (p->descr);"; attribute :>> obligation="global loader cleanup is not per-domain retirement"; }
part source30:SourceRow { attribute :>> key="run-landing"; attribute :>> path="vendor/gambit/lib/setup.c"; attribute :>> needle="___VOLATILE ___SCMOBJ marker = ___FAL;"; attribute :>> obligation="run has an enclosing catcher and post-catch cleanup"; }
part source31:SourceRow { attribute :>> key="tcl-source-delete"; attribute :>> path="vendor/gambit/examples/tcltk/tcltk.scm"; attribute :>> needle="___EXT(___release_rc) (___CAST(void*,client_data));"; attribute :>> obligation="close source admission before native storage release"; }
part source32:SourceRow { attribute :>> key="target-invocation-return"; attribute :>> path="vendor/gambit/lib/setup.c"; attribute :>> needle="___ps->context->fp += ___FRAME_SPACE(2);"; attribute :>> obligation="landing precedes target ___call return; caller-side exit receipt is separate"; }
part source33:SourceRow { attribute :>> key="still-body-accounting"; attribute :>> path="vendor/gambit/lib/_mem/configuration.inc"; attribute :>> needle="#define ___STILL_BODY (5+1)"; attribute :>> obligation="current local still object header cost; not allocator overhead"; }
part source34:SourceRow { attribute :>> key="copy-payload-before-publish"; attribute :>> path="vendor/gambit/lib/_mem/copy-reservations.inc"; attribute :>> needle="*alloc++ = *body++;"; attribute :>> obligation="root forwarding can be visible before payload initialization finishes"; }
part source35:SourceRow { attribute :>> key="raw-decrement"; attribute :>> path="vendor/gambit/lib/_mem/still-refcount.inc"; attribute :>> needle="___BODY0(obj)[___STILL_REFCOUNT-___STILL_BODY]--;"; attribute :>> obligation="count update is not idempotent or a receipt transaction"; }
part source36:SourceRow { attribute :>> key="raw-increment"; attribute :>> path="vendor/gambit/lib/_mem/still-refcount.inc"; attribute :>> needle="___BODY0(obj)[___STILL_REFCOUNT-___STILL_BODY]++;"; attribute :>> obligation="all competing writers must be excluded or migrated"; }
part source37:SourceRow { attribute :>> key="scheme-refcount-writer"; attribute :>> path="vendor/gambit/lib/_kernel.scm"; attribute :>> needle="(define-prim (##still-obj-refcount-dec! obj)"; attribute :>> obligation="managed marker aliases can reach a Scheme-level refcount writer"; }
part source38:SourceRow { attribute :>> key="initial-still-count"; attribute :>> path="vendor/gambit/lib/_mem/object-allocation.inc"; attribute :>> needle="base[___STILL_REFCOUNT] = 1;"; attribute :>> obligation="one native ownership reference at still allocation"; }
part source39:SourceRow { attribute :>> key="vector-constructor"; attribute :>> path="vendor/gambit/lib/_mem/object-allocation.inc"; attribute :>> needle="___WORD obj = ___alloc_scmobj (___ps, ___sVECTOR, length<<___LWS);"; attribute :>> obligation="one logical still vector constructor for each current marker"; }
part source40:SourceRow { attribute :>> key="still-root-selection"; attribute :>> path="vendor/gambit/lib/_mem/object-scanning.inc"; attribute :>> needle="if (base[___STILL_REFCOUNT] == 0)"; attribute :>> obligation="GC observes count and must synchronize with a qualified release leaf"; }
part source41:SourceRow { attribute :>> key="gc-slot-winner"; attribute :>> path="vendor/gambit/lib/_mem/copy-reservations.inc"; attribute :>> needle="*cell = ___TAG(alloc - ___REFERENCE_TO_BODY, ___TYP(obj));"; attribute :>> obligation="collector updates the actual supplied root cell"; }
part source42:SourceRow { attribute :>> key="gc-slot-forwarded"; attribute :>> path="vendor/gambit/lib/_mem/copy-reservations.inc"; attribute :>> needle="*cell = ___TAG(___UNTAG_AS(head_now, ___FORW), ___TYP(obj));"; attribute :>> obligation="loser reloads canonical forwarding result into root cell"; }
part source43:SourceRow { attribute :>> key="native-frame-reflection"; attribute :>> path="vendor/gambit/lib/_kernel.scm"; attribute :>> needle="(define-prim (##frame-ref frame i)"; attribute :>> obligation="opaque native-token ABI needs reflection semantics and alias policy"; }
part source44:SourceRow { attribute :>> key="frame-serialization"; attribute :>> path="vendor/gambit/lib/_system.scm"; attribute :>> needle="(serialize! (frame-ref obj i))"; attribute :>> obligation="persistent continuations must not reconstruct a live native catcher from stale tokens"; }
part source45:SourceRow { attribute :>> key="scheme-vector-allocator"; attribute :>> path="vendor/gambit/lib/_kernel.scm"; attribute :>> needle="___ALLOC_SCMOBJ_INLINE(VECTOR, ___WORD, n, 0);"; attribute :>> obligation="Scheme allocator is not a drop-in C API for callback bootstrap"; }
part def IssuerRow { attribute key:String; attribute proposedIssuer:String; attribute actualSource:String; attribute status:String; attribute responsibility:String; }
part issuer0:IssuerRow { attribute :>> key="prepare"; attribute :>> proposedIssuer="StableSubtreeCoordinator"; attribute :>> actualSource="setup.c run and preexisting source-owned RootBundle"; attribute :>> status="required adapter; not a qualified native signer"; attribute :>> responsibility="record every private candidate before interruptible work; partial/unknown failure retains original roots and native references"; }
part issuer1:IssuerRow { attribute :>> key="landing"; attribute :>> proposedIssuer="GeneratedCatcherLandingAdapter"; attribute :>> actualSource="foreign_conversion END_TRY plus setup.c ___call destination check"; attribute :>> status="required adapter; not a qualified native signer"; attribute :>> responsibility="sign after exact frame, error kind, marker/context and thread/operation checks; restored current catcher is not caught frame identity"; }
part issuer2:IssuerRow { attribute :>> key="target-return"; attribute :>> proposedIssuer="NativeInvocationExitAdapter"; attribute :>> actualSource="setup.c ___call return to ___run"; attribute :>> status="required adapter; not a qualified native signer"; attribute :>> responsibility="target catcher arrival precedes invocation exit; outer release also requires owner-use closure; SFUN retries are outside the bounded ___run profile"; }
part issuer3:IssuerRow { attribute :>> key="marker-release"; attribute :>> proposedIssuer="ManagedMarkerOwner"; attribute :>> actualSource="kill_sfun_stack_marker and still-refcount plain decrement"; attribute :>> status="required adapter; NoAbandon and writer exclusion remain open"; attribute :>> responsibility="one reference release per marker; keep exclusive GC/writer/cancellation custody through effect and receipt commit before reply"; }
part issuer4:IssuerRow { attribute :>> key="root-slot"; attribute :>> proposedIssuer="RootRegistryScannerAdapter"; attribute :>> actualSource="mark_array actual *cell stores and execution-context roots"; attribute :>> status="required adapter; no full native slot map"; attribute :>> responsibility="enumerate/update registry and live context cells; keep mutators parked through partial updates, then require fresh reload"; }
part issuer5:IssuerRow { attribute :>> key="code-retire"; attribute :>> proposedIssuer="ImageLeaseCoordinator"; attribute :>> actualSource="captured-frame descriptor loads and global dlclose"; attribute :>> status="required adapter; no global native signer"; attribute :>> responsibility="drain captured frames, admitted readers and native frames before image release; a marker count of zero is insufficient"; }
part issuer6:IssuerRow { attribute :>> key="token-profile"; attribute :>> proposedIssuer="NativeEntrySpec and FrameSpec generator"; attribute :>> actualSource="SFUN marker constructor, frame-ref and frame serialization"; attribute :>> status="research alternative; unqualified"; attribute :>> responsibility="opaque return-token profile must preserve Scheme control and account for reflection, raw aliases, serialization and ABI invalidation"; }
part def NeedRow { attribute key:String; attribute kind:String; attribute path:String; attribute scope:String; ref owner:Owner; }
part need0:NeedRow { attribute :>> key="Catcher-formal"; attribute :>> kind="formal"; attribute :>> path="dev/refactoring/modern-c/models/quint/catcher_landing_marker_settlement.qnt"; attribute :>> scope="bounded-catcher-marker-slot-protocol"; ref :>> owner = controlOwner; }
part need1:NeedRow { attribute :>> key="Catcher-bridge"; attribute :>> kind="bridge"; attribute :>> path="dev/refactoring/modern-c/models/lean/CatcherSettlement.lean"; attribute :>> scope="typed-ir-lean-physical-gap-model"; ref :>> owner = controlOwner; }
part need2:NeedRow { attribute :>> key="Catcher-prepare"; attribute :>> kind="native"; attribute :>> path="vendor/gambit/lib/setup.c"; attribute :>> scope="stable-private-preparation-and-partial-failure-custody"; ref :>> owner = controlOwner; }
part need3:NeedRow { attribute :>> key="Catcher-landing"; attribute :>> kind="native"; attribute :>> path="vendor/gambit/include/_gambit/foreign_conversion.h.in"; attribute :>> scope="target-frame-error-class-and-incarnation-receipt"; ref :>> owner = controlOwner; }
part need4:NeedRow { attribute :>> key="Catcher-marker-release"; attribute :>> kind="native"; attribute :>> path="vendor/gambit/lib/_mem/still-refcount.inc"; attribute :>> scope="no-abandon-single-writer-GC-excluded-count-release"; ref :>> owner = controlOwner; }
part need5:NeedRow { attribute :>> key="Catcher-root-slots"; attribute :>> kind="native"; attribute :>> path="vendor/gambit/lib/_mem/copy-reservations.inc"; attribute :>> scope="VM-slot-and-resumed-context-update-freeze"; ref :>> owner = rootsOwner; }
part need6:NeedRow { attribute :>> key="Catcher-descriptors"; attribute :>> kind="native"; attribute :>> path="vendor/gambit/lib/os_dyn.c"; attribute :>> scope="capture-reader-native-global-image-closure"; ref :>> owner = codeOwner; }
part need7:NeedRow { attribute :>> key="Catcher-entry-abi"; attribute :>> kind="native"; attribute :>> path="vendor/gambit/gsc/_ptree2.scm"; attribute :>> scope="all-entry-and-reflection-alias-qualification"; ref :>> owner = controlOwner; }
part def BindingRow { attribute actionName:String; attribute lemma:String; }
part binding0:BindingRow { attribute :>> actionName="catcher_landing_marker_settlement.prepareFirst"; attribute :>> lemma="CatcherSettlement.prepareFirstPreserves"; }
part binding1:BindingRow { attribute :>> actionName="catcher_landing_marker_settlement.prepareSecond"; attribute :>> lemma="CatcherSettlement.prepareSecondPreserves"; }
part binding2:BindingRow { attribute :>> actionName="catcher_landing_marker_settlement.rollbackPartial"; attribute :>> lemma="CatcherSettlement.rollbackPartialPreserves"; }
part binding3:BindingRow { attribute :>> actionName="catcher_landing_marker_settlement.rollbackReady"; attribute :>> lemma="CatcherSettlement.rollbackReadyPreserves"; }
part binding4:BindingRow { attribute :>> actionName="catcher_landing_marker_settlement.preparationUnknown"; attribute :>> lemma="CatcherSettlement.preparationUnknownPreserves"; }
part binding5:BindingRow { attribute :>> actionName="catcher_landing_marker_settlement.auditPreparation"; attribute :>> lemma="CatcherSettlement.auditPreparationPreserves"; }
part binding6:BindingRow { attribute :>> actionName="catcher_landing_marker_settlement.publishEscrow"; attribute :>> lemma="CatcherSettlement.publishEscrowPreserves"; }
part binding7:BindingRow { attribute :>> actionName="catcher_landing_marker_settlement.escrowReplyLost"; attribute :>> lemma="CatcherSettlement.escrowReplyLostPreserves"; }
part binding8:BindingRow { attribute :>> actionName="catcher_landing_marker_settlement.queryEscrow"; attribute :>> lemma="CatcherSettlement.queryEscrowPreserves"; }
part binding9:BindingRow { attribute :>> actionName="catcher_landing_marker_settlement.issueTransfer"; attribute :>> lemma="CatcherSettlement.issueTransferPreserves"; }
part binding10:BindingRow { attribute :>> actionName="catcher_landing_marker_settlement.issueOtherError"; attribute :>> lemma="CatcherSettlement.issueOtherErrorPreserves"; }
part binding11:BindingRow { attribute :>> actionName="catcher_landing_marker_settlement.catchInner"; attribute :>> lemma="CatcherSettlement.catchInnerPreserves"; }
part binding12:BindingRow { attribute :>> actionName="catcher_landing_marker_settlement.restoreInnerCatcher"; attribute :>> lemma="CatcherSettlement.restoreInnerCatcherPreserves"; }
part binding13:BindingRow { attribute :>> actionName="catcher_landing_marker_settlement.catchOuter"; attribute :>> lemma="CatcherSettlement.catchOuterPreserves"; }
part binding14:BindingRow { attribute :>> actionName="catcher_landing_marker_settlement.restoreOuterCatcher"; attribute :>> lemma="CatcherSettlement.restoreOuterCatcherPreserves"; }
part binding15:BindingRow { attribute :>> actionName="catcher_landing_marker_settlement.borrowFresh"; attribute :>> lemma="CatcherSettlement.borrowFreshPreserves"; }
part binding16:BindingRow { attribute :>> actionName="catcher_landing_marker_settlement.releaseBorrow"; attribute :>> lemma="CatcherSettlement.releaseBorrowPreserves"; }
part binding17:BindingRow { attribute :>> actionName="catcher_landing_marker_settlement.validateLanding"; attribute :>> lemma="CatcherSettlement.validateLandingPreserves"; }
part binding18:BindingRow { attribute :>> actionName="catcher_landing_marker_settlement.publishLanding"; attribute :>> lemma="CatcherSettlement.publishLandingPreserves"; }
part binding19:BindingRow { attribute :>> actionName="catcher_landing_marker_settlement.landingReplyLost"; attribute :>> lemma="CatcherSettlement.landingReplyLostPreserves"; }
part binding20:BindingRow { attribute :>> actionName="catcher_landing_marker_settlement.queryLanding"; attribute :>> lemma="CatcherSettlement.queryLandingPreserves"; }
part binding21:BindingRow { attribute :>> actionName="catcher_landing_marker_settlement.beginInnerRelease"; attribute :>> lemma="CatcherSettlement.beginInnerReleasePreserves"; }
part binding22:BindingRow { attribute :>> actionName="catcher_landing_marker_settlement.decrementInner"; attribute :>> lemma="CatcherSettlement.decrementInnerPreserves"; }
part binding23:BindingRow { attribute :>> actionName="catcher_landing_marker_settlement.commitInnerRelease"; attribute :>> lemma="CatcherSettlement.commitInnerReleasePreserves"; }
part binding24:BindingRow { attribute :>> actionName="catcher_landing_marker_settlement.innerReplyLost"; attribute :>> lemma="CatcherSettlement.innerReplyLostPreserves"; }
part binding25:BindingRow { attribute :>> actionName="catcher_landing_marker_settlement.queryInnerRelease"; attribute :>> lemma="CatcherSettlement.queryInnerReleasePreserves"; }
part binding26:BindingRow { attribute :>> actionName="catcher_landing_marker_settlement.nativeTargetReturned"; attribute :>> lemma="CatcherSettlement.nativeTargetReturnedPreserves"; }
part binding27:BindingRow { attribute :>> actionName="catcher_landing_marker_settlement.beginOuterRelease"; attribute :>> lemma="CatcherSettlement.beginOuterReleasePreserves"; }
part binding28:BindingRow { attribute :>> actionName="catcher_landing_marker_settlement.decrementOuter"; attribute :>> lemma="CatcherSettlement.decrementOuterPreserves"; }
part binding29:BindingRow { attribute :>> actionName="catcher_landing_marker_settlement.commitOuterRelease"; attribute :>> lemma="CatcherSettlement.commitOuterReleasePreserves"; }
part binding30:BindingRow { attribute :>> actionName="catcher_landing_marker_settlement.outerReplyLost"; attribute :>> lemma="CatcherSettlement.outerReplyLostPreserves"; }
part binding31:BindingRow { attribute :>> actionName="catcher_landing_marker_settlement.queryOuterRelease"; attribute :>> lemma="CatcherSettlement.queryOuterReleasePreserves"; }
part binding32:BindingRow { attribute :>> actionName="catcher_landing_marker_settlement.settleGuards"; attribute :>> lemma="CatcherSettlement.settleGuardsPreserves"; }
part binding33:BindingRow { attribute :>> actionName="catcher_landing_marker_settlement.resumeCaptured"; attribute :>> lemma="CatcherSettlement.resumeCapturedPreserves"; }
part binding34:BindingRow { attribute :>> actionName="catcher_landing_marker_settlement.finishResumption"; attribute :>> lemma="CatcherSettlement.finishResumptionPreserves"; }
part binding35:BindingRow { attribute :>> actionName="catcher_landing_marker_settlement.dropCaptured"; attribute :>> lemma="CatcherSettlement.dropCapturedPreserves"; }
part binding36:BindingRow { attribute :>> actionName="catcher_landing_marker_settlement.startGc"; attribute :>> lemma="CatcherSettlement.startGcPreserves"; }
part binding37:BindingRow { attribute :>> actionName="catcher_landing_marker_settlement.rewriteRootOnly"; attribute :>> lemma="CatcherSettlement.rewriteRootOnlyPreserves"; }
part binding38:BindingRow { attribute :>> actionName="catcher_landing_marker_settlement.rewriteRegistryFirst"; attribute :>> lemma="CatcherSettlement.rewriteRegistryFirstPreserves"; }
part binding39:BindingRow { attribute :>> actionName="catcher_landing_marker_settlement.rewriteContextSlot"; attribute :>> lemma="CatcherSettlement.rewriteContextSlotPreserves"; }
part binding40:BindingRow { attribute :>> actionName="catcher_landing_marker_settlement.initializeCopiedObject"; attribute :>> lemma="CatcherSettlement.initializeCopiedObjectPreserves"; }
part binding41:BindingRow { attribute :>> actionName="catcher_landing_marker_settlement.finishGc"; attribute :>> lemma="CatcherSettlement.finishGcPreserves"; }
part binding42:BindingRow { attribute :>> actionName="catcher_landing_marker_settlement.closeRootAdmission"; attribute :>> lemma="CatcherSettlement.closeRootAdmissionPreserves"; }
part binding43:BindingRow { attribute :>> actionName="catcher_landing_marker_settlement.retireRoots"; attribute :>> lemma="CatcherSettlement.retireRootsPreserves"; }
part binding44:BindingRow { attribute :>> actionName="catcher_landing_marker_settlement.ackDescriptorGrace"; attribute :>> lemma="CatcherSettlement.ackDescriptorGracePreserves"; }
part binding45:BindingRow { attribute :>> actionName="catcher_landing_marker_settlement.retireDescriptor"; attribute :>> lemma="CatcherSettlement.retireDescriptorPreserves"; }
part def RouteRow { attribute component:String; attribute actionName:String; attribute lemma:String; attribute producerAnchor:String; attribute obligationId:String; }
part route0:RouteRow { attribute :>> component="control"; attribute :>> actionName="catcher_landing_marker_settlement.prepareFirst"; attribute :>> lemma="CatcherSettlement.prepareFirstPreserves"; attribute :>> producerAnchor="run-landing"; attribute :>> obligationId="Catcher-prepare"; }
part route1:RouteRow { attribute :>> component="control"; attribute :>> actionName="catcher_landing_marker_settlement.prepareSecond"; attribute :>> lemma="CatcherSettlement.prepareSecondPreserves"; attribute :>> producerAnchor="run-landing"; attribute :>> obligationId="Catcher-prepare"; }
part route2:RouteRow { attribute :>> component="control"; attribute :>> actionName="catcher_landing_marker_settlement.rollbackPartial"; attribute :>> lemma="CatcherSettlement.rollbackPartialPreserves"; attribute :>> producerAnchor="run-landing"; attribute :>> obligationId="Catcher-prepare"; }
part route3:RouteRow { attribute :>> component="control"; attribute :>> actionName="catcher_landing_marker_settlement.rollbackReady"; attribute :>> lemma="CatcherSettlement.rollbackReadyPreserves"; attribute :>> producerAnchor="run-landing"; attribute :>> obligationId="Catcher-prepare"; }
part route4:RouteRow { attribute :>> component="control"; attribute :>> actionName="catcher_landing_marker_settlement.preparationUnknown"; attribute :>> lemma="CatcherSettlement.preparationUnknownPreserves"; attribute :>> producerAnchor="run-landing"; attribute :>> obligationId="Catcher-prepare"; }
part route5:RouteRow { attribute :>> component="control"; attribute :>> actionName="catcher_landing_marker_settlement.auditPreparation"; attribute :>> lemma="CatcherSettlement.auditPreparationPreserves"; attribute :>> producerAnchor="run-landing"; attribute :>> obligationId="Catcher-prepare"; }
part route6:RouteRow { attribute :>> component="control"; attribute :>> actionName="catcher_landing_marker_settlement.publishEscrow"; attribute :>> lemma="CatcherSettlement.publishEscrowPreserves"; attribute :>> producerAnchor="run-landing"; attribute :>> obligationId="Catcher-prepare"; }
part route7:RouteRow { attribute :>> component="control"; attribute :>> actionName="catcher_landing_marker_settlement.escrowReplyLost"; attribute :>> lemma="CatcherSettlement.escrowReplyLostPreserves"; attribute :>> producerAnchor="run-landing"; attribute :>> obligationId="Catcher-prepare"; }
part route8:RouteRow { attribute :>> component="control"; attribute :>> actionName="catcher_landing_marker_settlement.queryEscrow"; attribute :>> lemma="CatcherSettlement.queryEscrowPreserves"; attribute :>> producerAnchor="run-landing"; attribute :>> obligationId="Catcher-prepare"; }
part route9:RouteRow { attribute :>> component="control"; attribute :>> actionName="catcher_landing_marker_settlement.issueTransfer"; attribute :>> lemma="CatcherSettlement.issueTransferPreserves"; attribute :>> producerAnchor="call-catcher"; attribute :>> obligationId="Catcher-landing"; }
part route10:RouteRow { attribute :>> component="control"; attribute :>> actionName="catcher_landing_marker_settlement.issueOtherError"; attribute :>> lemma="CatcherSettlement.issueOtherErrorPreserves"; attribute :>> producerAnchor="call-catcher"; attribute :>> obligationId="Catcher-landing"; }
part route11:RouteRow { attribute :>> component="control"; attribute :>> actionName="catcher_landing_marker_settlement.catchInner"; attribute :>> lemma="CatcherSettlement.catchInnerPreserves"; attribute :>> producerAnchor="call-catcher"; attribute :>> obligationId="Catcher-landing"; }
part route12:RouteRow { attribute :>> component="control"; attribute :>> actionName="catcher_landing_marker_settlement.restoreInnerCatcher"; attribute :>> lemma="CatcherSettlement.restoreInnerCatcherPreserves"; attribute :>> producerAnchor="call-catcher"; attribute :>> obligationId="Catcher-landing"; }
part route13:RouteRow { attribute :>> component="control"; attribute :>> actionName="catcher_landing_marker_settlement.catchOuter"; attribute :>> lemma="CatcherSettlement.catchOuterPreserves"; attribute :>> producerAnchor="call-catcher"; attribute :>> obligationId="Catcher-landing"; }
part route14:RouteRow { attribute :>> component="control"; attribute :>> actionName="catcher_landing_marker_settlement.restoreOuterCatcher"; attribute :>> lemma="CatcherSettlement.restoreOuterCatcherPreserves"; attribute :>> producerAnchor="call-catcher"; attribute :>> obligationId="Catcher-landing"; }
part route15:RouteRow { attribute :>> component="roots"; attribute :>> actionName="catcher_landing_marker_settlement.borrowFresh"; attribute :>> lemma="CatcherSettlement.borrowFreshPreserves"; attribute :>> producerAnchor="gc-slot-winner"; attribute :>> obligationId="Catcher-root-slots"; }
part route16:RouteRow { attribute :>> component="roots"; attribute :>> actionName="catcher_landing_marker_settlement.releaseBorrow"; attribute :>> lemma="CatcherSettlement.releaseBorrowPreserves"; attribute :>> producerAnchor="gc-slot-winner"; attribute :>> obligationId="Catcher-root-slots"; }
part route17:RouteRow { attribute :>> component="control"; attribute :>> actionName="catcher_landing_marker_settlement.validateLanding"; attribute :>> lemma="CatcherSettlement.validateLandingPreserves"; attribute :>> producerAnchor="call-catcher"; attribute :>> obligationId="Catcher-landing"; }
part route18:RouteRow { attribute :>> component="control"; attribute :>> actionName="catcher_landing_marker_settlement.publishLanding"; attribute :>> lemma="CatcherSettlement.publishLandingPreserves"; attribute :>> producerAnchor="call-catcher"; attribute :>> obligationId="Catcher-landing"; }
part route19:RouteRow { attribute :>> component="control"; attribute :>> actionName="catcher_landing_marker_settlement.landingReplyLost"; attribute :>> lemma="CatcherSettlement.landingReplyLostPreserves"; attribute :>> producerAnchor="call-catcher"; attribute :>> obligationId="Catcher-landing"; }
part route20:RouteRow { attribute :>> component="control"; attribute :>> actionName="catcher_landing_marker_settlement.queryLanding"; attribute :>> lemma="CatcherSettlement.queryLandingPreserves"; attribute :>> producerAnchor="call-catcher"; attribute :>> obligationId="Catcher-landing"; }
part route21:RouteRow { attribute :>> component="control"; attribute :>> actionName="catcher_landing_marker_settlement.beginInnerRelease"; attribute :>> lemma="CatcherSettlement.beginInnerReleasePreserves"; attribute :>> producerAnchor="raw-decrement"; attribute :>> obligationId="Catcher-marker-release"; }
part route22:RouteRow { attribute :>> component="control"; attribute :>> actionName="catcher_landing_marker_settlement.decrementInner"; attribute :>> lemma="CatcherSettlement.decrementInnerPreserves"; attribute :>> producerAnchor="raw-decrement"; attribute :>> obligationId="Catcher-marker-release"; }
part route23:RouteRow { attribute :>> component="control"; attribute :>> actionName="catcher_landing_marker_settlement.commitInnerRelease"; attribute :>> lemma="CatcherSettlement.commitInnerReleasePreserves"; attribute :>> producerAnchor="raw-decrement"; attribute :>> obligationId="Catcher-marker-release"; }
part route24:RouteRow { attribute :>> component="control"; attribute :>> actionName="catcher_landing_marker_settlement.innerReplyLost"; attribute :>> lemma="CatcherSettlement.innerReplyLostPreserves"; attribute :>> producerAnchor="raw-decrement"; attribute :>> obligationId="Catcher-marker-release"; }
part route25:RouteRow { attribute :>> component="control"; attribute :>> actionName="catcher_landing_marker_settlement.queryInnerRelease"; attribute :>> lemma="CatcherSettlement.queryInnerReleasePreserves"; attribute :>> producerAnchor="raw-decrement"; attribute :>> obligationId="Catcher-marker-release"; }
part route26:RouteRow { attribute :>> component="control"; attribute :>> actionName="catcher_landing_marker_settlement.nativeTargetReturned"; attribute :>> lemma="CatcherSettlement.nativeTargetReturnedPreserves"; attribute :>> producerAnchor="target-invocation-return"; attribute :>> obligationId="Catcher-landing"; }
part route27:RouteRow { attribute :>> component="control"; attribute :>> actionName="catcher_landing_marker_settlement.beginOuterRelease"; attribute :>> lemma="CatcherSettlement.beginOuterReleasePreserves"; attribute :>> producerAnchor="raw-decrement"; attribute :>> obligationId="Catcher-marker-release"; }
part route28:RouteRow { attribute :>> component="control"; attribute :>> actionName="catcher_landing_marker_settlement.decrementOuter"; attribute :>> lemma="CatcherSettlement.decrementOuterPreserves"; attribute :>> producerAnchor="raw-decrement"; attribute :>> obligationId="Catcher-marker-release"; }
part route29:RouteRow { attribute :>> component="control"; attribute :>> actionName="catcher_landing_marker_settlement.commitOuterRelease"; attribute :>> lemma="CatcherSettlement.commitOuterReleasePreserves"; attribute :>> producerAnchor="raw-decrement"; attribute :>> obligationId="Catcher-marker-release"; }
part route30:RouteRow { attribute :>> component="control"; attribute :>> actionName="catcher_landing_marker_settlement.outerReplyLost"; attribute :>> lemma="CatcherSettlement.outerReplyLostPreserves"; attribute :>> producerAnchor="raw-decrement"; attribute :>> obligationId="Catcher-marker-release"; }
part route31:RouteRow { attribute :>> component="control"; attribute :>> actionName="catcher_landing_marker_settlement.queryOuterRelease"; attribute :>> lemma="CatcherSettlement.queryOuterReleasePreserves"; attribute :>> producerAnchor="raw-decrement"; attribute :>> obligationId="Catcher-marker-release"; }
part route32:RouteRow { attribute :>> component="control"; attribute :>> actionName="catcher_landing_marker_settlement.settleGuards"; attribute :>> lemma="CatcherSettlement.settleGuardsPreserves"; attribute :>> producerAnchor="raw-decrement"; attribute :>> obligationId="Catcher-marker-release"; }
part route33:RouteRow { attribute :>> component="control"; attribute :>> actionName="catcher_landing_marker_settlement.resumeCaptured"; attribute :>> lemma="CatcherSettlement.resumeCapturedPreserves"; attribute :>> producerAnchor="native-frame-reflection"; attribute :>> obligationId="Catcher-entry-abi"; }
part route34:RouteRow { attribute :>> component="control"; attribute :>> actionName="catcher_landing_marker_settlement.finishResumption"; attribute :>> lemma="CatcherSettlement.finishResumptionPreserves"; attribute :>> producerAnchor="native-frame-reflection"; attribute :>> obligationId="Catcher-entry-abi"; }
part route35:RouteRow { attribute :>> component="code"; attribute :>> actionName="catcher_landing_marker_settlement.dropCaptured"; attribute :>> lemma="CatcherSettlement.dropCapturedPreserves"; attribute :>> producerAnchor="captured-frame-decode"; attribute :>> obligationId="Catcher-descriptors"; }
part route36:RouteRow { attribute :>> component="roots"; attribute :>> actionName="catcher_landing_marker_settlement.startGc"; attribute :>> lemma="CatcherSettlement.startGcPreserves"; attribute :>> producerAnchor="gc-slot-winner"; attribute :>> obligationId="Catcher-root-slots"; }
part route37:RouteRow { attribute :>> component="roots"; attribute :>> actionName="catcher_landing_marker_settlement.rewriteRootOnly"; attribute :>> lemma="CatcherSettlement.rewriteRootOnlyPreserves"; attribute :>> producerAnchor="gc-slot-winner"; attribute :>> obligationId="Catcher-root-slots"; }
part route38:RouteRow { attribute :>> component="roots"; attribute :>> actionName="catcher_landing_marker_settlement.rewriteRegistryFirst"; attribute :>> lemma="CatcherSettlement.rewriteRegistryFirstPreserves"; attribute :>> producerAnchor="gc-slot-winner"; attribute :>> obligationId="Catcher-root-slots"; }
part route39:RouteRow { attribute :>> component="roots"; attribute :>> actionName="catcher_landing_marker_settlement.rewriteContextSlot"; attribute :>> lemma="CatcherSettlement.rewriteContextSlotPreserves"; attribute :>> producerAnchor="gc-slot-winner"; attribute :>> obligationId="Catcher-root-slots"; }
part route40:RouteRow { attribute :>> component="roots"; attribute :>> actionName="catcher_landing_marker_settlement.initializeCopiedObject"; attribute :>> lemma="CatcherSettlement.initializeCopiedObjectPreserves"; attribute :>> producerAnchor="gc-slot-winner"; attribute :>> obligationId="Catcher-root-slots"; }
part route41:RouteRow { attribute :>> component="roots"; attribute :>> actionName="catcher_landing_marker_settlement.finishGc"; attribute :>> lemma="CatcherSettlement.finishGcPreserves"; attribute :>> producerAnchor="gc-slot-winner"; attribute :>> obligationId="Catcher-root-slots"; }
part route42:RouteRow { attribute :>> component="roots"; attribute :>> actionName="catcher_landing_marker_settlement.closeRootAdmission"; attribute :>> lemma="CatcherSettlement.closeRootAdmissionPreserves"; attribute :>> producerAnchor="gc-slot-winner"; attribute :>> obligationId="Catcher-root-slots"; }
part route43:RouteRow { attribute :>> component="roots"; attribute :>> actionName="catcher_landing_marker_settlement.retireRoots"; attribute :>> lemma="CatcherSettlement.retireRootsPreserves"; attribute :>> producerAnchor="gc-slot-winner"; attribute :>> obligationId="Catcher-root-slots"; }
part route44:RouteRow { attribute :>> component="code"; attribute :>> actionName="catcher_landing_marker_settlement.ackDescriptorGrace"; attribute :>> lemma="CatcherSettlement.ackDescriptorGracePreserves"; attribute :>> producerAnchor="captured-frame-decode"; attribute :>> obligationId="Catcher-descriptors"; }
part route45:RouteRow { attribute :>> component="code"; attribute :>> actionName="catcher_landing_marker_settlement.retireDescriptor"; attribute :>> lemma="CatcherSettlement.retireDescriptorPreserves"; attribute :>> producerAnchor="captured-frame-decode"; attribute :>> obligationId="Catcher-descriptors"; }
part def ProofRow { attribute key:String; attribute lemma:String; }
part proof0:ProofRow { attribute :>> key="initialSafe"; attribute :>> lemma="CatcherSettlement.initialSafe"; }
part proof1:ProofRow { attribute :>> key="stepPreserves"; attribute :>> lemma="CatcherSettlement.stepPreserves"; }
part proof2:ProofRow { attribute :>> key="reachableSafe"; attribute :>> lemma="CatcherSettlement.reachableSafe"; }
part proof3:ProofRow { attribute :>> key="partialKeepsOriginal"; attribute :>> lemma="CatcherSettlement.partialKeepsOriginal"; }
part proof4:ProofRow { attribute :>> key="landingIssuerCut"; attribute :>> lemma="CatcherSettlement.landingIssuerCut"; }
part proof5:ProofRow { attribute :>> key="transitHasNoReceipt"; attribute :>> lemma="CatcherSettlement.transitHasNoReceipt"; }
part proof6:ProofRow { attribute :>> key="innerGapHasCustodian"; attribute :>> lemma="CatcherSettlement.innerGapHasCustodian"; }
part proof7:ProofRow { attribute :>> key="outerGapHasCustodian"; attribute :>> lemma="CatcherSettlement.outerGapHasCustodian"; }
part proof8:ProofRow { attribute :>> key="innerExactlyOnce"; attribute :>> lemma="CatcherSettlement.innerExactlyOnce"; }
part proof9:ProofRow { attribute :>> key="outerAfterInner"; attribute :>> lemma="CatcherSettlement.outerAfterInner"; }
part proof10:ProofRow { attribute :>> key="preReturnFrameLive"; attribute :>> lemma="CatcherSettlement.preReturnFrameLive"; }
part proof11:ProofRow { attribute :>> key="nativeBorrowFresh"; attribute :>> lemma="CatcherSettlement.nativeBorrowFresh"; }
part proof12:ProofRow { attribute :>> key="unreadyObjectHasCustodian"; attribute :>> lemma="CatcherSettlement.unreadyObjectHasCustodian"; }
part proof13:ProofRow { attribute :>> key="partialCopyNotExposed"; attribute :>> lemma="CatcherSettlement.partialCopyNotExposed"; }
part proof14:ProofRow { attribute :>> key="resumedSlotCoherent"; attribute :>> lemma="CatcherSettlement.resumedSlotCoherent"; }
part proof15:ProofRow { attribute :>> key="retirementCut"; attribute :>> lemma="CatcherSettlement.retirementCut"; }
part proof16:ProofRow { attribute :>> key="captureKeepsDescriptor"; attribute :>> lemma="CatcherSettlement.captureKeepsDescriptor"; }
part proof17:ProofRow { attribute :>> key="queryInnerDoesNotReplay"; attribute :>> lemma="CatcherSettlement.queryInnerDoesNotReplay"; }
part proof18:ProofRow { attribute :>> key="queryOuterDoesNotReplay"; attribute :>> lemma="CatcherSettlement.queryOuterDoesNotReplay"; }
part def PaperRow { attribute key:String; attribute title:String; attribute url:String; attribute section:String; attribute basis:String; attribute boundary:String; }
part paper0:PaperRow { attribute :>> key="gambit-pvm"; attribute :>> title="Feeley and Miller: A parallel virtual machine for efficient Scheme compilation"; attribute :>> url="https://www.iro.umontreal.ca/~feeley/papers/FeeleyMillerLFP90.pdf"; attribute :>> section="2"; attribute :>> basis="Front/back-end contract carries machine-specific facts"; attribute :>> boundary="Historical PVM is not a current C23 ABI proof"; }
part paper1:PaperRow { attribute :>> key="gambit-c-segments"; attribute :>> title="Feeley: Portable first-class continuations with C"; attribute :>> url="https://www.schemeworkshop.org/2000/feeley.ps"; attribute :>> section="1-5"; attribute :>> basis="Unlimited Scheme extent differs from dynamic C extent; independent native segments proposed"; attribute :>> boundary="Section 5 says not implemented then; preserve arbitrary C local state; no historical timings transferred"; }
part paper2:PaperRow { attribute :>> key="ocaml-effects"; attribute :>> title="Retrofitting Effect Handlers onto OCaml"; attribute :>> url="https://anil.recoil.org/papers/2021-pldi-retroeff.pdf"; attribute :>> section="3.1 and 5.3"; attribute :>> basis="Separate system/fiber stacks and explicit callback transitions"; attribute :>> boundary="One-shot effects do not cross C frames; neither restriction is silently applied to Gambit"; }
part paper3:PaperRow { attribute :>> key="c23-draft"; attribute :>> title="WG14 N3096 C23 working draft"; attribute :>> url="https://www.open-std.org/jtc1/sc22/wg14/www/docs/n3096.pdf"; attribute :>> section="5.1.2.4; 7.13.2.1"; attribute :>> basis="Release/acquire publication; longjmp requires same thread and live setjmp invocation"; attribute :>> boundary="Working draft, not purchased final ISO text; atomics do not extend C automatic lifetime"; }
part paper4:PaperRow { attribute :>> key="chez-stale-native"; attribute :>> title="Chez Scheme foreign interface"; attribute :>> url="https://cisco.github.io/ChezScheme/csug10.3.0/foreign.html"; attribute :>> section="4.4 and callback registration example"; attribute :>> basis="Nested foreign contexts become stale on return below them; callback code needs explicit retention"; attribute :>> boundary="Comparative mechanism only; not a Gambit implementation proof"; }
part def GroundingRow { attribute component:String; attribute producerAnchor:String; attribute paperKey:String; attribute obligationId:String; }
part grounding0:GroundingRow { attribute :>> component="control"; attribute :>> producerAnchor="call-catcher"; attribute :>> paperKey="gambit-c-segments"; attribute :>> obligationId="Catcher-landing"; }
part grounding1:GroundingRow { attribute :>> component="control"; attribute :>> producerAnchor="sfun-generator"; attribute :>> paperKey="gambit-pvm"; attribute :>> obligationId="Catcher-entry-abi"; }
part grounding2:GroundingRow { attribute :>> component="control"; attribute :>> producerAnchor="catcher-restore"; attribute :>> paperKey="ocaml-effects"; attribute :>> obligationId="Catcher-landing"; }
part grounding3:GroundingRow { attribute :>> component="control"; attribute :>> producerAnchor="catcher-local"; attribute :>> paperKey="c23-draft"; attribute :>> obligationId="Catcher-marker-release"; }
part grounding4:GroundingRow { attribute :>> component="code"; attribute :>> producerAnchor="captured-frame-decode"; attribute :>> paperKey="chez-stale-native"; attribute :>> obligationId="Catcher-descriptors"; }
part def GainRow { attribute key:String; attribute avoided:String; attribute added:String; attribute condition:String; }
part gain0:GainRow { attribute :>> key="G1"; attribute :>> avoided="One target-classified landing record can replace inferred completion at arbitrary catch sites"; attribute :>> added="Frame/thread/context/operation identity checks and stable receipt storage"; attribute :>> condition="Current END_TRY is not a signer; only exact target UNWIND route is modeled as accepted return"; }
part gain1:GainRow { attribute :>> key="G2"; attribute :>> avoided="Reply replay performs zero additional native reference decrements after commit"; attribute :>> added="Query lookup, operation retention and generation protection"; attribute :>> condition="Uncommitted physical effect remains inside an unproven native NoAbandon interval; no crash recovery claim"; }
part gain2:GainRow { attribute :>> key="G3"; attribute :>> avoided="Two-entry model performs exactly two native marker-reference drops in a completed path"; attribute :>> added="Exclusive writer/collector participation and two stable commit records"; attribute :>> condition="Does not reduce the baseline two drops; establishes conditional correctness, not speedup"; }
part gain3:GainRow { attribute :>> key="G4"; attribute :>> avoided="Opaque return-token candidate could retire one logical marker-vector construction and one native count release per admitted entry"; attribute :>> added="Stable token slot, RootBundle, generation lookup and FrameSpec/reflection/serialization migration"; attribute :>> condition="E marker-owning entries: net object constructors E-(R+S), native count releases E-D only if replacement qualifies; R views/S boxes/D new owned releases may erase savings; native paths retired zero"; }
part gain4:GainRow { attribute :>> key="G5"; attribute :>> avoided="Slot identity survives relocation; stale native cached values need not be trusted"; attribute :>> added="Mutable registry/context cells, scanner freeze and fresh borrow reload"; attribute :>> condition="Partial cell updates cannot be exposed to a running borrower or Scheme context"; }
part gain5:GainRow { attribute :>> key="G6"; attribute :>> avoided="One root/code/receipt ledger could replace separate implicit ownership reconstruction"; attribute :>> added="Metadata and native pin occupancy plus reader-grace work"; attribute :>> condition="Savings require deletion of old responsibilities, not a second ledger layered over them"; }
part gain6:GainRow { attribute :>> key="G7"; attribute :>> avoided="C23 expresses both retained-marker and opaque-token candidates"; attribute :>> added="Same GC, source, landing and code-lifetime obligations in Zig"; attribute :>> condition="No Zig-specific net return established; no per-resumption thread saving claimed"; }
part def MemoryRow { attribute key:String; attribute publication:String; attribute observation:String; attribute obligation:String; }
part memory0:MemoryRow { attribute :>> key="frame-record"; attribute :>> publication="Initialize stable FrameId/operation before setjmp, publish under owner admission"; attribute :>> observation="Acquire/pin stable record; use unchanged pre-setjmp local or lookup after landing"; attribute :>> obligation="Modified nonvolatile automatic values cannot be used as post-longjmp evidence"; }
part memory1:MemoryRow { attribute :>> key="escrow"; attribute :>> publication="Release publish immutable subtree membership and owned leases before physical transfer"; attribute :>> observation="Exact native owner validates the same operation and target incarnation"; attribute :>> obligation="Partial preparation rollback is private; unknown preparation requires old-executor exclusion before reconciliation"; }
part memory2:MemoryRow { attribute :>> key="landing"; attribute :>> publication="Release commit classified target landing after catcher restoration and destination checks"; attribute :>> observation="Acquire query returns same terminal record without invoking native transfer again"; attribute :>> obligation="Current ps->catcher has already been restored; it is not the landed-frame identity"; }
part memory3:MemoryRow { attribute :>> key="marker"; attribute :>> publication="Exclude all marker-count writers and collector readers; disable non-local exit sources for leaf"; attribute :>> observation="Perform count decrement then release commit receipt while custody still held"; attribute :>> obligation="An atomic done flag around a plain decrement is insufficient; no unsupported abandoning profile may enter this leaf"; }
part memory4:MemoryRow { attribute :>> key="slot-update"; attribute :>> publication="Collector exclusively writes actual registered cells while mutator/native borrowers are parked"; attribute :>> observation="Update registry/context cells and initialize payload before publishing completion; reload before native use"; attribute :>> obligation="Acquire alone does not move a copied SCMOBJ; descriptor and root leases survive the partial-copy interval"; }
part memory5:MemoryRow { attribute :>> key="descriptor"; attribute :>> publication="Close future admission and release last capture/scanner/native lease"; attribute :>> observation="Acquire complete cross-VM closure before unload"; attribute :>> obligation="Marker invalidation or count zero does not prove descriptor retirement"; }
part def ContractRow { attribute fromNode:String; attribute toNode:String; attribute custody:String; }
part contract0:ContractRow { attribute :>> fromNode="Admitted_Roots_and_Catchers"; attribute :>> toNode="Private_Subtree_Preparation"; attribute :>> custody="original native references and roots stay owned"; }
part contract1:ContractRow { attribute :>> fromNode="Private_Subtree_Preparation"; attribute :>> toNode="Known_Private_Rollback"; attribute :>> custody="release private extra leases only"; }
part contract2:ContractRow { attribute :>> fromNode="Private_Subtree_Preparation"; attribute :>> toNode="Unknown_Preparation_Custody"; attribute :>> custody="old executor/pins retained until qualified reconciliation"; }
part contract3:ContractRow { attribute :>> fromNode="Private_Subtree_Preparation"; attribute :>> toNode="Stable_Escrow_Record"; attribute :>> custody="atomic commit after full preparation"; }
part contract4:ContractRow { attribute :>> fromNode="Stable_Escrow_Record"; attribute :>> toNode="Inner_Catcher"; attribute :>> custody="unwind issued; no landing receipt yet"; }
part contract5:ContractRow { attribute :>> fromNode="Inner_Catcher"; attribute :>> toNode="Restored_Parent_Catcher"; attribute :>> custody="destination mismatch propagates"; }
part contract6:ContractRow { attribute :>> fromNode="Restored_Parent_Catcher"; attribute :>> toNode="Target_Catcher_Restored"; attribute :>> custody="caught frame is outer; current catcher becomes prior frame"; }
part contract7:ContractRow { attribute :>> fromNode="Target_Catcher_Restored"; attribute :>> toNode="Classified_Landing_Record"; attribute :>> custody="check operation, frame, thread, error and marker; freshly rooted data"; }
part contract8:ContractRow { attribute :>> fromNode="Classified_Landing_Record"; attribute :>> toNode="Exclusive_Marker_Release"; attribute :>> custody="NoAbandon and GC/writer exclusion"; }
part contract9:ContractRow { attribute :>> fromNode="Exclusive_Marker_Release"; attribute :>> toNode="Effect_Before_Receipt"; attribute :>> custody="plain decrement has happened; stable custodian cannot abandon"; }
part contract10:ContractRow { attribute :>> fromNode="Effect_Before_Receipt"; attribute :>> toNode="Committed_Release_Record"; attribute :>> custody="commit before releasing exclusion or returning reply"; }
part contract11:ContractRow { attribute :>> fromNode="Committed_Release_Record"; attribute :>> toNode="Idempotent_Reply_Query"; attribute :>> custody="lost reply never replays decrement"; }
part contract12:ContractRow { attribute :>> fromNode="Both_Markers_Committed"; attribute :>> toNode="Captured_Scheme_Resumption"; attribute :>> custody="guards settled; fresh Scheme ticket; native return remains expired"; }
part contract13:ContractRow { attribute :>> fromNode="Captured_Scheme_Resumption"; attribute :>> toNode="GC_Registry_Cell"; attribute :>> custody="freeze context before relocation"; }
part contract14:ContractRow { attribute :>> fromNode="GC_Registry_Cell"; attribute :>> toNode="GC_Context_Cell"; attribute :>> custody="partial update held under scanner ownership"; }
part contract15:ContractRow { attribute :>> fromNode="GC_Ready_Join"; attribute :>> toNode="Root_And_Code_Grace"; attribute :>> custody="coherent cells AND initialized payload before exposure; final capture and reader closure"; }
part contract16:ContractRow { attribute :>> fromNode="Root_And_Code_Grace"; attribute :>> toNode="Descriptor_Retirement"; attribute :>> custody="last captured/native/scanner/global owner closure"; }
part def RoleRow { attribute key:String; attribute identity:String; attribute retirement:String; attribute boundary:String; }
part role0:RoleRow { attribute :>> key="StablePreparation"; attribute :>> identity="Private progress ledger outside the abandoned C frames"; attribute :>> retirement="Known rollback returns only private extra leases; original custody persists"; attribute :>> boundary="Unknown preparation is not permission to free or repeat"; }
part role1:RoleRow { attribute :>> key="CatcherLandingReceipt"; attribute :>> identity="OperationId, NativeThreadIncarnation, ContextId, TargetFrameId, marker identity and exit kind"; attribute :>> retirement="Published after exact target restoration/checks, retained for replay"; attribute :>> boundary="Intermediate catcher and current catcher pointer are not equivalent identities"; }
part role2:RoleRow { attribute :>> key="MarkerReleaseTicket"; attribute :>> identity="Marker incarnation plus one native-owned reference and committed settlement"; attribute :>> retirement="Effect and receipt occur inside one qualified NoAbandon/exclusive interval"; attribute :>> boundary="Ordinary refcount decrement is not idempotent and current code has no durable ticket"; }
part role3:RoleRow { attribute :>> key="MutableRootSlot"; attribute :>> identity="Stable SlotKey with GC-rewritten SCMOBJ, source/context transfer and borrow lease"; attribute :>> retirement="Reader/admission grace after final semantic owner exits"; attribute :>> boundary="C23 visibility does not substitute for root enumeration or slot rewriting"; }
part role4:RoleRow { attribute :>> key="OpaqueReturnTokenCandidate"; attribute :>> identity="Preissued native return handle separated from Scheme procedure roots"; attribute :>> retirement="Expired native return traps; storage/descriptor/replay leases retire independently"; attribute :>> boundary="Requires native-entry ABI and reflection/serialization design; not a drop-in Scheme allocator substitution"; }
part def CompositionRow { attribute key:String; attribute fromAction:String; attribute toAction:String; attribute lemma:String; attribute fromComponent:String; attribute toComponent:String; attribute sharedConstraint:String; }
part composition0:CompositionRow { attribute :>> key="preparation-to-landing"; attribute :>> fromAction="catcher_landing_marker_settlement.publishEscrow"; attribute :>> toAction="catcher_landing_marker_settlement.publishLanding"; attribute :>> lemma="CatcherSettlement.landingIssuerCut"; attribute :>> fromComponent="control"; attribute :>> toComponent="control"; attribute :>> sharedConstraint="Escrow commit is not a landing receipt; same stable operation and actual target frame"; }
part composition1:CompositionRow { attribute :>> key="landing-to-target-exit"; attribute :>> fromAction="catcher_landing_marker_settlement.nativeTargetReturned"; attribute :>> toAction="catcher_landing_marker_settlement.decrementOuter"; attribute :>> lemma="CatcherSettlement.outerGapHasCustodian"; attribute :>> fromComponent="control"; attribute :>> toComponent="control"; attribute :>> sharedConstraint="Target catcher landing does not authorize outer-marker release before the target invocation exits"; }
part composition2:CompositionRow { attribute :>> key="landing-to-marker"; attribute :>> fromAction="catcher_landing_marker_settlement.publishLanding"; attribute :>> toAction="catcher_landing_marker_settlement.decrementInner"; attribute :>> lemma="CatcherSettlement.innerGapHasCustodian"; attribute :>> fromComponent="control"; attribute :>> toComponent="control"; attribute :>> sharedConstraint="Physical decrement requires the accepted landing and an exclusive NoAbandon interval"; }
part composition3:CompositionRow { attribute :>> key="marker-to-query"; attribute :>> fromAction="catcher_landing_marker_settlement.commitInnerRelease"; attribute :>> toAction="catcher_landing_marker_settlement.queryInnerRelease"; attribute :>> lemma="CatcherSettlement.innerExactlyOnce"; attribute :>> fromComponent="control"; attribute :>> toComponent="control"; attribute :>> sharedConstraint="A lost reply queries the committed ticket; no second decrement"; }
part composition4:CompositionRow { attribute :>> key="gc-to-resumption"; attribute :>> fromAction="catcher_landing_marker_settlement.rewriteContextSlot"; attribute :>> toAction="catcher_landing_marker_settlement.finishResumption"; attribute :>> lemma="CatcherSettlement.resumedSlotCoherent"; attribute :>> fromComponent="roots"; attribute :>> toComponent="control"; attribute :>> sharedConstraint="GC may update cells in steps; a resumed mutator is parked until context and registry agree"; }
part composition5:CompositionRow { attribute :>> key="root-to-marker"; attribute :>> fromAction="catcher_landing_marker_settlement.borrowFresh"; attribute :>> toAction="catcher_landing_marker_settlement.decrementInner"; attribute :>> lemma="CatcherSettlement.nativeBorrowFresh"; attribute :>> fromComponent="roots"; attribute :>> toComponent="control"; attribute :>> sharedConstraint="Root slot is freshly reloaded and moving GC excluded during raw native effect"; }
part composition6:CompositionRow { attribute :>> key="capture-to-code"; attribute :>> fromAction="catcher_landing_marker_settlement.resumeCaptured"; attribute :>> toAction="catcher_landing_marker_settlement.retireDescriptor"; attribute :>> lemma="CatcherSettlement.captureKeepsDescriptor"; attribute :>> fromComponent="control"; attribute :>> toComponent="code"; attribute :>> sharedConstraint="Marker release does not discharge captured Scheme frame descriptor leases"; }
part composition7:CompositionRow { attribute :>> key="root-to-code"; attribute :>> fromAction="catcher_landing_marker_settlement.retireRoots"; attribute :>> toAction="catcher_landing_marker_settlement.retireDescriptor"; attribute :>> lemma="CatcherSettlement.retirementCut"; attribute :>> fromComponent="roots"; attribute :>> toComponent="code"; attribute :>> sharedConstraint="Slot retirement and image retirement have different closure conditions"; }
part contract17:ContractRow { attribute :>> fromNode="Classified_Landing_Record"; attribute :>> toNode="Target_Invocation_Exit"; attribute :>> custody="caller-side evidence after the identified ___call returns"; }
part contract18:ContractRow { attribute :>> fromNode="Target_Invocation_Exit"; attribute :>> toNode="Owner_Last_Use_Check"; attribute :>> custody="invocation return alone does not close marker owner; qualify final use"; }
part contract19:ContractRow { attribute :>> fromNode="Committed_Release_Record"; attribute :>> toNode="Outer_Marker_Release"; attribute :>> custody="inner reference committed; target invocation-exit receipt also required"; }
part contract20:ContractRow { attribute :>> fromNode="Outer_Marker_Release"; attribute :>> toNode="Both_Markers_Committed"; attribute :>> custody="separate outer effect and commit under same qualified custody"; }
part contract21:ContractRow { attribute :>> fromNode="GC_Registry_Cell"; attribute :>> toNode="Payload_Initialization"; attribute :>> custody="root address can be updated before copying payload"; }
part contract22:ContractRow { attribute :>> fromNode="GC_Context_Cell"; attribute :>> toNode="GC_Ready_Join"; attribute :>> custody="all registered cells coherent; payload also required"; }
part contract23:ContractRow { attribute :>> fromNode="Payload_Initialization"; attribute :>> toNode="GC_Ready_Join"; attribute :>> custody="initialized payload; coherent context cell also required"; }
part source46:SourceRow { attribute :>> key="owner-reuse-loop"; attribute :>> path="vendor/gambit/include/_gambit/foreign_conversion.h.in"; attribute :>> needle="#define ___SFUN_ERROR_VOID while"; attribute :>> obligation="SFUN conversion-error retry reuses marker; invocation exit is not owner-use closure"; }
part leaf4:LeafRow { attribute :>> key="leaf-owner-last-use"; attribute :>> component="control"; attribute :>> actionName="catcher_landing_marker_settlement.nativeTargetReturned"; attribute :>> lemma="CatcherSettlement.outerAfterInner"; attribute :>> producerAnchor="owner-reuse-loop"; attribute :>> qualification="Bounded outer ___run single-call/last-use profile with qualified owner-use closure"; attribute :>> boundary="A returned ___call cannot close an outer SFUN marker owner that may reenter its conversion-error loop; that profile remains uncertified"; }
part role5:RoleRow { attribute :>> key="MarkerOwnerUseClosure"; attribute :>> identity="MarkerOwnerId plus final-use generation; distinct from each invocation FrameId"; attribute :>> retirement="Release only after invocation exit and all future owner uses are closed"; attribute :>> boundary="Current bounded model admits outer ___run only; outer SFUN retry lifecycle needs additional states and native qualification"; }
part contract24:ContractRow { attribute :>> fromNode="Owner_Last_Use_Check"; attribute :>> toNode="Invocation_And_Owner_Closure"; attribute :>> custody="___run final-use profile; outer SFUN retry closure remains unresolved"; }
part contract25:ContractRow { attribute :>> fromNode="Invocation_And_Owner_Closure"; attribute :>> toNode="Outer_Marker_Release"; attribute :>> custody="invocation receipt AND owner-use closure; same operation and marker owner"; }
}
