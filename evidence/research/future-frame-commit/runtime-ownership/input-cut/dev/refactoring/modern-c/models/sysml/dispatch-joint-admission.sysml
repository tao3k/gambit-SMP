package GambitDispatchJointAdmission { private import ScalarValues::*;
part def SourceRow { attribute key:String; attribute path:String; attribute needle:String; attribute obligation:String; }
part source0:SourceRow { attribute :>> key="catcher"; attribute :>> path="vendor/gambit/include/_gambit/foreign_conversion.h.in"; attribute :>> needle="___ps->catcher = &___jbuf;"; attribute :>> obligation="catcher is automatic activation, restored at END_TRY"; }
part source1:SourceRow { attribute :>> key="throw"; attribute :>> path="vendor/gambit/include/_gambit/foreign_conversion.h.in"; attribute :>> needle="#define ___THROW(e)do { ___ps->longjmp_err"; attribute :>> obligation="nonlocal jump can bypass nested local ENDs"; }
part source2:SourceRow { attribute :>> key="language-c"; attribute :>> path="vendor/gambit/include/_gambit/language.h.in"; attribute :>> needle="#define ___USE_SETJMP"; attribute :>> obligation="C path uses setjmp; no C++ RAII assumption"; }
part source3:SourceRow { attribute :>> key="call-entry"; attribute :>> path="vendor/gambit/lib/setup.c"; attribute :>> needle="___EXP_FUNC(___SCMOBJ,___call)"; attribute :>> obligation="GC phase rejection before frame writes; catcher created later"; }
part source4:SourceRow { attribute :>> key="marker-rooted"; attribute :>> path="vendor/gambit/lib/c_intf.c"; attribute :>> needle="proc_or_false = *proc_root; /* reload after allocating the marker */"; attribute :>> obligation="rooted startup endpoint reloads; generic wrapper local not registry"; }
part source5:SourceRow { attribute :>> key="marker-raw"; attribute :>> path="vendor/gambit/lib/c_intf.c"; attribute :>> needle="Legacy raw SFUN entry is not made a registered-root interface"; attribute :>> obligation="do not infer generic ingress roots"; }
part source6:SourceRow { attribute :>> key="marker-kill"; attribute :>> path="vendor/gambit/lib/c_intf.c"; attribute :>> needle="___still_obj_refcount_dec (marker);"; attribute :>> obligation="different object and native lifetime"; }
part source7:SourceRow { attribute :>> key="scan-context"; attribute :>> path="vendor/gambit/lib/_mem/root-origins.inc"; attribute :>> needle="mark_array (work, context->r, sizeof(context->r)/sizeof(*context->r));"; attribute :>> obligation="includes exact PSR1 slot"; }
part source8:SourceRow { attribute :>> key="owner-cleanup"; attribute :>> path="vendor/gambit/lib/_mem/collection-round.inc"; attribute :>> needle="vm->gc_participants[id].phase = ___GC_OWNER_CLEANUP;"; attribute :>> obligation="restored stacks do not authorize managed reentry"; }
part source9:SourceRow { attribute :>> key="darwin-config"; attribute :>> path="vendor/gambit/config.status"; attribute :>> needle="'--disable-smp'"; attribute :>> obligation="configured arm64 GCC16 subset not SMP native qualification"; }
part source10:SourceRow { attribute :>> key="width-config"; attribute :>> path="vendor/gambit/config.log"; attribute :>> needle="ac_cv_sizeof_long=8"; attribute :>> obligation="historical generated profile"; }
part source11:SourceRow { attribute :>> key="build-command"; attribute :>> path="vendor/gambit/bin/gambuild-C"; attribute :>> needle="/opt/homebrew/Cellar/gcc/16.2.0/bin/gcc-16"; attribute :>> obligation="actual recorded toolchain command"; }
part source12:SourceRow { attribute :>> key="feeley-paper"; attribute :>> path="evidence/research/sfun-converter-use-closure/feeley-sfp-paper.txt"; attribute :>> needle="return to C frames"; attribute :>> obligation="Scheme continuation extent versus C activation extent"; }
part source13:SourceRow { attribute :>> key="tcl-native-callback"; attribute :>> path="vendor/gambit/examples/tcltk/tcltk.scm"; attribute :>> needle="char *result = tcltk_call (___EXT(___data_rc)"; attribute :>> obligation="real callback loads RC payload before SFUN marker allocation"; }
part source14:SourceRow { attribute :>> key="tcl-register"; attribute :>> path="vendor/gambit/examples/tcltk/tcltk.scm"; attribute :>> needle="___result = ___BOOLEAN (Tcl_CreateCommand"; attribute :>> obligation="native command registration supplies callback and delete hooks"; }
part source15:SourceRow { attribute :>> key="tcl-export"; attribute :>> path="vendor/gambit/examples/tcltk/tcltk.scm"; attribute :>> needle="(c-define (##tcltk-call vect args)"; attribute :>> obligation="typed-result SFUN source producer"; }
part source16:SourceRow { attribute :>> key="tcl-delete"; attribute :>> path="vendor/gambit/examples/tcltk/tcltk.scm"; attribute :>> needle="___HIDDEN void scheme_delete_cmd"; attribute :>> obligation="delete hook releases payload/RC, not a Scheme invocation"; }
part source17:SourceRow { attribute :>> key="tcl-error-callback"; attribute :>> path="vendor/gambit/examples/tcltk/tcltk.scm"; attribute :>> needle="tcltk_eval_error (___CAST(char*,Tcl_GetStringResult(tcl_interp)));"; attribute :>> obligation="native error translator calls a second SFUN endpoint"; }
part source18:SourceRow { attribute :>> key="tcl-error-export"; attribute :>> path="vendor/gambit/examples/tcltk/tcltk.scm"; attribute :>> needle="(c-define (##tcltk-eval-error msg)"; attribute :>> obligation="void error callback also needs refusal policy"; }
part source19:SourceRow { attribute :>> key="tcl-source-publish"; attribute :>> path="vendor/gambit/examples/tcltk/tcltk.scm"; attribute :>> needle="___EXT(___set_data_rc) (cd, vect);"; attribute :>> obligation="STILL vector count protects payload while alive; delete requires borrow closure"; }
part source20:SourceRow { attribute :>> key="rc-source-read"; attribute :>> path="vendor/gambit/lib/_mem/rc-allocation.inc"; attribute :>> needle="___EXP_FUNC(___SCMOBJ,___data_rc)"; attribute :>> obligation="read value is not an atomic borrow or root transfer"; }
part source21:SourceRow { attribute :>> key="rc-source-write"; attribute :>> path="vendor/gambit/lib/_mem/rc-allocation.inc"; attribute :>> needle="h->data = val;"; attribute :>> obligation="public setter must join source-root writer admission"; }
part source22:SourceRow { attribute :>> key="rc-scan"; attribute :>> path="vendor/gambit/lib/_mem/rc-roots.inc"; attribute :>> needle="mark_array (work, &h->data, 1);"; attribute :>> obligation="actual context-owned RC data scanner"; }
part source23:SourceRow { attribute :>> key="rc-addref"; attribute :>> path="vendor/gambit/lib/_mem/rc-allocation.inc"; attribute :>> needle="h->refcount++;"; attribute :>> obligation="plain native RC count is not a versioned payload borrow"; }
part source24:SourceRow { attribute :>> key="rc-release"; attribute :>> path="vendor/gambit/lib/_mem/rc-allocation.inc"; attribute :>> needle="if (--h->refcount == 0)"; attribute :>> obligation="unlinks/free header at zero; separate Scheme hold"; }
part source25:SourceRow { attribute :>> key="rc-forced-cleanup"; attribute :>> path="vendor/gambit/lib/_mem/rc-allocation.inc"; attribute :>> needle="___HIDDEN void cleanup_rc"; attribute :>> obligation="forced list cleanup ignores borrower protocol; shutdown admission open"; }
part source26:SourceRow { attribute :>> key="rc-register"; attribute :>> path="vendor/gambit/lib/_mem/rc-allocation.inc"; attribute :>> needle="h->next = head;"; attribute :>> obligation="source registration mutates collector-scanned list"; }
part source27:SourceRow { attribute :>> key="rc-public-import"; attribute :>> path="vendor/gambit/include/_gambit/runtime_protocols.h.in"; attribute :>> needle="___IMP_FUNC(void,___set_data_rc)"; attribute :>> obligation="public void setter cannot report checked unknown/failure by itself"; }
part source28:SourceRow { attribute :>> key="rc-public-export"; attribute :>> path="vendor/gambit/lib/setup.c"; attribute :>> needle="___GSTATE->___set_data_rc"; attribute :>> obligation="function-table exposure; closed explicit writer census not all clients"; }
part source29:SourceRow { attribute :>> key="closure-setter"; attribute :>> path="vendor/gambit/lib/os_dyn.c"; attribute :>> needle="___set_data_rc (c_closure, proc);"; attribute :>> obligation="other explicit setter is C closure initialization"; }
part source30:SourceRow { attribute :>> key="tcl-result-transfer"; attribute :>> path="vendor/gambit/examples/tcltk/tcltk.scm"; attribute :>> needle="___CAST(Tcl_FreeProc*,___EXT(___release_string))"; attribute :>> obligation="normal result ownership transfer remains required"; }
part source31:SourceRow { attribute :>> key="native-string-free"; attribute :>> path="vendor/gambit/lib/c_intf.c"; attribute :>> needle="___EXP_FUNC(void,___release_string)"; attribute :>> obligation="normal Gambit result free calls RC release, not Scheme directly"; }
part source32:SourceRow { attribute :>> key="tcl-null-result"; attribute :>> path="vendor/gambit/examples/tcltk/tcltk.scm"; attribute :>> needle="if (result == NULL)"; attribute :>> obligation="NULL means valid empty result, not a refusal sentinel"; }
part source33:SourceRow { attribute :>> key="tcl-eval-driver"; attribute :>> path="vendor/gambit/examples/tcltk/tcltk.scm"; attribute :>> needle="else if (Tcl_Eval (tcl_interp, cmd) != TCL_OK)"; attribute :>> obligation="old native error translator invokes Scheme without origin distinction"; }
part source34:SourceRow { attribute :>> key="tcl-event-driver"; attribute :>> path="vendor/gambit/examples/tcltk/tcltk.scm"; attribute :>> needle="Tcl_DoOneEvent (TCL_DONT_WAIT)"; attribute :>> obligation="native scope producer must start before lookup/dispatch, not callback prologue"; }
part source35:SourceRow { attribute :>> key="tcl-interp-delete"; attribute :>> path="vendor/gambit/examples/tcltk/tcltk.scm"; attribute :>> needle="Tcl_DeleteInterp (tcl_interp);"; attribute :>> obligation="logical interpreter deletion and owner scope drain are distinct"; }
part source36:SourceRow { attribute :>> key="root-strong-source"; attribute :>> path="vendor/gambit/lib/_mem/root-origins.inc"; attribute :>> needle="mark_rc (work, context);"; attribute :>> obligation="reuse context-owned RC root enumeration"; }
part source37:SourceRow { attribute :>> key="foreign-release-clear"; attribute :>> path="vendor/gambit/lib/c_intf.c"; attribute :>> needle="___FOREIGN_PTR_FIELD(obj) ="; attribute :>> obligation="callback completion not inferred from clearing fields"; }
part source38:SourceRow { attribute :>> key="root-decrement"; attribute :>> path="vendor/gambit/lib/_mem/still-refcount.inc"; attribute :>> needle="___BODY0(obj)[___STILL_REFCOUNT-___STILL_BODY]--;"; attribute :>> obligation="plain Scheme still counter needs its own owner/effect receipt"; }
part source39:SourceRow { attribute :>> key="tcl-native-dispatch"; attribute :>> path="evidence/research/source-references/tcl/cbf86d62348d6b052e1961b4df995960fb21545f/generic/tclBasic.c"; attribute :>> needle="result = cmdPtr->proc(cmdPtr->clientData, interp, objc, argv);"; attribute :>> obligation="callback uses clientData; argv freed only after callback returns"; }
part source40:SourceRow { attribute :>> key="tcl-argv-release"; attribute :>> path="evidence/research/source-references/tcl/cbf86d62348d6b052e1961b4df995960fb21545f/generic/tclBasic.c"; attribute :>> needle="TclStackFree(interp, (void *) argv);"; attribute :>> obligation="borrowed argv cannot be queued after native scope without copy"; }
part source41:SourceRow { attribute :>> key="tcl-native-delete"; attribute :>> path="evidence/research/source-references/tcl/cbf86d62348d6b052e1961b4df995960fb21545f/generic/tclBasic.c"; attribute :>> needle="cmdPtr->deleteProc(cmdPtr->deleteData);"; attribute :>> obligation="application data deletion precedes final command struct release"; }
part source42:SourceRow { attribute :>> key="tcl-delete-order"; attribute :>> path="evidence/research/source-references/tcl/cbf86d62348d6b052e1961b4df995960fb21545f/generic/tclBasic.c"; attribute :>> needle="TclCleanupCommandMacro(cmdPtr);"; attribute :>> obligation="command refcount is not payload protection"; }
part source43:SourceRow { attribute :>> key="tcl-set-info"; attribute :>> path="evidence/research/source-references/tcl/cbf86d62348d6b052e1961b4df995960fb21545f/generic/tclBasic.c"; attribute :>> needle="cmdPtr->clientData = infoPtr->clientData;"; attribute :>> obligation="native command setter bypasses old logical registration owner unless managed"; }
part source44:SourceRow { attribute :>> key="tcl-set-delete"; attribute :>> path="evidence/research/source-references/tcl/cbf86d62348d6b052e1961b4df995960fb21545f/generic/tclBasic.c"; attribute :>> needle="cmdPtr->deleteData = infoPtr->deleteData;"; attribute :>> obligation="deleteData may differ from current dispatch clientData"; }
part source45:SourceRow { attribute :>> key="tcl-get-info"; attribute :>> path="evidence/research/source-references/tcl/cbf86d62348d6b052e1961b4df995960fb21545f/generic/tclBasic.c"; attribute :>> needle="infoPtr->clientData = cmdPtr->clientData;"; attribute :>> obligation="raw ClientData can escape through command info"; }
part source46:SourceRow { attribute :>> key="tcl-token-epoch"; attribute :>> path="evidence/research/source-references/tcl/cbf86d62348d6b052e1961b4df995960fb21545f/generic/tclBasic.c"; attribute :>> needle="cmdPtr->cmdEpoch++;"; attribute :>> obligation="Tcl command epoch is not VM storage/payload generation"; }
part source47:SourceRow { attribute :>> key="tcl-native-publication"; attribute :>> path="evidence/research/source-references/tcl/cbf86d62348d6b052e1961b4df995960fb21545f/generic/tclBasic.c"; attribute :>> needle="cmdPtr->deleteData = clientData;"; attribute :>> obligation="initial create binds native dispatch and delete data"; }
part source48:SourceRow { attribute :>> key="tcl-result-free-hook"; attribute :>> path="evidence/research/source-references/tcl/cbf86d62348d6b052e1961b4df995960fb21545f/generic/tclResult.c"; attribute :>> needle="oldFreeProc(oldResult);"; attribute :>> obligation="SetResult invokes prior custom free callback; record refusal before publication"; }
part source49:SourceRow { attribute :>> key="tcl-command-type"; attribute :>> path="evidence/research/source-references/tcl/cbf86d62348d6b052e1961b4df995960fb21545f/generic/tclInt.h"; attribute :>> needle="typedef struct Command"; attribute :>> obligation="native Command type distinct from Gambit RC header"; }
part source50:SourceRow { attribute :>> key="ocaml-domain-contract"; attribute :>> path="vendor/ocaml/otherlibs/systhreads/caml/threads.h"; attribute :>> needle="must not access any OCaml data,"; attribute :>> obligation="registered thread, domain access and GC roots are separate obligations"; }
part source51:SourceRow { attribute :>> key="ocaml-thread-register"; attribute :>> path="vendor/ocaml/otherlibs/systhreads/caml/threads.h"; attribute :>> needle="The domain lock"; attribute :>> obligation="registration does not itself supply a held domain lock"; }
part source52:SourceRow { attribute :>> key="ocaml-root-write"; attribute :>> path="vendor/ocaml/runtime/caml/memory.h"; attribute :>> needle="will not be assigned directly."; attribute :>> obligation="root identity and modification protocol required for efficient scanning"; }
part source53:SourceRow { attribute :>> key="ocaml-root-lock"; attribute :>> path="vendor/ocaml/runtime/globroots.c"; attribute :>> needle="static caml_plat_mutex roots_mutex"; attribute :>> obligation="root list synchronization; not a lock-free read/write guarantee"; }
part source54:SourceRow { attribute :>> key="ocaml-root-tombstone"; attribute :>> path="vendor/ocaml/runtime/globroots.c"; attribute :>> needle="*p = ROOT_DELETED;"; attribute :>> obligation="deferred removal while iteration in progress, not concurrent unrestricted slot deletion"; }
part source55:SourceRow { attribute :>> key="ocaml-blocking"; attribute :>> path="vendor/ocaml/runtime/signals.c"; attribute :>> needle="caml_release_domain_lock();"; attribute :>> obligation="native blocking and runtime access have explicit transitions"; }
part source56:SourceRow { attribute :>> key="otp-no-lookup"; attribute :>> path="vendor/erlang-otp/erts/emulator/internal_doc/ThreadProgress.md"; attribute :>> needle="remove the possibility to look up"; attribute :>> obligation="disable discovery before grace, with references dropped by known-state boundary"; }
part source57:SourceRow { attribute :>> key="otp-unmanaged"; attribute :>> path="vendor/erlang-otp/erts/emulator/internal_doc/ThreadProgress.md"; attribute :>> needle="two reference counters"; attribute :>> obligation="unmanaged delay remains explicitly counted; hot counters can contend"; }
part source58:SourceRow { attribute :>> key="otp-no-blanket-scheduler"; attribute :>> path="vendor/erlang-otp/erts/emulator/beam/erl_thr_progress.h"; attribute :>> needle="return ERTS_THR_PRGR_DHANDLE_MANAGED;"; attribute :>> obligation="managed designation has scheduler/quiescent-state premises"; }
part source59:SourceRow { attribute :>> key="otp-isolation"; attribute :>> path="vendor/erlang-otp/erts/emulator/internal_doc/GarbageCollection.md"; attribute :>> needle="Each Erlang process has its own stack and heap"; attribute :>> obligation="process-local collection depends on isolation; not Scheme shared-heap semantics"; }
part source60:SourceRow { attribute :>> key="otp-native-limit"; attribute :>> path="vendor/erlang-otp/erts/doc/references/erl_nif.md"; attribute :>> needle="a separate set of schedulers called dirty schedulers"; attribute :>> obligation="long native execution gets separate scheduler treatment, not forced-safe termination"; }
part source61:SourceRow { attribute :>> key="gambit-native-thread"; attribute :>> path="vendor/gambit/lib/os_thread.c"; attribute :>> needle="pthread_create (&thread_id,"; attribute :>> obligation="real OS-thread producer contradicts single-green-thread-only characterization"; }
part source62:SourceRow { attribute :>> key="gambit-start-thread"; attribute :>> path="vendor/gambit/lib/setup.c"; attribute :>> needle="if ((r->result = ___thread_create (t))"; attribute :>> obligation="processor resize starts native threads; native readiness is separate from useful parallelism"; }
part source63:SourceRow { attribute :>> key="gambit-steal"; attribute :>> path="vendor/gambit/lib/_thread.scm"; attribute :>> needle="There are no runnable threads locally, so try to steal"; attribute :>> obligation="Gambit already has local queues and work stealing; do not invent missing mechanisms"; }
part source64:SourceRow { attribute :>> key="gambit-shared-send"; attribute :>> path="vendor/gambit/lib/_thread.scm"; attribute :>> needle="(define-prim (##thread-send"; attribute :>> obligation="actor API alone does not imply ownership-isolated message payloads"; }
part source65:SourceRow { attribute :>> key="gambit-gc-stages"; attribute :>> path="vendor/gambit/lib/_mem/collection-round.inc"; attribute :>> needle="case ___GC_ROOT_STRONG:"; attribute :>> obligation="GC phases exist and have explicit worker obligations; global throughput unproved"; }
part source66:SourceRow { attribute :>> key="pvm-lazy-source"; attribute :>> path="evidence/research/source-references/feeley-pvm/ad1f9ca247f0c97835bda99bd387ca735767ab68ed4338897ade618ad769d2f1.txt"; attribute :>> needle="2.7 Parallelism in PVM"; attribute :>> obligation="primary task/work/done and lazy materialization mechanism; current GVM refinement open"; }
part def ComponentRow { attribute componentId:String; attribute sharedContract:String; attribute role:String; }
part component0:ComponentRow { attribute :>> componentId="native-scope"; attribute :>> sharedContract="NativeScope/RootReservation/JointReceipt"; attribute :>> role="Tcl owner, pre-lookup grace and logical deletion"; }
part component1:ComponentRow { attribute :>> componentId="root-domain"; attribute :>> sharedContract="NativeScope/RootReservation/JointReceipt"; attribute :>> role="source slot census, short mutation grant and freeze"; }
part component2:ComponentRow { attribute :>> componentId="joint-custody"; attribute :>> sharedContract="NativeScope/RootReservation/JointReceipt"; attribute :>> role="stable reservation/commit receipt and native outcome"; }
part component3:ComponentRow { attribute :>> componentId="runtime-foundation"; attribute :>> sharedContract="NativeScope/RootReservation/JointReceipt"; attribute :>> role="execution context, native worker, actor profile and modern-C migration"; }
part def LearningRow { attribute key:String; attribute source:String; attribute mechanism:String; attribute fact:String; attribute mismatch:String; attribute candidate:String; attribute status:String; }
part learning0:LearningRow { attribute :>> key="feeley-native-extent"; attribute :>> source="feeley-paper"; attribute :>> mechanism="Scheme continuation versus native stack extent"; attribute :>> fact="historical lazy native-frame removal and independent native-stack proposal are distinguished"; attribute :>> mismatch="paper does not implement a C23 source-borrow service; proposed native-thread approach was not implemented there"; attribute :>> candidate="keep native scope alive until real native-frame last use; never equate Scheme yield with native quiescence"; attribute :>> status="SOURCE-FACT; GAMBIT-INFERENCE-CONDITIONAL"; }
part learning1:LearningRow { attribute :>> key="ocaml-entry"; attribute :>> source="ocaml-domain-contract"; attribute :>> mechanism="thread registration plus runtime access"; attribute :>> fact="foreign threads must register and acquire domain access before runtime use"; attribute :>> mismatch="Gambit processor/context and multishot continuation are not an OCaml domain"; attribute :>> candidate="native owner proof and collector root authority remain separately checked"; attribute :>> status="SOURCE-FACT; GAMBIT-INFERENCE-CONDITIONAL"; }
part learning2:LearningRow { attribute :>> key="ocaml-roots"; attribute :>> source="ocaml-root-write"; attribute :>> mechanism="stable root address with controlled writes"; attribute :>> fact="generational root setters update collector bookkeeping; root iteration uses synchronized deletion rules"; attribute :>> mismatch="does not root old payload after arbitrary overwrite; no blanket lock-free guarantee"; attribute :>> candidate="retain/update source slots under a real scanner protocol; fixed-slot profile first"; attribute :>> status="SOURCE-FACT; GAMBIT-INFERENCE-CONDITIONAL"; }
part learning3:LearningRow { attribute :>> key="otp-grace"; attribute :>> source="otp-no-lookup"; attribute :>> mechanism="remove lookup then wait for managed progress"; attribute :>> fact="safe retirement relies on no new lookup and old references dropped before known-state reporting"; attribute :>> mismatch="Scheme scheduling checkpoint need not drop native C frames or raw ClientData aliases"; attribute :>> candidate="outer native scope begins before Tcl dispatch; logical deletion cannot immediately free source"; attribute :>> status="SOURCE-FACT; GAMBIT-INFERENCE-CONDITIONAL"; }
part learning4:LearningRow { attribute :>> key="otp-unmanaged"; attribute :>> source="otp-unmanaged"; attribute :>> mechanism="explicit unmanaged progress delay"; attribute :>> fact="unmanaged callers use handles/counters; documentation warns about contention"; attribute :>> mismatch="cannot call all Tcl/native threads managed just because Scheme has a scheduler"; attribute :>> candidate="use owner-confined scope accounting where possible; quantify shared-counter alternative separately"; attribute :>> status="SOURCE-FACT; GAMBIT-INFERENCE-CONDITIONAL"; }
part learning5:LearningRow { attribute :>> key="otp-actor-heap"; attribute :>> source="otp-isolation"; attribute :>> mechanism="per-process generational heap"; attribute :>> fact="isolated process roots enable local GC; off-heap data has separate ownership"; attribute :>> mismatch="Scheme aliasing, mutable pairs, closures and general continuations can cross actors"; attribute :>> candidate="optional ownership-isolated actor profile needs explicit transfer semantics; shared Scheme remains supported"; attribute :>> status="SOURCE-FACT; GAMBIT-INFERENCE-CONDITIONAL"; }
part learning6:LearningRow { attribute :>> key="otp-long-native"; attribute :>> source="otp-native-limit"; attribute :>> mechanism="separate dirty schedulers"; attribute :>> fact="long NIFs can run outside ordinary schedulers"; attribute :>> mismatch="dirty scheduling does not revoke arbitrary C memory writes or provide Tcl thread affinity"; attribute :>> candidate="classify native work and block/return authority; do not move Tcl calls across owners blindly"; attribute :>> status="SOURCE-FACT; GAMBIT-INFERENCE-CONDITIONAL"; }
part learning7:LearningRow { attribute :>> key="pvm-lazy-futures"; attribute :>> source="pvm-lazy-source"; attribute :>> mechanism="lazy future materialization at steal"; attribute :>> fact="PVM separates task/work/done; lazy execution delays parent splitting and placeholder allocation until another processor resumes the parent"; attribute :>> mismatch="historical PVM capability does not prove current GVM implements safe split points or effect-preserving implicit parallelism"; attribute :>> candidate="evaluate FrameSpec-supported split/restore with explicit eligible task semantics; separate from actor isolation"; attribute :>> status="PRIMARY-PAPER; GAMBIT-REFINEMENT-OPEN"; }
part def IssuerRow { attribute key:String; attribute source:String; attribute existing:String; attribute candidate:String; attribute gap:String; }
part issuer0:IssuerRow { attribute :>> key="outer-scope"; attribute :>> source="tcl-eval-driver"; attribute :>> existing="native eval wrapper and event driver surround Tcl"; attribute :>> candidate="Tcl interpreter owner acquires native scope before dispatch can select ClientData"; attribute :>> gap="Scheme mutex does not prove OS-thread affinity or full entry closure"; }
part issuer1:IssuerRow { attribute :>> key="root-reserve"; attribute :>> source="rc-scan"; attribute :>> existing="context-owned RC list scanned by mark_rc"; attribute :>> candidate="root-domain admission owns stable source slot and short root-write reservation"; attribute :>> gap="no current tryReserve checked API"; }
part issuer2:IssuerRow { attribute :>> key="joint-commit"; attribute :>> source="tcl-native-callback"; attribute :>> existing="raw scalar data_rc load before tcltk_call"; attribute :>> candidate="stable per-attempt record commits only after both native and root authority accepted"; attribute :>> gap="no cross-domain magical atomic issuer; stable finisher required"; }
part issuer3:IssuerRow { attribute :>> key="delete"; attribute :>> source="tcl-delete"; attribute :>> existing="immediate payload and header release"; attribute :>> candidate="native owner closes discoverability, defers physical disposal until old scope and borrow drain"; attribute :>> gap="active native selection may predate callback prologue"; }
part issuer4:IssuerRow { attribute :>> key="refusal"; attribute :>> source="tcl-eval-driver"; attribute :>> existing="old translator can call Scheme again"; attribute :>> candidate="native owner keeps definitive refused/no-commit outcome and bypasses translator"; attribute :>> gap="actual native outcome ABI unqualified"; }
part issuer5:IssuerRow { attribute :>> key="unknown"; attribute :>> source="rc-register"; attribute :>> existing="root ownership has concrete registry/slot effects"; attribute :>> candidate="root domain keeps pending/committed record; outer native owner retains matching scope; exact ticket query"; attribute :>> gap="never retry as new invocation or free from absence of acknowledgement"; }
part def ProfileRow { attribute key:String; attribute scope:String; attribute permission:String; attribute boundary:String; }
part profile0:ProfileRow { attribute :>> key="fixed-payload"; attribute :>> scope="Tcl and C-closure constructors in audited source initialize once"; attribute :>> permission="seal managed publication against semantic setter; GC slot relocation still allowed"; attribute :>> boundary="not a deep freeze of the vector/procedure; public bypass not silently accepted"; }
part profile1:ProfileRow { attribute :>> key="mutable-payload"; attribute :>> scope="explicit checked setter compatibility profile"; attribute :>> permission="prepare rooted new value; publish new version synchronously; retain old borrowed version cells"; attribute :>> boundary="do not block a reentrant setter waiting for its own borrower"; }
part profile2:ProfileRow { attribute :>> key="loaded-source"; attribute :>> scope="local Tcl commit cbf86d62348d6b052e1961b4df995960fb21545f"; attribute :>> permission="source-qualified C-call ordering only"; attribute :>> boundary="not installed Tcl identity, Darwin binary ABI or native test evidence"; }
part profile3:ProfileRow { attribute :>> key="nested-native"; attribute :>> scope="native frames may catch errors or invoke old result free callbacks"; attribute :>> permission="preserve causal refusal in native frame ancestry independently of Tcl result"; attribute :>> boundary="normal Gambit free hook is RC release; arbitrary reentry target is an extension hypothesis"; }
part def PathRow { attribute key:String; attribute producer:String; attribute consumer:String; attribute classification:String; attribute missing:String; }
part path0:PathRow { attribute :>> key="registration-read"; attribute :>> producer="tcl-register"; attribute :>> consumer="tcl-native-callback"; attribute :>> classification="actual registered source producer/consumer"; attribute :>> missing="source borrow currently absent"; }
part path1:PathRow { attribute :>> key="delete-payload"; attribute :>> producer="tcl-native-delete"; attribute :>> consumer="tcl-delete"; attribute :>> classification="pinned Tcl delete -> actual Gambit hook"; attribute :>> missing="loaded library correspondence"; }
part path2:PathRow { attribute :>> key="rc-setters"; attribute :>> producer="rc-source-write"; attribute :>> consumer="closure-setter"; attribute :>> classification="plain public store plus explicit constructor callers"; attribute :>> missing="indirect/public postpublication writer closure"; }
part path3:PathRow { attribute :>> key="native-command-setter"; attribute :>> producer="tcl-set-info"; attribute :>> consumer="tcl-get-info"; attribute :>> classification="native bypass/escape capability"; attribute :>> missing="not exercised by audited Gambit adapter"; }
part path4:PathRow { attribute :>> key="result-old-free"; attribute :>> producer="tcl-result-free-hook"; attribute :>> consumer="native-string-free"; attribute :>> classification="old free callback invoked; selected normal free is RC-only"; attribute :>> missing="no observed Scheme reentry from this free hook"; }
part path5:PathRow { attribute :>> key="refusal-error-callback"; attribute :>> producer="tcl-eval-driver"; attribute :>> consumer="tcl-error-export"; attribute :>> classification="real old translator calls Scheme"; attribute :>> missing="checked origin frame/adapter not implemented"; }
part path6:PathRow { attribute :>> key="real-native-smp"; attribute :>> producer="gambit-native-thread"; attribute :>> consumer="gambit-start-thread"; attribute :>> classification="OS-thread creation and processor activation exist"; attribute :>> missing="parallel efficiency and native correctness not established"; }
part path7:PathRow { attribute :>> key="existing-stealing"; attribute :>> producer="gambit-steal"; attribute :>> consumer="gambit-gc-stages"; attribute :>> classification="scheduler stealing and GC phases are real mechanisms"; attribute :>> missing="not a whole-runtime scaling proof"; }
part def RouteRow { attribute component:String; attribute actionName:String; attribute lemma:String; attribute producerAnchor:String; attribute obligationId:String; }
part route0:RouteRow { attribute :>> component="native-scope"; attribute :>> actionName="dispatch_joint_admission.enterNative"; attribute :>> lemma="DispatchJoint.enterNativePreserves"; attribute :>> producerAnchor="tcl-native-dispatch"; attribute :>> obligationId="joint-safety"; }
part route1:RouteRow { attribute :>> component="native-scope"; attribute :>> actionName="dispatch_joint_admission.enterOther"; attribute :>> lemma="DispatchJoint.enterOtherPreserves"; attribute :>> producerAnchor="tcl-native-dispatch"; attribute :>> obligationId="joint-safety"; }
part route2:RouteRow { attribute :>> component="native-scope"; attribute :>> actionName="dispatch_joint_admission.leaveOther"; attribute :>> lemma="DispatchJoint.leaveOtherPreserves"; attribute :>> producerAnchor="tcl-native-dispatch"; attribute :>> obligationId="joint-safety"; }
part route3:RouteRow { attribute :>> component="native-scope"; attribute :>> actionName="dispatch_joint_admission.selectHandle"; attribute :>> lemma="DispatchJoint.selectHandlePreserves"; attribute :>> producerAnchor="tcl-native-dispatch"; attribute :>> obligationId="joint-safety"; }
part route4:RouteRow { attribute :>> component="native-scope"; attribute :>> actionName="dispatch_joint_admission.deleteCommand"; attribute :>> lemma="DispatchJoint.deleteCommandPreserves"; attribute :>> producerAnchor="tcl-native-delete"; attribute :>> obligationId="joint-safety"; }
part route5:RouteRow { attribute :>> component="root-domain"; attribute :>> actionName="dispatch_joint_admission.reserveRoot"; attribute :>> lemma="DispatchJoint.reserveRootPreserves"; attribute :>> producerAnchor="rc-scan"; attribute :>> obligationId="gc-freeze"; }
part route6:RouteRow { attribute :>> component="joint-custody"; attribute :>> actionName="dispatch_joint_admission.rejectBeforeReserve"; attribute :>> lemma="DispatchJoint.rejectBeforeReservePreserves"; attribute :>> producerAnchor="tcl-native-callback"; attribute :>> obligationId="joint-safety"; }
part route7:RouteRow { attribute :>> component="joint-custody"; attribute :>> actionName="dispatch_joint_admission.commitJoint"; attribute :>> lemma="DispatchJoint.commitJointPreserves"; attribute :>> producerAnchor="tcl-native-callback"; attribute :>> obligationId="joint-safety"; }
part route8:RouteRow { attribute :>> component="joint-custody"; attribute :>> actionName="dispatch_joint_admission.rejectReservedDelete"; attribute :>> lemma="DispatchJoint.rejectReservedDeletePreserves"; attribute :>> producerAnchor="tcl-native-callback"; attribute :>> obligationId="joint-safety"; }
part route9:RouteRow { attribute :>> component="joint-custody"; attribute :>> actionName="dispatch_joint_admission.abortPreparation"; attribute :>> lemma="DispatchJoint.abortPreparationPreserves"; attribute :>> producerAnchor="tcl-native-callback"; attribute :>> obligationId="joint-safety"; }
part route10:RouteRow { attribute :>> component="joint-custody"; attribute :>> actionName="dispatch_joint_admission.loseReply"; attribute :>> lemma="DispatchJoint.loseReplyPreserves"; attribute :>> producerAnchor="tcl-native-callback"; attribute :>> obligationId="joint-safety"; }
part route11:RouteRow { attribute :>> component="joint-custody"; attribute :>> actionName="dispatch_joint_admission.resolveReservedAbort"; attribute :>> lemma="DispatchJoint.resolveReservedAbortPreserves"; attribute :>> producerAnchor="tcl-native-callback"; attribute :>> obligationId="joint-safety"; }
part route12:RouteRow { attribute :>> component="joint-custody"; attribute :>> actionName="dispatch_joint_admission.ackCommit"; attribute :>> lemma="DispatchJoint.ackCommitPreserves"; attribute :>> producerAnchor="tcl-native-callback"; attribute :>> obligationId="joint-safety"; }
part route13:RouteRow { attribute :>> component="joint-custody"; attribute :>> actionName="dispatch_joint_admission.readSelected"; attribute :>> lemma="DispatchJoint.readSelectedPreserves"; attribute :>> producerAnchor="tcl-native-callback"; attribute :>> obligationId="joint-safety"; }
part route14:RouteRow { attribute :>> component="joint-custody"; attribute :>> actionName="dispatch_joint_admission.finishUse"; attribute :>> lemma="DispatchJoint.finishUsePreserves"; attribute :>> producerAnchor="tcl-native-callback"; attribute :>> obligationId="joint-safety"; }
part route15:RouteRow { attribute :>> component="joint-custody"; attribute :>> actionName="dispatch_joint_admission.retireBorrow"; attribute :>> lemma="DispatchJoint.retireBorrowPreserves"; attribute :>> producerAnchor="tcl-native-callback"; attribute :>> obligationId="joint-safety"; }
part route16:RouteRow { attribute :>> component="joint-custody"; attribute :>> actionName="dispatch_joint_admission.deliverOutcome"; attribute :>> lemma="DispatchJoint.deliverOutcomePreserves"; attribute :>> producerAnchor="tcl-native-callback"; attribute :>> obligationId="joint-safety"; }
part route17:RouteRow { attribute :>> component="native-scope"; attribute :>> actionName="dispatch_joint_admission.leaveScope"; attribute :>> lemma="DispatchJoint.leaveScopePreserves"; attribute :>> producerAnchor="tcl-native-dispatch"; attribute :>> obligationId="joint-safety"; }
part route18:RouteRow { attribute :>> component="native-scope"; attribute :>> actionName="dispatch_joint_admission.leaveEmptyScope"; attribute :>> lemma="DispatchJoint.leaveEmptyScopePreserves"; attribute :>> producerAnchor="tcl-native-dispatch"; attribute :>> obligationId="joint-safety"; }
part route19:RouteRow { attribute :>> component="root-domain"; attribute :>> actionName="dispatch_joint_admission.removeRoot"; attribute :>> lemma="DispatchJoint.removeRootPreserves"; attribute :>> producerAnchor="rc-scan"; attribute :>> obligationId="gc-freeze"; }
part route20:RouteRow { attribute :>> component="native-scope"; attribute :>> actionName="dispatch_joint_admission.freeStorage"; attribute :>> lemma="DispatchJoint.freeStoragePreserves"; attribute :>> producerAnchor="tcl-native-dispatch"; attribute :>> obligationId="joint-safety"; }
part route21:RouteRow { attribute :>> component="native-scope"; attribute :>> actionName="dispatch_joint_admission.freeControl"; attribute :>> lemma="DispatchJoint.freeControlPreserves"; attribute :>> producerAnchor="tcl-native-dispatch"; attribute :>> obligationId="joint-safety"; }
part route22:RouteRow { attribute :>> component="root-domain"; attribute :>> actionName="dispatch_joint_admission.closeGc"; attribute :>> lemma="DispatchJoint.closeGcPreserves"; attribute :>> producerAnchor="rc-scan"; attribute :>> obligationId="gc-freeze"; }
part route23:RouteRow { attribute :>> component="root-domain"; attribute :>> actionName="dispatch_joint_admission.freezeRoots"; attribute :>> lemma="DispatchJoint.freezeRootsPreserves"; attribute :>> producerAnchor="rc-scan"; attribute :>> obligationId="gc-freeze"; }
part route24:RouteRow { attribute :>> component="root-domain"; attribute :>> actionName="dispatch_joint_admission.beginScan"; attribute :>> lemma="DispatchJoint.beginScanPreserves"; attribute :>> producerAnchor="rc-scan"; attribute :>> obligationId="gc-freeze"; }
part route25:RouteRow { attribute :>> component="root-domain"; attribute :>> actionName="dispatch_joint_admission.endScan"; attribute :>> lemma="DispatchJoint.endScanPreserves"; attribute :>> producerAnchor="rc-scan"; attribute :>> obligationId="gc-freeze"; }
part route26:RouteRow { attribute :>> component="root-domain"; attribute :>> actionName="dispatch_joint_admission.resumeGc"; attribute :>> lemma="DispatchJoint.resumeGcPreserves"; attribute :>> producerAnchor="rc-scan"; attribute :>> obligationId="gc-freeze"; }
part def CompositionRow { attribute key:String; attribute lemma:String; attribute source:String; attribute obligation:String; attribute boundary:String; }
part composition0:CompositionRow { attribute :>> key="source-pin"; attribute :>> lemma="DispatchJointBridge.jointBorrowProvidesSourcePin"; attribute :>> source="tcl-native-callback"; attribute :>> obligation="parent-predicates"; attribute :>> boundary="one fixed payload and matched registration; predicate embedding, not full mutable-version simulation"; }
part composition1:CompositionRow { attribute :>> key="native-refusal"; attribute :>> lemma="DispatchJointBridge.refusalCanRecordNative"; attribute :>> source="tcl-eval-driver"; attribute :>> obligation="parent-predicates"; attribute :>> boundary="definitive refusal can record in an existing valid native eval frame; causal association remains premise"; }
part def MemoryRow { attribute key:String; attribute order:String; attribute premise:String; attribute obligation:String; }
part memory0:MemoryRow { attribute :>> key="outer-first"; attribute :>> order="native scope before lookup; revoke discovery before grace snapshot"; attribute :>> premise="all Tcl thread-affinity and external entry assumptions checked"; attribute :>> obligation="native-owner"; }
part memory1:MemoryRow { attribute :>> key="joint"; attribute :>> order="native handle validation then root reservation then stable commit then payload read"; attribute :>> premise="new scalar read cannot precede confirmed record; no allocation/callout under short mutation lease"; attribute :>> obligation="c23-memory"; }
part memory2:MemoryRow { attribute :>> key="gc"; attribute :>> order="close root admission; drain accepted mutation; freeze slots; update; reopen"; attribute :>> premise="active native scope is storage grace, not a GC worker vote"; attribute :>> obligation="root-scanner-adapter"; }
part memory3:MemoryRow { attribute :>> key="unknown"; attribute :>> order="keep exact reserved/committed state rooted and query ticket"; attribute :>> premise="root-domain finisher can resolve reservation without waiting for a requester blocked on GC"; attribute :>> obligation="stable-finisher"; }
part memory4:MemoryRow { attribute :>> key="retire"; attribute :>> order="known outcome, actual last use, native grace, root unregister, header free, control retirement"; attribute :>> premise="continuation resumption does not itself restore native-frame authority"; attribute :>> obligation="native-last-use"; }
part def GainRow { attribute key:String; attribute benefit:String; attribute cost:String; attribute condition:String; attribute refutation:String; }
part gain0:GainRow { attribute :>> key="scope-amortization"; attribute :>> benefit="M callbacks inside E outer native scopes need E outer grace enter/exit pairs rather than M independent outer protections"; attribute :>> cost="per-callback root/attempt checks still needed; scopes can delay disposal"; attribute :>> condition="E less than M and all lookups enclosed; owner-confined counter is not a shared atomic"; attribute :>> refutation="M approximately E or long scopes erase amortization and retain much metadata"; }
part gain1:GainRow { attribute :>> key="gc-independence"; attribute :>> benefit="GC need not wait for entire native callback lifetimes if their registered source roots remain enumerable"; attribute :>> cost="short root-writer drain and stable root records"; attribute :>> condition="fixed payload and complete root scanner coverage"; attribute :>> refutation="retained raw unregistered values force reject or additional rooting"; }
part gain2:GainRow { attribute :>> key="native-refusal"; attribute :>> benefit="R definitive rejections do not invoke Scheme error translation at this boundary"; attribute :>> cost="typed native delivery and exact attempt receipts"; attribute :>> condition="every outer entry checks causal origin"; attribute :>> refutation="TCL_ERROR or NULL alone does not preserve refusal identity"; }
part gain3:GainRow { attribute :>> key="unknown"; attribute :>> benefit="no blind reissue and no speculative disposal of unknown commits"; attribute :>> cost="Q unresolved attempts retain O(Q) stable records and roots; no unconditional progress bound"; attribute :>> condition="root owner authoritative query/finisher"; attribute :>> refutation="a lost finisher can retain forever or block freeze"; }
part gain4:GainRow { attribute :>> key="thread-progress-choice"; attribute :>> benefit="potentially amortize metadata retirement across many removals"; attribute :>> cost="epoch participation, native handle accounting, grace latency and counter contention"; attribute :>> condition="adopt only after all known-state and unmanaged-reader premises are met"; attribute :>> refutation="Erlang managed-thread guarantee is not available automatically in Gambit"; }
part gain5:GainRow { attribute :>> key="whole-smp"; attribute :>> benefit="leverage existing OS-thread queues/stealing and precise continuation semantics"; attribute :>> cost="GC/FFI/owner redesign and serial overhead need separate accounting"; attribute :>> condition="measure useful ready parallel work and serial span; exclude wrong-profile/config cases"; attribute :>> refutation="adding actors or a language switch alone proves no speedup"; }
part gain6:GainRow { attribute :>> key="lazy-task-materialization"; attribute :>> benefit="for N eligible lazy calls and S materialized splits, N-S calls avoid immediate separate parent-task/placeholder materialization versus eager policy"; attribute :>> cost="marker and strictness checks for N calls plus split/restore and ownership for S splits"; attribute :>> condition="explicit future semantics or proved eligibility; current GVM split and root/continuation refinement open"; attribute :>> refutation="heavy marker/check costs, expensive splits, effect-order change or S close to N can erase gains"; }
part def ContractRow { attribute fromNode:String; attribute toNode:String; attribute custody:String; }
part contract0:ContractRow { attribute :>> fromNode="Feeley native extent"; attribute :>> toNode="Native scope owner"; attribute :>> custody="native frames and Scheme continuation lifetime are different"; }
part contract1:ContractRow { attribute :>> fromNode="Erlang lookup/grace"; attribute :>> toNode="Native scope owner"; attribute :>> custody="learn removal-before-quiescence; do not assume Gambit checkpoints qualify"; }
part contract2:ContractRow { attribute :>> fromNode="OCaml root/access contract"; attribute :>> toNode="GC root domain"; attribute :>> custody="learn stable slot and controlled runtime access; not API substitution"; }
part contract3:ContractRow { attribute :>> fromNode="Native scope owner"; attribute :>> toNode="Tcl lookup and dispatch"; attribute :>> custody="acquire before ClientData selection; interpreter thread owner required"; }
part contract4:ContractRow { attribute :>> fromNode="Tcl lookup and dispatch"; attribute :>> toNode="Joint attempt record"; attribute :>> custody="selected handle identity retained across deletion"; }
part contract5:ContractRow { attribute :>> fromNode="GC root domain"; attribute :>> toNode="Joint attempt record"; attribute :>> custody="short rooted reservation; confirm exact commit before payload read"; }
part contract6:ContractRow { attribute :>> fromNode="Logical deletion"; attribute :>> toNode="Native scope owner"; attribute :>> custody="close new discovery; keep preselected old scopes alive"; }
part contract7:ContractRow { attribute :>> fromNode="GC freeze"; attribute :>> toNode="GC root domain"; attribute :>> custody="drain mutation reservation; active native grace can remain"; }
part contract8:ContractRow { attribute :>> fromNode="Joint attempt record"; attribute :>> toNode="Native outcome ledger"; attribute :>> custody="definitive refusal or exact unknown ticket; no Scheme error retry"; }
part contract9:ContractRow { attribute :>> fromNode="Joint attempt record"; attribute :>> toNode="Retirement"; attribute :>> custody="known delivery, no borrower, native grace, scanner and root retirement"; }
part contract10:ContractRow { attribute :>> fromNode="Actor isolation profile"; attribute :>> toNode="Whole Gambit architecture"; attribute :>> custody="optional transfer restrictions; preserve default shared Scheme semantics"; }
part contract11:ContractRow { attribute :>> fromNode="Existing SMP scheduler"; attribute :>> toNode="Whole Gambit architecture"; attribute :>> custody="reuse real processor threads, queues and stealing; diagnose remaining span"; }
part contract12:ContractRow { attribute :>> fromNode="PVM lazy futures"; attribute :>> toNode="FrameSpec split/steal plan"; attribute :>> custody="only materialize eligible parent continuation when parallelism is used; split/root model open"; }
part contract13:ContractRow { attribute :>> fromNode="FrameSpec split/steal plan"; attribute :>> toNode="Whole Gambit architecture"; attribute :>> custody="potentially lower task overhead; not actor heap isolation and not covered by native-scope proof"; }
part def NeedRow { attribute key:String; attribute status:String; attribute condition:String; }
part need0:NeedRow { attribute :>> key="joint-safety"; attribute :>> status="formal"; attribute :>> condition="borrow requires native scope and rooted domain reservation; no free before old scopes drain"; }
part need1:NeedRow { attribute :>> key="unknown-custody"; attribute :>> status="formal"; attribute :>> condition="unknown reserved and committed states retain their owner; no payload read before confirmation"; }
part need2:NeedRow { attribute :>> key="gc-freeze"; attribute :>> status="formal"; attribute :>> condition="freeze waits short root mutation, not all native scopes; frozen root census unchanged"; }
part need3:NeedRow { attribute :>> key="parent-predicates"; attribute :>> status="formal"; attribute :>> condition="conditional embeddings into actual source-borrow and native-outcome parent ASTs"; }
part need4:NeedRow { attribute :>> key="native-owner"; attribute :>> status="unresolved"; attribute :>> condition="all Tcl eval/event entries and interpreter affinity establish outer scope before lookup"; }
part need5:NeedRow { attribute :>> key="all-lookup-closure"; attribute :>> status="unresolved"; attribute :>> condition="delete/set-info/get-info and external ClientData retainers obey the same registration generation"; }
part need6:NeedRow { attribute :>> key="stable-finisher"; attribute :>> status="unresolved"; attribute :>> condition="reserved unknown outcomes have a non-abandonable root-domain finisher, independent of blocked requester"; }
part need7:NeedRow { attribute :>> key="root-scanner-adapter"; attribute :>> status="unresolved"; attribute :>> condition="real source slot/register/update/retirement paths match frozen manifest for every context"; }
part need8:NeedRow { attribute :>> key="c23-memory"; attribute :>> status="unresolved"; attribute :>> condition="atomic admission/reservation/commit and release/acquire reclamation refine C23"; }
part need9:NeedRow { attribute :>> key="native-last-use"; attribute :>> status="unresolved"; attribute :>> condition="all unwind/continuation/FFI paths supply actual native-frame last-use and target no-use receipts"; }
part need10:NeedRow { attribute :>> key="global-smp-diagnosis"; attribute :>> status="unresolved"; attribute :>> condition="source mechanism census does not establish scaling, fairness, native safety or the user-reported bottleneck"; }
part need11:NeedRow { attribute :>> key="actor-transfer"; attribute :>> status="unresolved"; attribute :>> condition="isolated profile must preserve or explicitly restrict aliases, payload identity and continuation boundaries"; }
part need12:NeedRow { attribute :>> key="future-split"; attribute :>> status="unresolved"; attribute :>> condition="task eligibility, split-point roots and exclusive split/restore ownership require a separate model; current native-scope proof does not discharge it"; }
}
