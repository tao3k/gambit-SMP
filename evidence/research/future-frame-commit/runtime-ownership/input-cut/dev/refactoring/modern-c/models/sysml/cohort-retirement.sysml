package GambitCohortRetirement { private import ScalarValues::*;
part def SourceRow { attribute key:String; attribute path:String; attribute needle:String; attribute limit:String; }
part source0:SourceRow { attribute :>> key="shrink-admission"; attribute :>> path="vendor/gambit/lib/_mem/capacity-resize.inc"; attribute :>> needle="if (head->next != head)"; attribute :>> limit="reject nonempty RC domain; no general handoff inferred"; }
part source1:SourceRow { attribute :>> key="shrink-join"; attribute :>> path="vendor/gambit/lib/setup.c"; attribute :>> needle="___transfer_retired_still (ps, ___ps);"; attribute :>> limit="only after known successful thread_join"; }
part source2:SourceRow { attribute :>> key="retained-join"; attribute :>> path="vendor/gambit/lib/setup.c"; attribute :>> needle="r->slots[i].phase = ___RESIZE_SLOT_RETAINED;"; attribute :>> limit="join failure retains resources; no termination proof"; }
part source3:SourceRow { attribute :>> key="old-roster"; attribute :>> path="vendor/gambit/lib/setup.c"; attribute :>> needle="old-set commit, matching OP_SET_PROCESSOR_COUNT"; attribute :>> limit="departing thread uses committed count before exit"; }
part source4:SourceRow { attribute :>> key="still-transfer"; attribute :>> path="vendor/gambit/lib/_mem/capacity-resize.inc"; attribute :>> needle="retirement is not object death."; attribute :>> limit="successful join and closed collective are stated preconditions"; }
part source5:SourceRow { attribute :>> key="cleanup-api"; attribute :>> path="vendor/gambit/lib/setup.c"; attribute :>> needle="___GSTATE->___cleanup_pstate"; attribute :>> limit="public function-table access; internal caller census not external closure"; }
part source6:SourceRow { attribute :>> key="root-domain-cleanup"; attribute :>> path="vendor/gambit/lib/_mem/memory-lifecycle.inc"; attribute :>> needle="prepare_rc_cleanup (___ps);"; attribute :>> limit="then still cleanup, RC cleanup and gate destruction"; }
part source7:SourceRow { attribute :>> key="setup-failure"; attribute :>> path="vendor/gambit/lib/setup.c"; attribute :>> needle="if ((err = setup_sync_op_pstate (___ps))"; attribute :>> limit="unpublished initialization failure is distinct from live worker shrink"; }
part source8:SourceRow { attribute :>> key="whole-vm-cleanup"; attribute :>> path="vendor/gambit/lib/setup.c"; attribute :>> needle="VM cleanup retained resize resources"; attribute :>> limit="global shutdown refuses retained resize, not full external observer grace"; }
part source9:SourceRow { attribute :>> key="previous-grace"; attribute :>> path="dev/refactoring/modern-c/models/quint/rc_reader_grace.qnt"; attribute :>> needle="action confirmCohortDrain="; attribute :>> limit="abstract physical-drain permit refined here; not implemented counter service"; }
part def ObligationRow { attribute key:String; attribute status:String; attribute condition:String; }
part obligation0:ObligationRow { attribute :>> key="cohort-safety"; attribute :>> status="conditional-model"; attribute :>> condition="closed admission; normal drain; known worker termination; zero exported observers"; }
part obligation1:ObligationRow { attribute :>> key="internal-shrink"; attribute :>> status="source-bound"; attribute :>> condition="actual old-set commit, native thread exit, successful join then transfer and cleanup"; }
part obligation2:ObligationRow { attribute :>> key="external-api"; attribute :>> status="unresolved"; attribute :>> condition="public cleanup and foreign pointer readers require stable enclosing VM authority"; }
part obligation3:ObligationRow { attribute :>> key="native-drain"; attribute :>> status="unresolved"; attribute :>> condition="all claims, descendants and abnormal exits covered by effective collective"; }
part obligation4:ObligationRow { attribute :>> key="native-join"; attribute :>> status="unresolved"; attribute :>> condition="successful join adapter and cancellation/exception landing qualified on selected target"; }
part obligation5:ObligationRow { attribute :>> key="c23-refinement"; attribute :>> status="unresolved"; attribute :>> condition="memory orders, generation and native width correspondence"; }
part def RouteRow { attribute actionName:String; attribute lemma:String; attribute source:String; attribute obligation:String; }
part route0:RouteRow { attribute :>> actionName="enterLookup"; attribute :>> lemma="CohortRetirement.enterLookupPreserves"; attribute :>> source="old-roster"; attribute :>> obligation="cohort-safety"; }
part route1:RouteRow { attribute :>> actionName="exitLookup"; attribute :>> lemma="CohortRetirement.exitLookupPreserves"; attribute :>> source="old-roster"; attribute :>> obligation="cohort-safety"; }
part route2:RouteRow { attribute :>> actionName="acquireExternal"; attribute :>> lemma="CohortRetirement.acquireExternalPreserves"; attribute :>> source="old-roster"; attribute :>> obligation="cohort-safety"; }
part route3:RouteRow { attribute :>> actionName="returnExternal"; attribute :>> lemma="CohortRetirement.returnExternalPreserves"; attribute :>> source="old-roster"; attribute :>> obligation="cohort-safety"; }
part route4:RouteRow { attribute :>> actionName="closeRoster"; attribute :>> lemma="CohortRetirement.closeRosterPreserves"; attribute :>> source="old-roster"; attribute :>> obligation="cohort-safety"; }
part route5:RouteRow { attribute :>> actionName="escapeScanner"; attribute :>> lemma="CohortRetirement.escapeScannerPreserves"; attribute :>> source="old-roster"; attribute :>> obligation="cohort-safety"; }
part route6:RouteRow { attribute :>> actionName="collectiveDrain"; attribute :>> lemma="CohortRetirement.collectiveDrainPreserves"; attribute :>> source="old-roster"; attribute :>> obligation="cohort-safety"; }
part route7:RouteRow { attribute :>> actionName="exitWorker"; attribute :>> lemma="CohortRetirement.exitWorkerPreserves"; attribute :>> source="shrink-join"; attribute :>> obligation="cohort-safety"; }
part route8:RouteRow { attribute :>> actionName="joinUnknown"; attribute :>> lemma="CohortRetirement.joinUnknownPreserves"; attribute :>> source="retained-join"; attribute :>> obligation="cohort-safety"; }
part route9:RouteRow { attribute :>> actionName="joinKnown"; attribute :>> lemma="CohortRetirement.joinKnownPreserves"; attribute :>> source="shrink-join"; attribute :>> obligation="cohort-safety"; }
part route10:RouteRow { attribute :>> actionName="retireDomain"; attribute :>> lemma="CohortRetirement.retireDomainPreserves"; attribute :>> source="shrink-join"; attribute :>> obligation="cohort-safety"; }
part def GainRow { attribute key:String; attribute saved:String; attribute added:String; attribute condition:String; attribute status:String; }
part gain0:GainRow { attribute :>> key="closed-internal-readers"; attribute :>> saved="0 added per-lookup RMW if all internal readers remain in closed collective"; attribute :>> added="existing barriers and join retained"; attribute :>> condition="complete internal synchronous scope; no exported lookup"; attribute :>> status="conditional"; }
part gain1:GainRow { attribute :>> key="shrink-domain"; attribute :>> saved="reuse existing RC-empty rejection; no RC migration needed for admitted shrink"; attribute :>> added="nonempty RC domains remain ineligible until real handoff exists"; attribute :>> condition="existing can_retire_pstate plus known join"; attribute :>> status="source-bound"; }
part gain2:GainRow { attribute :>> key="exported-readers"; attribute :>> saved="no universal hazard scheme forced on synchronous internal users"; attribute :>> added="O(A) enrolled observer leases for A exported readers or explicit refusal"; attribute :>> condition="stable admission anchor before first VM/task load"; attribute :>> status="unresolved-native"; }
part gain3:GainRow { attribute :>> key="failed-join"; attribute :>> saved="0 speculative cleanups or gate destruction after unknown join"; attribute :>> added="retained worker/VM/native resources; unbounded retention possible"; attribute :>> condition="unknown is not worker termination"; attribute :>> status="conditional-model"; }
part gain4:GainRow { attribute :>> key="retirement"; attribute :>> saved="0 runtime paths retired by formal checks"; attribute :>> added="unify typed cleanup preconditions across live shrink and private setup rollback"; attribute :>> condition="native all-callers and abnormal-exit refinements"; attribute :>> status="design-only"; }
part def IssuerRow { attribute key:String; attribute source:String; attribute signature:String; attribute gap:String; }
part issuer0:IssuerRow { attribute :>> key="roster-coordinator"; attribute :>> source="old-roster"; attribute :>> signature="old roster commit before departing thread exit"; attribute :>> gap="external entrants not inherently closed"; }
part issuer1:IssuerRow { attribute :>> key="native-join-owner"; attribute :>> source="shrink-join"; attribute :>> signature="successful join witnesses departing OS-thread termination"; attribute :>> gap="does not witness external thread or callback retirement"; }
part issuer2:IssuerRow { attribute :>> key="storage-owner"; attribute :>> source="still-transfer"; attribute :>> signature="transfer surviving still list and accounting before context cleanup"; attribute :>> gap="RC and effectful domains rejected by current shrink admission"; }
part issuer3:IssuerRow { attribute :>> key="vm-api-owner"; attribute :>> source="cleanup-api"; attribute :>> signature="stable VM entry permit before public cleanup and first pointer load"; attribute :>> gap="current public ABI does not supply composed receipt"; }
part issuer4:IssuerRow { attribute :>> key="retained-custodian"; attribute :>> source="retained-join"; attribute :>> signature="keep old native/storage identity on unknown join or escaped scan"; attribute :>> gap="recovery and liveness not established"; }
part def ConsumerRow { attribute key:String; attribute source:String; attribute access:String; attribute lifetime:String; attribute limit:String; }
part consumer0:ConsumerRow { attribute :>> key="live-shrink"; attribute :>> source="shrink-join"; attribute :>> access="old-set commit -> exit -> join -> still transfer -> cleanup"; attribute :>> lifetime="departing worker known dead; remaining roster lives"; attribute :>> limit="other native readers need separate closure"; }
part consumer1:ConsumerRow { attribute :>> key="abort-growth"; attribute :>> source="retained-join"; attribute :>> access="abort entry then join created threads; cleanup initialized slots only if joins known"; attribute :>> lifetime="unpublished contexts and retained native entry records"; attribute :>> limit="unknown create/published contexts are not private rollback"; }
part consumer2:ConsumerRow { attribute :>> key="setup-rollback"; attribute :>> source="setup-failure"; attribute :>> access="cleanup after failed sync initialization before successful setup return"; attribute :>> lifetime="exclusive unpublished setup lifetime"; attribute :>> limit="must prove no custom callback published it"; }
part consumer3:ConsumerRow { attribute :>> key="global-shutdown"; attribute :>> source="whole-vm-cleanup"; attribute :>> access="shrink to one; reject retained requests; cleanup current pstate and VM"; attribute :>> lifetime="setup/VM lifecycle owner"; attribute :>> limit="public foreign users and reentry still unresolved"; }
part consumer4:ConsumerRow { attribute :>> key="public-cleanup"; attribute :>> source="cleanup-api"; attribute :>> access="function pointers exported in global table"; attribute :>> lifetime="caller must provide enclosing lifetime and exclusivity"; attribute :>> limit="internal grep is not external caller closure"; }
part def EdgeRow { attribute fromNode:String; attribute toNode:String; attribute contract:String; }
part edge0:EdgeRow { attribute :>> fromNode="Old roster"; attribute :>> toNode="Closed collective"; attribute :>> contract="close membership and drain internal readers / descendants"; }
part edge1:EdgeRow { attribute :>> fromNode="Closed collective"; attribute :>> toNode="Worker exit"; attribute :>> contract="departing thread exits before native cleanup"; }
part edge2:EdgeRow { attribute :>> fromNode="Worker exit"; attribute :>> toNode="Known join"; attribute :>> contract="one OS-thread termination receipt"; }
part edge3:EdgeRow { attribute :>> fromNode="Known join"; attribute :>> toNode="Storage handoff"; attribute :>> contract="transfer still objects and accounting; require RC admission"; }
part edge4:EdgeRow { attribute :>> fromNode="Storage handoff"; attribute :>> toNode="Domain retirement"; attribute :>> contract="also close and drain exported observers"; }
part edge5:EdgeRow { attribute :>> fromNode="Unknown join / escaped scanner"; attribute :>> toNode="Retained custody"; attribute :>> contract="no cleanup or gate reuse; no invented completion"; }
part edge6:EdgeRow { attribute :>> fromNode="Public cleanup API"; attribute :>> toNode="External entry authority"; attribute :>> contract="first metadata load must already be safe"; }
}
