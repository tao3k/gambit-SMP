package GambitForceMaintenanceFidelity { private import ScalarValues::*;
part def Route { attribute key:String; attribute sourcePath:String; attribute needle:String; attribute obligation:String; }
part route0:Route { attribute :>> key="force-emitter"; attribute :>> sourcePath="vendor/gambit/gsc/_t-c-2.scm"; attribute :>> needle="(define (targ-apply-force)"; attribute :>> obligation="Emit internal return descriptor between FORCE1 and FORCE2; FORCE3 materializes result into declared destination"; }
part route1:Route { attribute :>> key="force-transfer"; attribute :>> sourcePath="vendor/gambit/lib/_kernel.scm"; attribute :>> needle="promise = ___ps->temp2;"; attribute :>> obligation="Save caller registers and actual return; transfer promise to PUSH_ARGS1 before Scheme can collect"; }
part route2:Route { attribute :>> key="thunk-call"; attribute :>> sourcePath="vendor/gambit/lib/_kernel.scm"; attribute :>> needle="(define-prim (##force-out-of-line promise)"; attribute :>> obligation="Thunk enables interrupts; promise must remain in ordinary roots; do not pin mutable promise state as immutable"; }
part route3:Route { attribute :>> key="restore-result"; attribute :>> sourcePath="vendor/gambit/lib/_kernel.scm"; attribute :>> needle="___ps->temp2 = ___R1;"; attribute :>> obligation="Save result before POP_REGS overwrites R1; reload at FORCE2 before any safepoint"; }
part route4:Route { attribute :>> key="force-macros"; attribute :>> sourcePath="vendor/gambit/include/gambit.h.in"; attribute :>> needle="#define ___FORCE2 ___temp=___ps->temp2;}}"; attribute :>> obligation="temp2 is a transient transfer slot; no direct GC registration inferred"; }
part route5:Route { attribute :>> key="stored-thunk"; attribute :>> sourcePath="vendor/gambit/lib/_kernel.c"; attribute :>> needle="___SET_R2(___PROMISESTATE(___STK(-6)))"; attribute :>> obligation="Stored generated code preserves promise in STK across thunk and POLL; native/configuration provenance open"; }
part route6:Route { attribute :>> key="stored-consumer"; attribute :>> sourcePath="vendor/gambit/lib/_std.c"; attribute :>> needle="___SET_R1(___FORCE3)"; attribute :>> obligation="Stored force entry immediately materializes result and returns; other destinations need complete audit"; }
part route7:Route { attribute :>> key="register-roots"; attribute :>> sourcePath="vendor/gambit/lib/mem.c"; attribute :>> needle="mark_array (___PSP ___ps->r,"; attribute :>> obligation="Ordinary register roots are rewritten by collector; PSTATE temp slots are not automatically included"; }
part route8:Route { attribute :>> key="descriptor-reader"; attribute :>> sourcePath="vendor/gambit/lib/mem.c"; attribute :>> needle="___RETI_GET_FS_LINK_GCMAP(actual_ra"; attribute :>> obligation="Scanner needs old actual return and descriptor under maintenance authorization"; }
part route9:Route { attribute :>> key="unload"; attribute :>> sourcePath="vendor/gambit/lib/os_dyn.c"; attribute :>> needle="dlclose (p->descr);"; attribute :>> obligation="Existing global cleanup is not a per-cohort two-gate grace protocol"; }
part def Contract { attribute key:String; attribute owner:String; attribute actionName:String; attribute invariant:String; attribute gap:String; }
part contract0:Contract { attribute :>> key="root-transfer"; attribute :>> owner="semantic/native"; attribute :>> actionName="saveCaller transferPromise"; attribute :>> invariant="Every collecting edge has live promise/result in declared movable roots"; attribute :>> gap="All generated destinations and effective target macros unproved"; }
part contract1:Contract { attribute :>> key="return-window"; attribute :>> owner="control/native"; attribute :>> actionName="saveResult restoreCaller consumeForce"; attribute :>> invariant="No collection or reentry while sole force-result carrier is temp2"; attribute :>> gap="Asynchronous suspension and native exits require effective-configuration refinement"; }
part contract2:Contract { attribute :>> key="maintenance-grant"; attribute :>> owner="roots/collector"; attribute :>> actionName="reserve enter"; attribute :>> invariant="Reserve before dereference; old root dependency authorizes scanning after external close"; attribute :>> gap="Root producer closure and generation ABA proof open"; }
part contract3:Contract { attribute :>> key="maintenance-close"; attribute :>> owner="release/roots"; attribute :>> actionName="rootCut closeMaintenance derive"; attribute :>> invariant="Cut independent publishers; admitted reservations and inherited child debt remain owned after cut"; attribute :>> gap="Visibility alone is insufficient; complete source producer list open"; }
part contract4:Contract { attribute :>> key="final-read"; attribute :>> owner="release/native"; attribute :>> actionName="lastRead retire"; attribute :>> invariant="Final metadata access happens before lease decrement; unknown debt retained"; attribute :>> gap="C11 last release to final acquire and loader hooks unproved"; }
part contract5:Contract { attribute :>> key="extraction"; attribute :>> owner="build/modeling"; attribute :>> actionName="extract admittedMeaning"; attribute :>> invariant="Successful resolved integer extraction preserves Option-valued meaning"; attribute :>> gap="JSON to resolved typed tree and remaining operators remain trusted"; }
part def Obligation { attribute key:String; attribute status:String; attribute scope:String; attribute counterexample:String; }
part obligation0:Obligation { attribute :>> key="integer-structural"; attribute :>> status="conditional-proved"; attribute :>> scope="Resolved integer literals fields addition and refusal; theorem extractionMeaning"; attribute :>> counterexample="Same spelling different binding index invalidates premise"; }
part obligation1:Obligation { attribute :>> key="return-value"; attribute :>> status="conditional-proved"; attribute :>> scope="Abstract save restore consume with no intervening moving collection"; attribute :>> counterexample="Moving result without rewriting temp2 gives stale value"; }
part obligation2:Obligation { attribute :>> key="lease-history"; attribute :>> status="bounded-checked"; attribute :>> scope="Two readers; reservation transfer; inherited child after close; late completion; unknown retained"; attribute :>> counterexample="Uncounted late reader after retirement breaks safe"; }
part obligation3:Obligation { attribute :>> key="json-binding"; attribute :>> status="open"; attribute :>> scope="Definition and variable IDs scope table types and duplicate definition rejection"; attribute :>> counterexample="Name-only dictionary can collapse distinct definitions"; }
part obligation4:Obligation { attribute :>> key="action-fidelity"; attribute :>> status="open"; attribute :>> scope="All selected boolean/update/choice syntax must relate actual typed IR to Lean AST"; attribute :>> counterexample="Sequential RHS or disabled branch retaining writes changes relation"; }
part obligation5:Obligation { attribute :>> key="source-c11"; attribute :>> status="open"; attribute :>> scope="Real safepoints aliases generation pin and loader final use"; attribute :>> counterexample="Acquire on unrelated counter does not synchronize publication"; }
part obligation6:Obligation { attribute :>> key="native-provenance"; attribute :>> status="open"; attribute :>> scope="Stored C effective Darwin macros object descriptors and platform lifetime"; attribute :>> counterexample="Stored C presence alone cannot attest loaded binary"; }
part def Gain { attribute key:String; attribute avoided:String; attribute added:String; attribute condition:String; }
part gain0:Gain { attribute :>> key="force-contract"; attribute :>> avoided="One hidden temp-slot ownership assumption per unsafe lowering edge"; attribute :>> added="Explicit root-transfer and no-safepoint annotation validation"; attribute :>> condition="Zero scan savings credited; remove old macros only when all consumers migrate"; }
part gain1:Gain { attribute :>> key="maintenance"; attribute :>> avoided="Premature unload or permanent blanket block on GC after external close"; attribute :>> added="One reservation and one reader ownership transfer per scan grant; final release per completion"; attribute :>> condition="Amortize per scan task or descriptor batch only under immutable cohort lifetime"; }
part gain2:Gain { attribute :>> key="retention"; attribute :>> avoided="Duplicate installed cohorts when actual last-use proof becomes available"; attribute :>> added="Retained bytes sum of live and unknown code/descriptor cohorts"; attribute :>> condition="No finite memory bound if raw aliases or unknown outcomes persist"; }
part gain3:Gain { attribute :>> key="incremental"; attribute :>> avoided="Unnecessary downstream rebuild when consumed ABI projection is unchanged"; attribute :>> added="Separate code content key descriptor ABI key extractor schema key and installed cohort generation"; attribute :>> condition="ABI changes invalidate actual consumers; no measured speedup"; }
part gain4:Gain { attribute :>> key="language-choice"; attribute :>> avoided="No duplicate Zig runtime or C compatibility support introduced"; attribute :>> added="Modern C generator and shared root/lifetime contract remain required"; attribute :>> condition="This research establishes no additional Zig benefit; mandatory runtime work is shared"; }
part history:GambitAssuranceRouting::ModelNeed { ref part :>> owner=GambitBuildAssurance::planner.component; attribute :>> obligationId="FM-H"; attribute :>> kind="interleaving"; attribute :>> subjectPath="dev/refactoring/modern-c/models/quint/force_maintenance.qnt"; attribute :>> subjectScope="Atomic dual-gate root-cut and reservation-reader custody finite relation"; attribute :>> premise="Abstract resolved trees and atomic protocol only; source and native unqualified"; }
part induction:GambitAssuranceRouting::ModelNeed { ref part :>> owner=GambitBuildAssurance::planner.component; attribute :>> obligationId="FM-I"; attribute :>> kind="induction"; attribute :>> subjectPath="dev/refactoring/modern-c/models/lean/ForceMaintenanceFidelity.lean"; attribute :>> subjectScope="Resolved integer extraction meaning and conditional force-result and custody lemmas"; attribute :>> premise="Abstract resolved trees and atomic protocol only; source and native unqualified"; }
part source:GambitAssuranceRouting::ModelNeed { ref part :>> owner=GambitBuildAssurance::planner.component; attribute :>> obligationId="FM-S"; attribute :>> kind="source-refinement"; attribute :>> subjectPath="dev/refactoring/modern-c/force-maintenance-fidelity-design.org"; attribute :>> subjectScope="Force roots full source closure and actual typed-IR extraction OPEN"; attribute :>> premise="Abstract resolved trees and atomic protocol only; source and native unqualified"; }
part platform:GambitAssuranceRouting::ModelNeed { ref part :>> owner=GambitBuildAssurance::planner.component; attribute :>> obligationId="FM-E"; attribute :>> kind="environment-refinement"; attribute :>> subjectPath="dev/refactoring/modern-c/force-maintenance-fidelity-design.org"; attribute :>> subjectScope="C11 effective Darwin macros loader and native provenance OPEN"; attribute :>> premise="Abstract resolved trees and atomic protocol only; source and native unqualified"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitRetiOfdSemantics::source; }
part def FormalBinding { attribute key:String; attribute qntAction:String; attribute leanLemma:String; attribute refinement:String; }
part binding0:FormalBinding { attribute :>> key="reserved-custody"; attribute :>> qntAction="reserve"; attribute :>> leanLemma="reservationBlocks"; attribute :>> refinement="Debt field projection exists conceptually; whole QNT step induction OPEN"; }
part binding1:FormalBinding { attribute :>> key="handoff"; attribute :>> qntAction="enter"; attribute :>> leanLemma="reservationTransferConserves"; attribute :>> refinement="Conditional Nat arithmetic; atomic-action C11 implementation OPEN"; }
part binding2:FormalBinding { attribute :>> key="unknown-retention"; attribute :>> qntAction="loseOutcome"; attribute :>> leanLemma="unknownBlocks"; attribute :>> refinement="Unknown blocks reclaim; recovery and eventual settlement OPEN"; }
}
