package GambitSfunOwnerUseClosure { private import ScalarValues::*;
part def Owner { attribute componentId:String; }
part controlOwner:Owner { attribute :>> componentId="control"; }
part rootsOwner:Owner { attribute :>> componentId="roots"; }
part def SourceRow { attribute key:String; attribute path:String; attribute needle:String; attribute obligation:String; }
part source0:SourceRow { attribute :>> key="sfun-maker"; attribute :>> path="vendor/gambit/include/_gambit/foreign_conversion.h.in"; attribute :>> needle="#define ___BEGIN_SFUN(proc,decl)"; attribute :>> obligation="one owner reference per SFUN admission"; }
part source1:SourceRow { attribute :>> key="void-loop"; attribute :>> path="vendor/gambit/include/_gambit/foreign_conversion.h.in"; attribute :>> needle="#define ___SFUN_ERROR_VOID while"; attribute :>> obligation="loop exists but no result converter"; }
part source2:SourceRow { attribute :>> key="scm-loop"; attribute :>> path="vendor/gambit/include/_gambit/foreign_conversion.h.in"; attribute :>> needle="#define ___SFUN_ERROR_SCMOBJ while"; attribute :>> obligation="direct Scheme result does not set conversion error"; }
part source3:SourceRow { attribute :>> key="typed-loop"; attribute :>> path="vendor/gambit/include/_gambit/foreign_conversion.h.in"; attribute :>> needle="#define ___SFUN_ERROR while"; attribute :>> obligation="typed result is converted after handler return"; }
part source4:SourceRow { attribute :>> key="sfun-finalizer"; attribute :>> path="vendor/gambit/include/_gambit/foreign_conversion.h.in"; attribute :>> needle="#define ___END_SFUN } ___EXT(___kill_sfun_stack_marker) (___marker);"; attribute :>> obligation="local final-use location after while and before propagation"; }
part source5:SourceRow { attribute :>> key="body-no-catcher"; attribute :>> path="vendor/gambit/include/_gambit/foreign_conversion.h.in"; attribute :>> needle="#define ___BEGIN_SFUN_BODY"; attribute :>> obligation="ordinary wrapper is not an unwind catcher"; }
part source6:SourceRow { attribute :>> key="conversion-s32"; attribute :>> path="vendor/gambit/include/_gambit/foreign_conversion.h.in"; attribute :>> needle="#define ___BEGIN_SFUN_SCMOBJ_TO_S32(s,c)"; attribute :>> obligation="return converter writes err"; }
part source7:SourceRow { attribute :>> key="scheme-result"; attribute :>> path="vendor/gambit/include/_gambit/foreign_conversion.h.in"; attribute :>> needle="#define ___SFUN_RESULT ___PSR1"; attribute :>> obligation="read Scheme result before conversion"; }
part source8:SourceRow { attribute :>> key="cfun-catcher"; attribute :>> path="vendor/gambit/include/_gambit/foreign_conversion.h.in"; attribute :>> needle="#define ___BEGIN_CFUN_BODY_CLEANUP ___W_ALL_INL ___BEGIN_TRY"; attribute :>> obligation="intermediate cleanup catcher is not global owner closure"; }
part source9:SourceRow { attribute :>> key="catcher-restore"; attribute :>> path="vendor/gambit/include/_gambit/foreign_conversion.h.in"; attribute :>> needle="#define ___END_TRY } ___ps->catcher = ___old_catcher; }"; attribute :>> obligation="record caught frame separately from restored current catcher"; }
part source10:SourceRow { attribute :>> key="generator-conversion"; attribute :>> path="vendor/gambit/gsc/_ptree2.scm"; attribute :>> needle="(define (c-set-result sfun? result-typ)"; attribute :>> obligation="typed, void and Scheme-object classification"; }
part source11:SourceRow { attribute :>> key="generator-loop"; attribute :>> path="vendor/gambit/gsc/_ptree2.scm"; attribute :>> needle="\"SFUN_ERROR_SCMOBJ\""; attribute :>> obligation="generator chooses loop and emits another c-set-result"; }
part source12:SourceRow { attribute :>> key="generator-body"; attribute :>> path="vendor/gambit/gsc/_ptree2.scm"; attribute :>> needle="c-id-prefix \"BEGIN_SFUN_BODY\" nl-str"; attribute :>> obligation="real c-define wrapper producer"; }
part source13:SourceRow { attribute :>> key="generator-arg-cleanup"; attribute :>> path="vendor/gambit/gsc/_ptree2.scm"; attribute :>> needle="(define (c-convert-argument sfun? numbered-typ body)"; attribute :>> obligation="argument conversion and cleanup wrap the body"; }
part source14:SourceRow { attribute :>> key="handler-input"; attribute :>> path="vendor/gambit/lib/_kernel.scm"; attribute :>> needle="___VECTORELEM(___ps->temp3, 0)) /* arg 3 = procedure */"; attribute :>> obligation="same marker preserves procedure until owner closes"; }
part source15:SourceRow { attribute :>> key="handler-default"; attribute :>> path="vendor/gambit/lib/_kernel.scm"; attribute :>> needle="___PRMCELL(___G__23__23_raise_2d_sfun_2d_conversion_2d_exception.prm))"; attribute :>> obligation="default path raises Scheme exception"; }
part source16:SourceRow { attribute :>> key="scheme-raise"; attribute :>> path="vendor/gambit/lib/_kernel.scm"; attribute :>> needle="(define-prim (##raise-sfun-conversion-exception code message proc)"; attribute :>> obligation="typed Scheme exception producer"; }
part source17:SourceRow { attribute :>> key="dynamic-handler"; attribute :>> path="vendor/gambit/lib/_thread#.scm"; attribute :>> needle="((macro-current-exception-handler) obj)"; attribute :>> obligation="raise can return or transfer Scheme control"; }
part source18:SourceRow { attribute :>> key="exception-catcher"; attribute :>> path="vendor/gambit/lib/_thread.scm"; attribute :>> needle="(##continuation-graft cont catcher exc)"; attribute :>> obligation="Scheme handler transfer is not automatically native exit"; }
part source19:SourceRow { attribute :>> key="no-winding"; attribute :>> path="vendor/gambit/lib/_thread.scm"; attribute :>> needle="(define-prim ##continuation-graft-no-winding"; attribute :>> obligation="wind hooks do not cover all restoration"; }
part source20:SourceRow { attribute :>> key="marker-owner-check"; attribute :>> path="vendor/gambit/lib/_kernel.scm"; attribute :>> needle="/* not the same processor that created frame */"; attribute :>> obligation="owner affinity still required"; }
part source21:SourceRow { attribute :>> key="marker-live-check"; attribute :>> path="vendor/gambit/lib/_kernel.scm"; attribute :>> needle="/* not first return */"; attribute :>> obligation="expired native return is rejected"; }
part source22:SourceRow { attribute :>> key="call-marker-match"; attribute :>> path="vendor/gambit/lib/setup.c"; attribute :>> needle="stack_marker != ___ps->context->fp[___FRAME_SPACE(2)-2]"; attribute :>> obligation="current catch compares marker, not captured invocation epoch"; }
part source23:SourceRow { attribute :>> key="call-normal-status"; attribute :>> path="vendor/gambit/lib/setup.c"; attribute :>> needle="___PSR0 = ___ps->context->fp[-1];\n\n  return ___FIX(___NO_ERR);"; attribute :>> obligation="scoped ___call return control-flow review; other functions also use this literal"; }
part source24:SourceRow { attribute :>> key="native-propagate"; attribute :>> path="vendor/gambit/lib/setup.c"; attribute :>> needle="___EXP_FUNC(void,___propagate_error)"; attribute :>> obligation="nonzero error throws; it is after local marker cleanup"; }
part source25:SourceRow { attribute :>> key="marker-allocation"; attribute :>> path="vendor/gambit/lib/c_intf.c"; attribute :>> needle="stack_marker = ___make_vector (___ps, 2, ___FAL);"; attribute :>> obligation="constructor failure creates no successfully owned marker"; }
part source26:SourceRow { attribute :>> key="marker-reload"; attribute :>> path="vendor/gambit/lib/c_intf.c"; attribute :>> needle="proc_or_false = *proc_root; /* reload after allocating the marker */"; attribute :>> obligation="allocating bootstrap needs rooted procedure"; }
part source27:SourceRow { attribute :>> key="marker-kill"; attribute :>> path="vendor/gambit/lib/c_intf.c"; attribute :>> needle="___VECTORELEM(marker, 0) = ___FAL; /* invalidate the C stack frame */"; attribute :>> obligation="invalidation and native count release have different effects"; }
part source28:SourceRow { attribute :>> key="physical-count"; attribute :>> path="vendor/gambit/lib/_mem/still-refcount.inc"; attribute :>> needle="___BODY0(obj)[___STILL_REFCOUNT-___STILL_BODY]--;"; attribute :>> obligation="plain decrement cannot be retried"; }
part source29:SourceRow { attribute :>> key="root-slots"; attribute :>> path="vendor/gambit/lib/_mem/root-origins.inc"; attribute :>> needle="mark_array (work, context->r, sizeof(context->r)/sizeof(*context->r));"; attribute :>> obligation="logical root lease does not enumerate every slot"; }
part source30:SourceRow { attribute :>> key="saved-roots"; attribute :>> path="vendor/gambit/lib/_mem/root-origins.inc"; attribute :>> needle="mark_array (work, context->saved, sizeof(context->saved)/sizeof(*context->saved));"; attribute :>> obligation="captured and resumed contexts need their own roots"; }
part source31:SourceRow { attribute :>> key="example-typed"; attribute :>> path="vendor/gambit/examples/pthread/mylib.scm"; attribute :>> needle="(c-define (get-counter c) (counter) int \"get_counter\" \"\""; attribute :>> obligation="real general-return c-define entry"; }
part source32:SourceRow { attribute :>> key="example-direct"; attribute :>> path="vendor/gambit/examples/pthread/mylib.scm"; attribute :>> needle="(c-define (new-counter) () scheme-object \"new_counter\" \"\""; attribute :>> obligation="real direct-result entry"; }
part source33:SourceRow { attribute :>> key="example-void"; attribute :>> path="vendor/gambit/examples/pthread/mylib.scm"; attribute :>> needle="(c-define (release-counter c) (counter) void \"release_counter\" \"\""; attribute :>> obligation="real void entry"; }
part source34:SourceRow { attribute :>> key="example-apply"; attribute :>> path="vendor/gambit/examples/tcltk/tcltk.scm"; attribute :>> needle="(let ((result (##apply proc args)))"; attribute :>> obligation="arbitrary Scheme callback; wrapper normalizes result to string or false"; }
part source35:SourceRow { attribute :>> key="paper-fulltext"; attribute :>> path="evidence/research/source-references/feeley-sfp/8bb2fae8ae4b54d3a86206596f90e9cf73da39846af0f39244a476074cf81ed4.txt"; attribute :>> needle="3   Approa h 2:"; attribute :>> obligation="official primary paper local extraction; missing glyphs retained"; }
part def RoleRow { attribute key:String; attribute identity:String; attribute retirement:String; attribute boundary:String; }
part role0:RoleRow { attribute :>> key="MarkerOwner"; attribute :>> identity="OwnerId/incarnation plus one native ownership obligation"; attribute :>> retirement="Only after normal final-use closure or authenticated abandoned-subtree exit"; attribute :>> boundary="Distinct from each ___call and from captured Scheme frame origin"; }
part role1:RoleRow { attribute :>> key="Invocation"; attribute :>> identity="OwnerId plus active monotone InvocationEpoch and native frame id"; attribute :>> retirement="Complete current invocation; do not revoke owner at each return"; attribute :>> boundary="A historical Scheme frame may return through the currently active same-owner call"; }
part role2:RoleRow { attribute :>> key="ClosureReceipt"; attribute :>> identity="OwnerId/incarnation, FinalUseEpoch, converter plan, root/code bindings, mode"; attribute :>> retirement="Stable immutable record, publication before reply"; attribute :>> boundary="Old receipt cannot settle a future invocation or a new owner at the same address"; }
part role3:RoleRow { attribute :>> key="SchemeCapture"; attribute :>> identity="Scheme frame origin and rooted procedure/descriptor leases"; attribute :>> retirement="Final Scheme capture/use closure independently of native permission"; attribute :>> boundary="Multiple restoration prefixes remain legal after native owner expires"; }
part role4:RoleRow { attribute :>> key="EscapedCustodian"; attribute :>> identity="Stable guard outside discarded native frames"; attribute :>> retirement="Requires whole-subtree native exit and nested borrower drain"; attribute :>> boundary="Generic catcher arrival or elapsed time cannot sign owner closure"; }
part def IssuerRow { attribute key:String; attribute proposedIssuer:String; attribute actualSource:String; attribute status:String; attribute responsibility:String; }
part issuer0:IssuerRow { attribute :>> key="local-final-use"; attribute :>> proposedIssuer="GeneratedSfunFinalUseAdapter"; attribute :>> actualSource="_ptree2 c-make-function/c-set-result plus END_SFUN"; attribute :>> status="required adapter; not a qualified existing signer"; attribute :>> responsibility="Close admission only after last successful result conversion and all declared cleanup uses; then sign owner and final epoch"; }
part issuer1:IssuerRow { attribute :>> key="invocation"; attribute :>> proposedIssuer="CurrentInvocationExitAdapter"; attribute :>> actualSource="setup.c ___call matching marker and NO_ERR return"; attribute :>> status="control point exists; stable epoch record missing"; attribute :>> responsibility="Bind completion to the active native invocation, not the captured Scheme origin"; }
part issuer2:IssuerRow { attribute :>> key="abandoned-owner"; attribute :>> proposedIssuer="StableNativeReturnCoordinator"; attribute :>> actualSource="restored target catcher and subtree guard manifest"; attribute :>> status="required adapter; no existing complete signer"; attribute :>> responsibility="Confirm all discarded owner frames, native affinity and nested users before issuing abnormal closure"; }
part issuer3:IssuerRow { attribute :>> key="release"; attribute :>> proposedIssuer="ManagedMarkerOwner"; attribute :>> actualSource="kill_sfun_stack_marker and plain still decrement"; attribute :>> status="NoAbandon/native writer qualification unresolved"; attribute :>> responsibility="Consume this owner reference once after exact closure; commit before unmask/reply"; }
part issuer4:IssuerRow { attribute :>> key="roots-code"; attribute :>> proposedIssuer="RootRegistry and ImageLeaseCoordinator"; attribute :>> actualSource="root-origins and continuation descriptor consumers"; attribute :>> status="full native composition unresolved"; attribute :>> responsibility="GC root lease and descriptor retention survive owner invalidation and repeated Scheme restoration"; }
part def GainRow { attribute key:String; attribute avoided:String; attribute added:String; attribute condition:String; }
part gain0:GainRow { attribute :>> key="reuse"; attribute :>> avoided="Existing owner marker is reused across Q calls; no new per-call marker is required"; attribute :>> added="Invocation epochs/completion records and final-use gate"; attribute :>> condition="Current code already reuses it: do not count Q-E allocations as a new saving"; }
part gain1:GainRow { attribute :>> key="receipt"; attribute :>> avoided="Queries after commit add zero native reference decrements"; attribute :>> added="Stable receipt lookup, generation and retention work"; attribute :>> condition="Physical decrement/commit gap still needs NoAbandon; unknown outcomes retain resources"; }
part gain2:GainRow { attribute :>> key="finalizer"; attribute :>> avoided="One managed owner finalizer can replace three END_SFUN kill/propagate forms"; attribute :>> added="Generated result/converter effect plan and stable abnormal-exit cleanup"; attribute :>> condition="Remove unconditional duplicate kill sites after all three forms and abnormal exits qualify"; }
part gain3:GainRow { attribute :>> key="control"; attribute :>> avoided="Preserve old same-owner Scheme continuation delivery to current call"; attribute :>> added="Separate origin identity, current invocation and receipt ownership"; attribute :>> condition="Requiring origin epoch to equal active invocation changes supported control behavior"; }
part gain4:GainRow { attribute :>> key="token-alternative"; attribute :>> avoided="A qualified native token ABI may remove E marker vectors and E native releases"; attribute :>> added="R reflective views, S boxes and D newly owned native releases plus token support"; attribute :>> condition="Net object constructors E-R-S; native count releases E-D; Q calls may exceed E owners; no time/byte speedup proved"; }
part gain5:GainRow { attribute :>> key="root-descriptor"; attribute :>> avoided="One owner/capture/receipt ledger can replace repeated lifetime reconstruction"; attribute :>> added="Root enumeration, parked-context handoff and code grace"; attribute :>> condition="Only if obsolete responsibilities are deleted; existing necessary supports counted once"; }
part gain6:GainRow { attribute :>> key="language"; attribute :>> avoided="C23 can express this protocol and generate the finalizer from Scheme"; attribute :>> added="The same lifetime and source obligations remain for Zig"; attribute :>> condition="No Zig-specific net return is established by this study"; }
part def MemoryRow { attribute key:String; attribute publication:String; attribute observation:String; attribute obligation:String; }
part memory0:MemoryRow { attribute :>> key="invocation"; attribute :>> publication="Publish new current epoch before entering ___call under owner gate"; attribute :>> observation="Completion records current epoch after authenticated return"; attribute :>> obligation="Old-origin Scheme frames select a live owner; old completion receipts do not select a new invocation"; }
part memory1:MemoryRow { attribute :>> key="final-use"; attribute :>> publication="Close same-owner future-use admission after result and cleanup completion"; attribute :>> observation="Acquire zero active/nested users and exact final epoch, then commit closure"; attribute :>> obligation="Several C stores are not a hardware transaction; real gate and GC synchronization remain open"; }
part memory2:MemoryRow { attribute :>> key="escape"; attribute :>> publication="Preowned stable subtree record keeps roots/code while landing result is unknown"; attribute :>> observation="Exact native exit acknowledgement plus child/borrower closure"; attribute :>> obligation="No stack-local guard on a discarded C frame can be the sole issuer"; }
part memory3:MemoryRow { attribute :>> key="marker-drop"; attribute :>> publication="Qualified NoAbandon interval excludes GC/count writers through physical effect and receipt"; attribute :>> observation="Release commit before cancelling masks or replying; acquire query does not replay"; attribute :>> obligation="C23 atomics alone cannot couple plain -- with a separate receipt"; }
part memory4:MemoryRow { attribute :>> key="gc"; attribute :>> publication="Existing scanner/registry participation retains mutable slots while in use"; attribute :>> observation="Retire logical root only after final captures, guards and GC readers leave"; attribute :>> obligation="This model uses a root lease bit; moving-slot and image-group refinement to parent remains unproved"; }
part def PaperRow { attribute key:String; attribute title:String; attribute url:String; attribute section:String; attribute basis:String; attribute boundary:String; }
part paper0:PaperRow { attribute :>> key="gambit-primary"; attribute :>> title="Feeley: unrestricted continuation/C interoperability"; attribute :>> url="https://www.schemeworkshop.org/2000/feeley.ps"; attribute :>> section="1-5"; attribute :>> basis="Scheme control has unlimited extent; dynamic C targets expire independently"; attribute :>> boundary="Gambit-C 3.0 historical approach; native-thread proposal not then implemented; no timing transfer"; }
part paper1:PaperRow { attribute :>> key="gambit-pvm"; attribute :>> title="Feeley/Miller parallel VM"; attribute :>> url="https://www.iro.umontreal.ca/~feeley/papers/FeeleyMillerLFP90.pdf"; attribute :>> section="2"; attribute :>> basis="Explicit compiler/runtime interface is the place for origin and native return facts"; attribute :>> boundary="Not a proof of the current SFUN macros"; }
part paper2:PaperRow { attribute :>> key="ocaml-effects"; attribute :>> title="Retrofitting Effect Handlers onto OCaml"; attribute :>> url="https://anil.recoil.org/papers/2021-pldi-retroeff.pdf"; attribute :>> section="3.2;5.3"; attribute :>> basis="Explicit callback boundary and cleanup semantics"; attribute :>> boundary="Its one-shot/no-effects-across-C policy is not imported into Gambit"; }
part paper3:PaperRow { attribute :>> key="c23-draft"; attribute :>> title="WG14 N3096 C23 draft"; attribute :>> url="https://www.open-std.org/jtc1/sc22/wg14/www/docs/n3096.pdf"; attribute :>> section="5.1.2.4;7.13.2.1"; attribute :>> basis="Publication ordering plus same-thread live setjmp invocation"; attribute :>> boundary="Draft text; no atomic construct extends discarded C stack lifetime"; }
part def GroundingRow { attribute component:String; attribute producerAnchor:String; attribute paperKey:String; attribute obligationId:String; }
part grounding0:GroundingRow { attribute :>> component="control"; attribute :>> producerAnchor="marker-live-check"; attribute :>> paperKey="gambit-primary"; attribute :>> obligationId="Sfun-control-compatibility"; }
part grounding1:GroundingRow { attribute :>> component="control"; attribute :>> producerAnchor="generator-conversion"; attribute :>> paperKey="gambit-pvm"; attribute :>> obligationId="Sfun-lowering"; }
part grounding2:GroundingRow { attribute :>> component="control"; attribute :>> producerAnchor="cfun-catcher"; attribute :>> paperKey="ocaml-effects"; attribute :>> obligationId="Sfun-abnormal-exit"; }
part grounding3:GroundingRow { attribute :>> component="control"; attribute :>> producerAnchor="catcher-restore"; attribute :>> paperKey="c23-draft"; attribute :>> obligationId="Sfun-abnormal-exit"; }
part def ProfileRow { attribute key:String; attribute repeatable:String; attribute actionName:String; attribute lemma:String; attribute producerAnchor:String; attribute boundary:String; }
part profile0:ProfileRow { attribute :>> key="typed-result"; attribute :>> repeatable="potentially unbounded result-conversion retries"; attribute :>> actionName="sfun_owner_use_closure.retryHandler"; attribute :>> lemma="SfunOwner.liveOwnerDuringRetry"; attribute :>> producerAnchor="typed-loop"; attribute :>> boundary="QNT bounds four calls for analysis; it does not impose a runtime cap"; }
part profile1:ProfileRow { attribute :>> key="void-result"; attribute :>> repeatable="no repeated result conversion in built-in void form"; attribute :>> actionName="sfun_owner_use_closure.resultConversionSucceeds"; attribute :>> lemma="SfunOwner.invocationDoesNotClose"; attribute :>> producerAnchor="void-loop"; attribute :>> boundary="After input conversion failure handler call can return; no claim of repeated typed-result loop here"; }
part profile2:ProfileRow { attribute :>> key="scheme-object-result"; attribute :>> repeatable="direct PSR1 assignment does not create a result-conversion failure"; attribute :>> actionName="sfun_owner_use_closure.resultConversionSucceeds"; attribute :>> lemma="SfunOwner.invocationDoesNotClose"; attribute :>> producerAnchor="scm-loop"; attribute :>> boundary="Custom raw converter effects and arbitrary native mutation require separate qualification"; }
part def NeedRow { attribute key:String; attribute kind:String; attribute path:String; attribute scope:String; part owner:Owner; }
part need0:NeedRow { attribute :>> key="Sfun-formal"; attribute :>> kind="formal"; attribute :>> path="dev/refactoring/modern-c/models/lean/SfunOwner.lean"; attribute :>> scope="bounded formal protocol"; attribute :>> owner.componentId="control"; }
part need1:NeedRow { attribute :>> key="Sfun-bridge"; attribute :>> kind="bridge"; attribute :>> path="dev/modeling/tools/sfun-owner-use-closure-projection.py"; attribute :>> scope="trusted typed IR projection"; attribute :>> owner.componentId="control"; }
part need2:NeedRow { attribute :>> key="Sfun-lowering"; attribute :>> kind="native"; attribute :>> path="vendor/gambit/gsc/_ptree2.scm"; attribute :>> scope="exact generated normal final-use cut and converter support closure"; attribute :>> owner.componentId="control"; }
part need3:NeedRow { attribute :>> key="Sfun-abnormal-exit"; attribute :>> kind="native"; attribute :>> path="vendor/gambit/lib/setup.c"; attribute :>> scope="whole native subtree exit and stable owner closure signer"; attribute :>> owner.componentId="control"; }
part need4:NeedRow { attribute :>> key="Sfun-control-compatibility"; attribute :>> kind="native"; attribute :>> path="vendor/gambit/lib/_kernel.scm"; attribute :>> scope="same-owner old-origin delivery and fresh invocation receipts"; attribute :>> owner.componentId="control"; }
part need5:NeedRow { attribute :>> key="Sfun-release"; attribute :>> kind="native"; attribute :>> path="vendor/gambit/lib/c_intf.c"; attribute :>> scope="NoAbandon effect/receipt plus all native count writers"; attribute :>> owner.componentId="control"; }
part need6:NeedRow { attribute :>> key="Sfun-roots-code"; attribute :>> kind="native"; attribute :>> path="vendor/gambit/lib/_mem/root-origins.inc"; attribute :>> scope="complete moving roots and global image owners"; attribute :>> owner.componentId="roots"; }
part def BindingRow { attribute actionName:String; attribute lemma:String; }
part binding0:BindingRow { attribute :>> actionName="sfun_owner_use_closure.bodyCall"; attribute :>> lemma="SfunOwner.bodyCallPreserves"; }
part binding1:BindingRow { attribute :>> actionName="sfun_owner_use_closure.inputConversionFails"; attribute :>> lemma="SfunOwner.inputConversionFailsPreserves"; }
part binding2:BindingRow { attribute :>> actionName="sfun_owner_use_closure.captureCurrent"; attribute :>> lemma="SfunOwner.captureCurrentPreserves"; }
part binding3:BindingRow { attribute :>> actionName="sfun_owner_use_closure.callReturns"; attribute :>> lemma="SfunOwner.callReturnsPreserves"; }
part binding4:BindingRow { attribute :>> actionName="sfun_owner_use_closure.resultConversionFails"; attribute :>> lemma="SfunOwner.resultConversionFailsPreserves"; }
part binding5:BindingRow { attribute :>> actionName="sfun_owner_use_closure.retryHandler"; attribute :>> lemma="SfunOwner.retryHandlerPreserves"; }
part binding6:BindingRow { attribute :>> actionName="sfun_owner_use_closure.resultConversionSucceeds"; attribute :>> lemma="SfunOwner.resultConversionSucceedsPreserves"; }
part binding7:BindingRow { attribute :>> actionName="sfun_owner_use_closure.closeAdmission"; attribute :>> lemma="SfunOwner.closeAdmissionPreserves"; }
part binding8:BindingRow { attribute :>> actionName="sfun_owner_use_closure.signLocalClosure"; attribute :>> lemma="SfunOwner.signLocalClosurePreserves"; }
part binding9:BindingRow { attribute :>> actionName="sfun_owner_use_closure.enterNested"; attribute :>> lemma="SfunOwner.enterNestedPreserves"; }
part binding10:BindingRow { attribute :>> actionName="sfun_owner_use_closure.leaveNested"; attribute :>> lemma="SfunOwner.leaveNestedPreserves"; }
part binding11:BindingRow { attribute :>> actionName="sfun_owner_use_closure.outwardUnknown"; attribute :>> lemma="SfunOwner.outwardUnknownPreserves"; }
part binding12:BindingRow { attribute :>> actionName="sfun_owner_use_closure.drainDescendant"; attribute :>> lemma="SfunOwner.drainDescendantPreserves"; }
part binding13:BindingRow { attribute :>> actionName="sfun_owner_use_closure.ackNativeExit"; attribute :>> lemma="SfunOwner.ackNativeExitPreserves"; }
part binding14:BindingRow { attribute :>> actionName="sfun_owner_use_closure.signEscapedClosure"; attribute :>> lemma="SfunOwner.signEscapedClosurePreserves"; }
part binding15:BindingRow { attribute :>> actionName="sfun_owner_use_closure.beginRelease"; attribute :>> lemma="SfunOwner.beginReleasePreserves"; }
part binding16:BindingRow { attribute :>> actionName="sfun_owner_use_closure.physicalDrop"; attribute :>> lemma="SfunOwner.physicalDropPreserves"; }
part binding17:BindingRow { attribute :>> actionName="sfun_owner_use_closure.commitDrop"; attribute :>> lemma="SfunOwner.commitDropPreserves"; }
part binding18:BindingRow { attribute :>> actionName="sfun_owner_use_closure.loseClosureReply"; attribute :>> lemma="SfunOwner.loseClosureReplyPreserves"; }
part binding19:BindingRow { attribute :>> actionName="sfun_owner_use_closure.queryClosure"; attribute :>> lemma="SfunOwner.queryClosurePreserves"; }
part binding20:BindingRow { attribute :>> actionName="sfun_owner_use_closure.observeOldInvocation"; attribute :>> lemma="SfunOwner.observeOldInvocationPreserves"; }
part binding21:BindingRow { attribute :>> actionName="sfun_owner_use_closure.observeOldOwner"; attribute :>> lemma="SfunOwner.observeOldOwnerPreserves"; }
part binding22:BindingRow { attribute :>> actionName="sfun_owner_use_closure.resumeOldReturn"; attribute :>> lemma="SfunOwner.resumeOldReturnPreserves"; }
part binding23:BindingRow { attribute :>> actionName="sfun_owner_use_closure.resumeExpiredPrefix"; attribute :>> lemma="SfunOwner.resumeExpiredPrefixPreserves"; }
part binding24:BindingRow { attribute :>> actionName="sfun_owner_use_closure.rejectExpiredReturn"; attribute :>> lemma="SfunOwner.rejectExpiredReturnPreserves"; }
part binding25:BindingRow { attribute :>> actionName="sfun_owner_use_closure.dropCaptured"; attribute :>> lemma="SfunOwner.dropCapturedPreserves"; }
part binding26:BindingRow { attribute :>> actionName="sfun_owner_use_closure.beginGc"; attribute :>> lemma="SfunOwner.beginGcPreserves"; }
part binding27:BindingRow { attribute :>> actionName="sfun_owner_use_closure.endGc"; attribute :>> lemma="SfunOwner.endGcPreserves"; }
part binding28:BindingRow { attribute :>> actionName="sfun_owner_use_closure.retireRoots"; attribute :>> lemma="SfunOwner.retireRootsPreserves"; }
part binding29:BindingRow { attribute :>> actionName="sfun_owner_use_closure.retireCode"; attribute :>> lemma="SfunOwner.retireCodePreserves"; }
part binding30:BindingRow { attribute :>> actionName="sfun_owner_use_closure.newOwner"; attribute :>> lemma="SfunOwner.newOwnerPreserves"; }
part def RouteRow { attribute component:String; attribute actionName:String; attribute lemma:String; attribute producerAnchor:String; attribute obligationId:String; }
part route0:RouteRow { attribute :>> component="control"; attribute :>> actionName="sfun_owner_use_closure.bodyCall"; attribute :>> lemma="SfunOwner.bodyCallPreserves"; attribute :>> producerAnchor="typed-loop"; attribute :>> obligationId="Sfun-lowering"; }
part route1:RouteRow { attribute :>> component="control"; attribute :>> actionName="sfun_owner_use_closure.inputConversionFails"; attribute :>> lemma="SfunOwner.inputConversionFailsPreserves"; attribute :>> producerAnchor="typed-loop"; attribute :>> obligationId="Sfun-lowering"; }
part route2:RouteRow { attribute :>> component="control"; attribute :>> actionName="sfun_owner_use_closure.captureCurrent"; attribute :>> lemma="SfunOwner.captureCurrentPreserves"; attribute :>> producerAnchor="marker-live-check"; attribute :>> obligationId="Sfun-control-compatibility"; }
part route3:RouteRow { attribute :>> component="control"; attribute :>> actionName="sfun_owner_use_closure.callReturns"; attribute :>> lemma="SfunOwner.callReturnsPreserves"; attribute :>> producerAnchor="typed-loop"; attribute :>> obligationId="Sfun-lowering"; }
part route4:RouteRow { attribute :>> component="control"; attribute :>> actionName="sfun_owner_use_closure.resultConversionFails"; attribute :>> lemma="SfunOwner.resultConversionFailsPreserves"; attribute :>> producerAnchor="typed-loop"; attribute :>> obligationId="Sfun-lowering"; }
part route5:RouteRow { attribute :>> component="control"; attribute :>> actionName="sfun_owner_use_closure.retryHandler"; attribute :>> lemma="SfunOwner.retryHandlerPreserves"; attribute :>> producerAnchor="typed-loop"; attribute :>> obligationId="Sfun-lowering"; }
part route6:RouteRow { attribute :>> component="control"; attribute :>> actionName="sfun_owner_use_closure.resultConversionSucceeds"; attribute :>> lemma="SfunOwner.resultConversionSucceedsPreserves"; attribute :>> producerAnchor="typed-loop"; attribute :>> obligationId="Sfun-lowering"; }
part route7:RouteRow { attribute :>> component="control"; attribute :>> actionName="sfun_owner_use_closure.closeAdmission"; attribute :>> lemma="SfunOwner.closeAdmissionPreserves"; attribute :>> producerAnchor="typed-loop"; attribute :>> obligationId="Sfun-lowering"; }
part route8:RouteRow { attribute :>> component="control"; attribute :>> actionName="sfun_owner_use_closure.signLocalClosure"; attribute :>> lemma="SfunOwner.signLocalClosurePreserves"; attribute :>> producerAnchor="typed-loop"; attribute :>> obligationId="Sfun-lowering"; }
part route9:RouteRow { attribute :>> component="control"; attribute :>> actionName="sfun_owner_use_closure.enterNested"; attribute :>> lemma="SfunOwner.enterNestedPreserves"; attribute :>> producerAnchor="typed-loop"; attribute :>> obligationId="Sfun-lowering"; }
part route10:RouteRow { attribute :>> component="control"; attribute :>> actionName="sfun_owner_use_closure.leaveNested"; attribute :>> lemma="SfunOwner.leaveNestedPreserves"; attribute :>> producerAnchor="typed-loop"; attribute :>> obligationId="Sfun-lowering"; }
part route11:RouteRow { attribute :>> component="control"; attribute :>> actionName="sfun_owner_use_closure.outwardUnknown"; attribute :>> lemma="SfunOwner.outwardUnknownPreserves"; attribute :>> producerAnchor="catcher-restore"; attribute :>> obligationId="Sfun-abnormal-exit"; }
part route12:RouteRow { attribute :>> component="control"; attribute :>> actionName="sfun_owner_use_closure.drainDescendant"; attribute :>> lemma="SfunOwner.drainDescendantPreserves"; attribute :>> producerAnchor="catcher-restore"; attribute :>> obligationId="Sfun-abnormal-exit"; }
part route13:RouteRow { attribute :>> component="control"; attribute :>> actionName="sfun_owner_use_closure.ackNativeExit"; attribute :>> lemma="SfunOwner.ackNativeExitPreserves"; attribute :>> producerAnchor="catcher-restore"; attribute :>> obligationId="Sfun-abnormal-exit"; }
part route14:RouteRow { attribute :>> component="control"; attribute :>> actionName="sfun_owner_use_closure.signEscapedClosure"; attribute :>> lemma="SfunOwner.signEscapedClosurePreserves"; attribute :>> producerAnchor="catcher-restore"; attribute :>> obligationId="Sfun-abnormal-exit"; }
part route15:RouteRow { attribute :>> component="control"; attribute :>> actionName="sfun_owner_use_closure.beginRelease"; attribute :>> lemma="SfunOwner.beginReleasePreserves"; attribute :>> producerAnchor="marker-kill"; attribute :>> obligationId="Sfun-release"; }
part route16:RouteRow { attribute :>> component="control"; attribute :>> actionName="sfun_owner_use_closure.physicalDrop"; attribute :>> lemma="SfunOwner.physicalDropPreserves"; attribute :>> producerAnchor="marker-kill"; attribute :>> obligationId="Sfun-release"; }
part route17:RouteRow { attribute :>> component="control"; attribute :>> actionName="sfun_owner_use_closure.commitDrop"; attribute :>> lemma="SfunOwner.commitDropPreserves"; attribute :>> producerAnchor="marker-kill"; attribute :>> obligationId="Sfun-release"; }
part route18:RouteRow { attribute :>> component="control"; attribute :>> actionName="sfun_owner_use_closure.loseClosureReply"; attribute :>> lemma="SfunOwner.loseClosureReplyPreserves"; attribute :>> producerAnchor="marker-kill"; attribute :>> obligationId="Sfun-release"; }
part route19:RouteRow { attribute :>> component="control"; attribute :>> actionName="sfun_owner_use_closure.queryClosure"; attribute :>> lemma="SfunOwner.queryClosurePreserves"; attribute :>> producerAnchor="marker-kill"; attribute :>> obligationId="Sfun-release"; }
part route20:RouteRow { attribute :>> component="control"; attribute :>> actionName="sfun_owner_use_closure.observeOldInvocation"; attribute :>> lemma="SfunOwner.observeOldInvocationPreserves"; attribute :>> producerAnchor="marker-live-check"; attribute :>> obligationId="Sfun-control-compatibility"; }
part route21:RouteRow { attribute :>> component="control"; attribute :>> actionName="sfun_owner_use_closure.observeOldOwner"; attribute :>> lemma="SfunOwner.observeOldOwnerPreserves"; attribute :>> producerAnchor="marker-live-check"; attribute :>> obligationId="Sfun-control-compatibility"; }
part route22:RouteRow { attribute :>> component="control"; attribute :>> actionName="sfun_owner_use_closure.resumeOldReturn"; attribute :>> lemma="SfunOwner.resumeOldReturnPreserves"; attribute :>> producerAnchor="marker-live-check"; attribute :>> obligationId="Sfun-control-compatibility"; }
part route23:RouteRow { attribute :>> component="control"; attribute :>> actionName="sfun_owner_use_closure.resumeExpiredPrefix"; attribute :>> lemma="SfunOwner.resumeExpiredPrefixPreserves"; attribute :>> producerAnchor="marker-live-check"; attribute :>> obligationId="Sfun-control-compatibility"; }
part route24:RouteRow { attribute :>> component="control"; attribute :>> actionName="sfun_owner_use_closure.rejectExpiredReturn"; attribute :>> lemma="SfunOwner.rejectExpiredReturnPreserves"; attribute :>> producerAnchor="marker-live-check"; attribute :>> obligationId="Sfun-control-compatibility"; }
part route25:RouteRow { attribute :>> component="roots"; attribute :>> actionName="sfun_owner_use_closure.dropCaptured"; attribute :>> lemma="SfunOwner.dropCapturedPreserves"; attribute :>> producerAnchor="root-slots"; attribute :>> obligationId="Sfun-roots-code"; }
part route26:RouteRow { attribute :>> component="roots"; attribute :>> actionName="sfun_owner_use_closure.beginGc"; attribute :>> lemma="SfunOwner.beginGcPreserves"; attribute :>> producerAnchor="root-slots"; attribute :>> obligationId="Sfun-roots-code"; }
part route27:RouteRow { attribute :>> component="roots"; attribute :>> actionName="sfun_owner_use_closure.endGc"; attribute :>> lemma="SfunOwner.endGcPreserves"; attribute :>> producerAnchor="root-slots"; attribute :>> obligationId="Sfun-roots-code"; }
part route28:RouteRow { attribute :>> component="roots"; attribute :>> actionName="sfun_owner_use_closure.retireRoots"; attribute :>> lemma="SfunOwner.retireRootsPreserves"; attribute :>> producerAnchor="root-slots"; attribute :>> obligationId="Sfun-roots-code"; }
part route29:RouteRow { attribute :>> component="roots"; attribute :>> actionName="sfun_owner_use_closure.retireCode"; attribute :>> lemma="SfunOwner.retireCodePreserves"; attribute :>> producerAnchor="root-slots"; attribute :>> obligationId="Sfun-roots-code"; }
part route30:RouteRow { attribute :>> component="control"; attribute :>> actionName="sfun_owner_use_closure.newOwner"; attribute :>> lemma="SfunOwner.newOwnerPreserves"; attribute :>> producerAnchor="marker-live-check"; attribute :>> obligationId="Sfun-control-compatibility"; }
part def ProofRow { attribute key:String; attribute lemma:String; }
part proof0:ProofRow { attribute :>> key="invocationDoesNotClose"; attribute :>> lemma="SfunOwner.invocationDoesNotClose"; }
part proof1:ProofRow { attribute :>> key="liveOwnerDuringRetry"; attribute :>> lemma="SfunOwner.liveOwnerDuringRetry"; }
part proof2:ProofRow { attribute :>> key="activeHasFreshEpoch"; attribute :>> lemma="SfunOwner.activeHasFreshEpoch"; }
part proof3:ProofRow { attribute :>> key="signedClosureCut"; attribute :>> lemma="SfunOwner.signedClosureCut"; }
part proof4:ProofRow { attribute :>> key="unknownRetainsCustody"; attribute :>> lemma="SfunOwner.unknownRetainsCustody"; }
part proof5:ProofRow { attribute :>> key="effectGapHasCustody"; attribute :>> lemma="SfunOwner.effectGapHasCustody"; }
part proof6:ProofRow { attribute :>> key="settledExactlyOnce"; attribute :>> lemma="SfunOwner.settledExactlyOnce"; }
part proof7:ProofRow { attribute :>> key="captureKeepsRootsAndCode"; attribute :>> lemma="SfunOwner.captureKeepsRootsAndCode"; }
part proof8:ProofRow { attribute :>> key="retirementCut"; attribute :>> lemma="SfunOwner.retirementCut"; }
part proof9:ProofRow { attribute :>> key="physicalEffectExcludedFromGc"; attribute :>> lemma="SfunOwner.physicalEffectExcludedFromGc"; }
part proof10:ProofRow { attribute :>> key="expiredOwnerNotReopened"; attribute :>> lemma="SfunOwner.expiredOwnerNotReopened"; }
part proof11:ProofRow { attribute :>> key="generationDoesNotAlias"; attribute :>> lemma="SfunOwner.generationDoesNotAlias"; }
part proof12:ProofRow { attribute :>> key="initialSafe"; attribute :>> lemma="SfunOwner.initialSafe"; }
part proof13:ProofRow { attribute :>> key="stepPreserves"; attribute :>> lemma="SfunOwner.stepPreserves"; }
part proof14:ProofRow { attribute :>> key="reachableSafe"; attribute :>> lemma="SfunOwner.reachableSafe"; }
part proof15:ProofRow { attribute :>> key="oldInvocationQueryDoesNotSettle"; attribute :>> lemma="SfunOwner.oldInvocationQueryDoesNotSettle"; }
part proof16:ProofRow { attribute :>> key="oldOwnerQueryDoesNotSettle"; attribute :>> lemma="SfunOwner.oldOwnerQueryDoesNotSettle"; }
part proof17:ProofRow { attribute :>> key="resumedOriginCompletesCurrent"; attribute :>> lemma="SfunOwner.resumedOriginCompletesCurrent"; }
part proof18:ProofRow { attribute :>> key="receiptQueryDoesNotDrop"; attribute :>> lemma="SfunOwner.receiptQueryDoesNotDrop"; }
part def CompositionRow { attribute key:String; attribute fromAction:String; attribute toAction:String; attribute lemma:String; attribute fromComponent:String; attribute toComponent:String; attribute sharedConstraint:String; }
part composition0:CompositionRow { attribute :>> key="invocation-to-retry"; attribute :>> fromAction="sfun_owner_use_closure.callReturns"; attribute :>> toAction="sfun_owner_use_closure.retryHandler"; attribute :>> lemma="SfunOwner.invocationDoesNotClose"; attribute :>> fromComponent="control"; attribute :>> toComponent="control"; attribute :>> sharedConstraint="Returning from one call leaves owner valid for result conversion and retry"; }
part composition1:CompositionRow { attribute :>> key="origin-to-current"; attribute :>> fromAction="sfun_owner_use_closure.resumeOldReturn"; attribute :>> toAction="sfun_owner_use_closure.observeOldInvocation"; attribute :>> lemma="SfunOwner.resumedOriginCompletesCurrent"; attribute :>> fromComponent="control"; attribute :>> toComponent="control"; attribute :>> sharedConstraint="Scheme origin may be old; completion belongs to current native invocation"; }
part composition2:CompositionRow { attribute :>> key="normal-to-release"; attribute :>> fromAction="sfun_owner_use_closure.signLocalClosure"; attribute :>> toAction="sfun_owner_use_closure.physicalDrop"; attribute :>> lemma="SfunOwner.signedClosureCut"; attribute :>> fromComponent="control"; attribute :>> toComponent="control"; attribute :>> sharedConstraint="All future owner use closed and exact owner/epoch receipt before count release"; }
part composition3:CompositionRow { attribute :>> key="escape-to-release"; attribute :>> fromAction="sfun_owner_use_closure.ackNativeExit"; attribute :>> toAction="sfun_owner_use_closure.signEscapedClosure"; attribute :>> lemma="SfunOwner.unknownRetainsCustody"; attribute :>> fromComponent="control"; attribute :>> toComponent="control"; attribute :>> sharedConstraint="Unknown landing retains roots and native reference; subtree exit required"; }
part composition4:CompositionRow { attribute :>> key="capture-to-retirement"; attribute :>> fromAction="sfun_owner_use_closure.resumeExpiredPrefix"; attribute :>> toAction="sfun_owner_use_closure.retireCode"; attribute :>> lemma="SfunOwner.captureKeepsRootsAndCode"; attribute :>> fromComponent="control"; attribute :>> toComponent="roots"; attribute :>> sharedConstraint="Expired native return does not discharge Scheme captures or their descriptors"; }
part composition5:CompositionRow { attribute :>> key="gc-to-release"; attribute :>> fromAction="sfun_owner_use_closure.beginGc"; attribute :>> toAction="sfun_owner_use_closure.physicalDrop"; attribute :>> lemma="SfunOwner.physicalEffectExcludedFromGc"; attribute :>> fromComponent="roots"; attribute :>> toComponent="control"; attribute :>> sharedConstraint="GC and non-abandonable physical effect use the same qualified exclusion carrier"; }
part def LeafRow { attribute key:String; attribute component:String; attribute actionName:String; attribute lemma:String; attribute producerAnchor:String; attribute qualification:String; attribute boundary:String; }
part leaf0:LeafRow { attribute :>> key="final-use"; attribute :>> component="control"; attribute :>> actionName="sfun_owner_use_closure.signLocalClosure"; attribute :>> lemma="SfunOwner.signedClosureCut"; attribute :>> producerAnchor="sfun-finalizer"; attribute :>> qualification="Generated end-of-loop finalizer closes future use, not each ___call return"; attribute :>> boundary="All argument/result/custom converter cleanup and late callback uses must be covered; no current qualified signer"; }
part leaf1:LeafRow { attribute :>> key="origin-versus-receipt"; attribute :>> component="control"; attribute :>> actionName="sfun_owner_use_closure.resumeOldReturn"; attribute :>> lemma="SfunOwner.resumedOriginCompletesCurrent"; attribute :>> producerAnchor="call-marker-match"; attribute :>> qualification="Preserve old Scheme origin to live owner while current invocation gets a fresh receipt"; attribute :>> boundary="Never use originEpoch equality as a blanket native return restriction"; }
part leaf2:LeafRow { attribute :>> key="abnormal-subtree"; attribute :>> component="control"; attribute :>> actionName="sfun_owner_use_closure.ackNativeExit"; attribute :>> lemma="SfunOwner.unknownRetainsCustody"; attribute :>> producerAnchor="cfun-catcher"; attribute :>> qualification="Stable external guard confirms all discarded owner users before closure"; attribute :>> boundary="An intermediate catcher or Scheme exception handler is not a subtree-exit receipt"; }
part leaf3:LeafRow { attribute :>> key="no-abandon"; attribute :>> component="control"; attribute :>> actionName="sfun_owner_use_closure.physicalDrop"; attribute :>> lemma="SfunOwner.effectGapHasCustody"; attribute :>> producerAnchor="physical-count"; attribute :>> qualification="No allocation, callback, safepoint, asynchronous abandonment or competing count/GC access through effect and commit"; attribute :>> boundary="Source leaf purity alone does not qualify compiler instrumentation, cancellation or all raw aliases"; }
part def ContractRow { attribute fromNode:String; attribute toNode:String; attribute custody:String; }
part contract0:ContractRow { attribute :>> fromNode="One_Rooted_Marker_Owner"; attribute :>> toNode="Body_or_Input_Error"; attribute :>> custody="one existing native reference; owner stays valid"; }
part contract1:ContractRow { attribute :>> fromNode="Body_or_Input_Error"; attribute :>> toNode="Current_Call"; attribute :>> custody="new InvocationEpoch; same marker owner"; }
part contract2:ContractRow { attribute :>> fromNode="Current_Call"; attribute :>> toNode="Result_Conversion"; attribute :>> custody="___call returns NO_ERR; owner remains open"; }
part contract3:ContractRow { attribute :>> fromNode="Result_Conversion"; attribute :>> toNode="Conversion_Error_Handler"; attribute :>> custody="typed conversion failure; preserved procedure and dynamic exception handler"; }
part contract4:ContractRow { attribute :>> fromNode="Conversion_Error_Handler"; attribute :>> toNode="Current_Call"; attribute :>> custody="retry with new invocation, same marker"; }
part contract5:ContractRow { attribute :>> fromNode="Captured_Old_Scheme_Origin"; attribute :>> toNode="Current_Call"; attribute :>> custody="live same-owner return may complete current call"; }
part contract6:ContractRow { attribute :>> fromNode="Old_Completion_Receipt"; attribute :>> toNode="Current_Call"; attribute :>> custody="query only; cannot close or decrement current use"; }
part contract7:ContractRow { attribute :>> fromNode="Result_Conversion"; attribute :>> toNode="Final_Use_Check"; attribute :>> custody="success and all future converter/cleanup uses accounted"; }
part contract8:ContractRow { attribute :>> fromNode="Final_Use_Check"; attribute :>> toNode="Owner_Closure_Record"; attribute :>> custody="close admission, drain users, bind final epoch"; }
part contract9:ContractRow { attribute :>> fromNode="Current_Call"; attribute :>> toNode="Unknown_Native_Escape"; attribute :>> custody="stable guard keeps roots/code; local END_SFUN may be skipped"; }
part contract10:ContractRow { attribute :>> fromNode="Unknown_Native_Escape"; attribute :>> toNode="Confirmed_Subtree_Exit"; attribute :>> custody="exact landing plus descendant/owner last-use evidence"; }
part contract11:ContractRow { attribute :>> fromNode="Confirmed_Subtree_Exit"; attribute :>> toNode="Owner_Closure_Record"; attribute :>> custody="abnormal mode; no current complete native signer"; }
part contract12:ContractRow { attribute :>> fromNode="Owner_Closure_Record"; attribute :>> toNode="Physical_Drop_Gap"; attribute :>> custody="NoAbandon and GC/count-writer exclusion"; }
part contract13:ContractRow { attribute :>> fromNode="Physical_Drop_Gap"; attribute :>> toNode="Committed_Release"; attribute :>> custody="one owned decrement; commit before reply/unmask"; }
part contract14:ContractRow { attribute :>> fromNode="Committed_Release"; attribute :>> toNode="Idempotent_Query"; attribute :>> custody="lost reply performs no second decrement"; }
part contract15:ContractRow { attribute :>> fromNode="Committed_Release"; attribute :>> toNode="Expired_Scheme_Prefix"; attribute :>> custody="multi-shot Scheme computation remains possible; native return rejected"; }
part contract16:ContractRow { attribute :>> fromNode="Expired_Scheme_Prefix"; attribute :>> toNode="Root_and_Code_Retirement"; attribute :>> custody="last capture, GC and global image owners must leave"; }
part source36:SourceRow { attribute :>> key="initial-owned-reference"; attribute :>> path="vendor/gambit/lib/_mem/object-allocation.inc"; attribute :>> needle="base[___STILL_REFCOUNT] = 1;"; attribute :>> obligation="initial still header reference; additional owners still need separate accounting"; }
part gain7:GainRow { attribute :>> key="watermark-support"; attribute :>> avoided="Observation-only stale invocation handling can avoid adding one retained outcome record for every retry"; attribute :>> added="Per-owner current epoch/completed watermark and closure tombstone plus query-record pins"; attribute :>> condition="Bounded identity metadata O(E) for E owners, versus O(Q) retained per-call outcomes for Q calls, only if queries need no historical payload; this avoids new support cost and does not retire an existing ledger"; }
}
