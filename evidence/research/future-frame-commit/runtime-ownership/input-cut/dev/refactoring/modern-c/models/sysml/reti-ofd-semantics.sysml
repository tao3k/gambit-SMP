package GambitRetiOfdSemantics { private import ScalarValues::*;
part def SourceRoute { attribute key:String; attribute sourcePath:String; attribute needle:String; attribute obligation:String; attribute proofScope:String; }
part def StoredShape { attribute key:String; attribute kind:String; attribute count:Integer; attribute storedFs:Integer; attribute linkSlot:Integer; attribute mask:Integer; attribute actualFs:Integer; attribute provenance:String; }
part def BridgeScope { attribute key:String; attribute qualified:Boolean; attribute lemma:String; attribute premise:String; attribute gap:String; }
part def RetirementUser { attribute key:String; attribute sourcePath:String; attribute needle:String; attribute resource:String; attribute close:String; attribute finalUse:String; attribute unknown:String; }
part def Gain { attribute key:String; attribute avoided:String; attribute added:String; attribute condition:String; }
part def Gate { attribute key:String; attribute qualified:Boolean; attribute duty:String; }

ref part owner0=GambitRuntimeComposition::blueprintModule0;
ref part owner1=GambitRuntimeComposition::blueprintModule1;
ref part owner2=GambitRuntimeComposition::blueprintModule2;
ref part owner3=GambitRuntimeComposition::blueprintModule3;
ref part owner4=GambitRuntimeComposition::blueprintModule4;
ref part owner5=GambitRuntimeComposition::blueprintModule5;
ref part owner6=GambitRuntimeComposition::blueprintModule6;
ref part owner7=GambitRuntimeComposition::blueprintModule7;
ref part owner8=GambitRuntimeComposition::blueprintModule8;
part route0:SourceRoute { attribute :>> key="register-map-producer"; attribute :>> sourcePath="vendor/gambit/gsc/_t-c-2.scm"; attribute :>> needle="all saved GVM regs are live"; attribute :>> obligation="Internal map includes all saved registers and actual return; stored cfs is not actual fs"; attribute :>> proofScope="conditional coordinate/root-bit arithmetic"; }
part route1:SourceRoute { attribute :>> key="ofd-chunks"; attribute :>> sourcePath="vendor/gambit/gsc/_t-c-3.scm"; attribute :>> needle="(define (targ-gc-map-chunks"; attribute :>> obligation="Low-to-high 32-bit chunk stream covers actual expanded frame"; attribute :>> proofScope="symbolic reconstruction; no concrete map OFD witnessed"; }
part route2:SourceRoute { attribute :>> key="table-emitter"; attribute :>> sourcePath="vendor/gambit/gsc/_t-c-1.scm"; attribute :>> needle="\"DEF_OFD\""; attribute :>> obligation="Preserve RETI tag, stored cfs, link and chunk packing"; attribute :>> proofScope="source witness; code generation equivalence open"; }
part route3:SourceRoute { attribute :>> key="map-table"; attribute :>> sourcePath="vendor/gambit/lib/_std.c"; attribute :>> needle=",___DEF_LBL_INTRO(___H_map,"; attribute :>> obligation="22 direct IFD returns: 13 internal and 9 normal, no direct OFD"; attribute :>> proofScope="all stored tuples statically checked"; }
part route4:SourceRoute { attribute :>> key="save-registers"; attribute :>> sourcePath="vendor/gambit/lib/_kernel.scm"; attribute :>> needle="___PUSH_REGS /* push all GVM registers"; attribute :>> obligation="Push R0..R4 and actual return before publishing internal_return"; attribute :>> proofScope="five-register source case; all target configurations open"; }
part route5:SourceRoute { attribute :>> key="decode-reader"; attribute :>> sourcePath="vendor/gambit/include/gambit.h.in"; attribute :>> needle="___decode_frame_descriptor"; attribute :>> obligation="Decode inline/OFD and convert stored internal size once"; attribute :>> proofScope="source arithmetic under explicit configuration"; }
part route6:SourceRoute { attribute :>> key="scan-registers"; attribute :>> sourcePath="vendor/gambit/lib/mem.c"; attribute :>> needle="___RETI_GET_FS_LINK_GCMAP(actual_ra"; attribute :>> obligation="Read actual return metadata before scanning expanded saved-register frame"; attribute :>> proofScope="root values and moving updates source proof open"; }
part route7:SourceRoute { attribute :>> key="restore-registers"; attribute :>> sourcePath="vendor/gambit/lib/_kernel.scm"; attribute :>> needle="ira = ___POP;"; attribute :>> obligation="Restore actual return then registers in reverse push order; preserve force result separately"; attribute :>> proofScope="source closure with temp2 and caller continuation still open"; }
part route8:SourceRoute { attribute :>> key="module-ofd-fixup"; attribute :>> sourcePath="vendor/gambit/lib/setup.c"; attribute :>> needle="ofd_alloc += 1 + ___CEILING_DIV"; attribute :>> obligation="OFD pointer relocation advances by actual expanded map word count"; attribute :>> proofScope="ABI and loader lifetime refinement open"; }
part route9:SourceRoute { attribute :>> key="unload-consumer"; attribute :>> sourcePath="vendor/gambit/lib/os_dyn.c"; attribute :>> needle="dlclose (p->descr);"; attribute :>> obligation="Distinguish failed-load close and global unload; complete users before reclaim"; attribute :>> proofScope="no current per-module grace protocol established"; }
part shape0:StoredShape { attribute :>> key="___RETI-8-0-0x3f07"; attribute :>> kind="___RETI"; attribute :>> count=5; attribute :>> storedFs=8; attribute :>> linkSlot=0; attribute :>> mask=16135; attribute :>> actualFs=17; attribute :>> provenance="Stored current C only; no regenerated/current configuration or native-object match"; }
part shape1:StoredShape { attribute :>> key="___RETN-5-0-0x7"; attribute :>> kind="___RETN"; attribute :>> count=6; attribute :>> storedFs=5; attribute :>> linkSlot=0; attribute :>> mask=7; attribute :>> actualFs=5; attribute :>> provenance="Stored current C only; no regenerated/current configuration or native-object match"; }
part shape2:StoredShape { attribute :>> key="___RETN-5-0-0x9"; attribute :>> kind="___RETN"; attribute :>> count=2; attribute :>> storedFs=5; attribute :>> linkSlot=0; attribute :>> mask=9; attribute :>> actualFs=5; attribute :>> provenance="Stored current C only; no regenerated/current configuration or native-object match"; }
part shape3:StoredShape { attribute :>> key="___RETI-1-0-0x3f1"; attribute :>> kind="___RETI"; attribute :>> count=2; attribute :>> storedFs=1; attribute :>> linkSlot=0; attribute :>> mask=1009; attribute :>> actualFs=13; attribute :>> provenance="Stored current C only; no regenerated/current configuration or native-object match"; }
part shape4:StoredShape { attribute :>> key="___RETN-5-0-0xf"; attribute :>> kind="___RETN"; attribute :>> count=1; attribute :>> storedFs=5; attribute :>> linkSlot=0; attribute :>> mask=15; attribute :>> actualFs=5; attribute :>> provenance="Stored current C only; no regenerated/current configuration or native-object match"; }
part shape5:StoredShape { attribute :>> key="___RETI-8-8-0x3f03"; attribute :>> kind="___RETI"; attribute :>> count=3; attribute :>> storedFs=8; attribute :>> linkSlot=8; attribute :>> mask=16131; attribute :>> actualFs=17; attribute :>> provenance="Stored current C only; no regenerated/current configuration or native-object match"; }
part shape6:StoredShape { attribute :>> key="___RETI-8-8-0x3f01"; attribute :>> kind="___RETI"; attribute :>> count=1; attribute :>> storedFs=8; attribute :>> linkSlot=8; attribute :>> mask=16129; attribute :>> actualFs=17; attribute :>> provenance="Stored current C only; no regenerated/current configuration or native-object match"; }
part shape7:StoredShape { attribute :>> key="___RETI-1-4-0x3f1"; attribute :>> kind="___RETI"; attribute :>> count=1; attribute :>> storedFs=1; attribute :>> linkSlot=4; attribute :>> mask=1009; attribute :>> actualFs=13; attribute :>> provenance="Stored current C only; no regenerated/current configuration or native-object match"; }
part shape8:StoredShape { attribute :>> key="___RETI-3-4-0x3f7"; attribute :>> kind="___RETI"; attribute :>> count=1; attribute :>> storedFs=3; attribute :>> linkSlot=4; attribute :>> mask=1015; attribute :>> actualFs=13; attribute :>> provenance="Stored current C only; no regenerated/current configuration or native-object match"; }
part bridge0:BridgeScope { attribute :>> key="typed-ast-meaning"; attribute :>> qualified=true; attribute :>> lemma="stepMeaning"; attribute :>> premise="Twelve closed action bodies projected from official typed IR; deterministic pure guards and single final assignment"; attribute :>> gap="Quint parser/typechecker and Python extractor remain trusted, not kernel-verified"; }
part bridge1:BridgeScope { attribute :>> key="nested-simulation"; attribute :>> qualified=true; attribute :>> lemma="astToNested"; attribute :>> premise="Interpreted selected AST transitions compose with prior flat-to-nested relation"; attribute :>> gap="Not concrete Scheme/C execution or all Quint constructs"; }
part bridge2:BridgeScope { attribute :>> key="invariant-reflection"; attribute :>> qualified=true; attribute :>> lemma="invariantMeaning"; attribute :>> premise="Pure mathematical Int/Bool/record fragment and selected safe expression"; attribute :>> gap="No C integer overflow, pointer, weak-memory or exception semantics"; }
part bridge3:BridgeScope { attribute :>> key="simultaneous-update"; attribute :>> qualified=true; attribute :>> lemma="simultaneousReadsOld"; attribute :>> premise="Every RHS reads immutable old state; apply multiple updates only to result accumulator"; attribute :>> gap="No sequential action composition or extra assignments admitted by this projection"; }
part bridge4:BridgeScope { attribute :>> key="reti-root-arithmetic"; attribute :>> qualified=true; attribute :>> lemma="savedWindowEight"; attribute :>> premise="Five GVM registers, frame align4 reserve3 and stored current masks"; attribute :>> gap="Actual machine configuration and root values remain unqualified"; }
part bridge5:BridgeScope { attribute :>> key="ofd-reconstruction"; attribute :>> qualified=true; attribute :>> lemma="chunkReconstruction"; attribute :>> premise="Mathematical low/high 32-bit words and explicit expanded frame size"; attribute :>> gap="Synthetic 37-slot example is not an actual map OFD occurrence"; }
part bridge6:BridgeScope { attribute :>> key="trusted-extraction"; attribute :>> qualified=false; attribute :>> lemma="open"; attribute :>> premise="Actual source text to official typed IR to emitted Lean AST"; attribute :>> gap="Translator refusal checks and hashes are not parser/extractor correctness proofs"; }
part bridge7:BridgeScope { attribute :>> key="source-retirement"; attribute :>> qualified=false; attribute :>> lemma="open"; attribute :>> premise="Real root coverage, force/temp2, all aliases/OS users and final unload"; attribute :>> gap="Finite lease model and static symbols do not establish full source/C11 retirement"; }
part user0:RetirementUser { attribute :>> key="saved-continuations"; attribute :>> sourcePath="vendor/gambit/lib/mem.c"; attribute :>> needle="mark_captured_continuation"; attribute :>> resource="old labels/code plus inline/OFD metadata"; attribute :>> close="close new external invocations; do not invalidate old captured computation"; attribute :>> finalUse="all reachable captured/saved aliases gone or proved migration finished"; attribute :>> unknown="keep old cohort if reachability unknown"; }
part user1:RetirementUser { attribute :>> key="running-activations"; attribute :>> sourcePath="vendor/gambit/lib/_kernel.scm"; attribute :>> needle="___POP_REGS"; attribute :>> resource="old executable return targets and saved register frame interpretation"; attribute :>> close="no new external call grant; admitted callers may finish"; attribute :>> finalUse="last instruction and exception/catcher cleanup access, not function return alone"; attribute :>> unknown="retain root, code and descriptor pins"; }
part user2:RetirementUser { attribute :>> key="gc-maintenance"; attribute :>> sourcePath="vendor/gambit/lib/mem.c"; attribute :>> needle="___RETI_GET_FS_LINK_GCMAP(actual_ra"; attribute :>> resource="old codec/descriptor/code labels during scanning"; attribute :>> close="maintenance scan admission stays open while old rooted users remain; close only after producer-root retirement"; attribute :>> finalUse="all private/queued/in-flight scans complete after root cut"; attribute :>> unknown="unknown scan handoff retains responsibility"; }
part user3:RetirementUser { attribute :>> key="ffi-entry"; attribute :>> sourcePath="vendor/gambit/lib/setup.c"; attribute :>> needle="___EXP_FUNC(___SCMOBJ,___call)"; attribute :>> resource="native callbacks, closures and imported function pointers"; attribute :>> close="revoke registered callback/admission authority before close"; attribute :>> finalUse="nested callbacks, retained raw aliases and old catcher users fully drained"; attribute :>> unknown="raw unrevocable function pointers refuse unload"; }
part user4:RetirementUser { attribute :>> key="inspection"; attribute :>> sourcePath="vendor/gambit/lib/setup.c"; attribute :>> needle="___LABEL_INFO"; attribute :>> resource="profiler/debugger/stacktrace metadata and return label addresses"; attribute :>> close="inspection borrows acquire stable directory before access"; attribute :>> finalUse="all reader leases and delayed trace/diagnostic consumers finish"; attribute :>> unknown="unknown reader lifetime retains code/descriptor storage"; }
part user5:RetirementUser { attribute :>> key="loader-fixup"; attribute :>> sourcePath="vendor/gambit/lib/setup.c"; attribute :>> needle="___LABEL_DESCR_SET(lbl"; attribute :>> resource="OFD storage and installed labels"; attribute :>> close="candidate setup privately; publish immutable installed cohort"; attribute :>> finalUse="no installed label, scanner or saved return refers to old OFD"; attribute :>> unknown="retain candidate or old owner on unknown install result"; }
part user6:RetirementUser { attribute :>> key="os-unload"; attribute :>> sourcePath="vendor/gambit/lib/os_dyn.c"; attribute :>> needle="___DONT_UNLOAD_DYN_CODE"; attribute :>> resource="dynamic library handle, native finalizers and platform hooks"; attribute :>> close="policy plus full users; never conflate failed unpublished load with active cohort"; attribute :>> finalUse="loader confirms actual unload and accounting after last OS/native use"; attribute :>> unknown="failed/unknown unload keeps stable custodian"; }
part user7:RetirementUser { attribute :>> key="build-artifacts"; attribute :>> sourcePath="../gerbil-gambit-bootstrap-audit/src/gerbil/compiler/driver.ss"; attribute :>> needle="(def (compile-scm-file"; attribute :>> resource="cache files versus installed live code/descriptor cohort"; attribute :>> close="cache eviction authority cannot revoke runtime users"; attribute :>> finalUse="separate artifact deletion and runtime unload obligations"; attribute :>> unknown="unknown installed reference blocks runtime reclaim"; }
part gain0:Gain { attribute :>> key="reuse-current-frame-contract"; attribute :>> avoided="Duplicate semantic/register-map interpretation after real caller migration"; attribute :>> added="Source closure, complete metadata, target profiles and validation"; attribute :>> condition="RETI saving and exact masks already exist; no new scan reduction credited"; }
part gain1:Gain { attribute :>> key="interpreted-expression-bridge"; attribute :>> avoided="Manual action-name pairing without guard/update semantics"; attribute :>> added="Restricted typed-IR projection, Lean interpreter and rejecting admission"; attribute :>> condition="Kernel proof covers admitted AST only; parser/extractor trust boundary stays visible"; }
part gain2:Gain { attribute :>> key="narrow-abi-invalidation"; attribute :>> avoided="Unneeded frontend/runtime rebuild for unchanged consumed projections"; attribute :>> added="Spec/codec/tool keys, manifests and retained installed cohorts"; attribute :>> condition="Content change and codec change differ; physical register count changes can invalidate upstream semantics"; }
part gain3:Gain { attribute :>> key="safe-retirement"; attribute :>> avoided="Unsafe lifetime inference from idle caller or empty cache"; attribute :>> added="External close plus maintenance-root closure, five lease classes and unknown custody"; attribute :>> condition="No finite memory-retention bound without all-user progress; raw aliases may force permanent retention"; }
part gate0:Gate { attribute :>> key="source-to-ir"; attribute :>> qualified=false; attribute :>> duty="Official parser/typechecker and extractor correctness are not proved"; }
part gate1:Gate { attribute :>> key="full-quint"; attribute :>> qualified=false; attribute :>> duty="Then/run/assert, nondet picks, lambdas, sets and higher-order definitions excluded"; }
part gate2:Gate { attribute :>> key="source-frame-values"; attribute :>> qualified=false; attribute :>> duty="All saved root values, temp2, denv and exceptional restoration need semantic proof"; }
part gate3:Gate { attribute :>> key="actual-ofd"; attribute :>> qualified=false; attribute :>> duty="No direct map OFD present; full transitive callback OFD reachability unknown"; }
part gate4:Gate { attribute :>> key="machine-layout"; attribute :>> qualified=false; attribute :>> duty="Actual register count, word width, signed shifts, flags and current generated/native provenance unresolved"; }
part gate5:Gate { attribute :>> key="retirement-closure"; attribute :>> qualified=false; attribute :>> duty="Full writer/alias/reader list, maintenance gate close and C11 last-use protocol open"; }
part gate6:Gate { attribute :>> key="native-performance"; attribute :>> qualified=false; attribute :>> duty="No native/runtime/performance run or existing acceptance upgrade"; }
part history:GambitAssuranceRouting::ModelNeed { ref part :>> owner=GambitBuildAssurance::planner.component; attribute :>> obligationId="RO-H"; attribute :>> kind="interleaving"; attribute :>> subjectPath="dev/refactoring/modern-c/models/quint/reti_ofd_retirement.qnt"; attribute :>> subjectScope="Retirement external close plus surviving maintenance scans and five lease classes; finite custody only"; attribute :>> premise="Interpreted restricted AST proof is conditional on admitted official typed IR; no full Quint tool, Scheme runtime, native or performance proof"; }
part induction:GambitAssuranceRouting::ModelNeed { ref part :>> owner=GambitBuildAssurance::planner.component; attribute :>> obligationId="RO-I"; attribute :>> kind="induction"; attribute :>> subjectPath="dev/refactoring/modern-c/models/lean/RetiOfdSemantics.lean"; attribute :>> subjectScope="Restricted interpreter, conditional RETI/OFD arithmetic and abstract retirement conditions"; attribute :>> premise="Interpreted restricted AST proof is conditional on admitted official typed IR; no full Quint tool, Scheme runtime, native or performance proof"; }
part expression:GambitAssuranceRouting::ModelNeed { ref part :>> owner=GambitBuildAssurance::planner.component; attribute :>> obligationId="RO-X"; attribute :>> kind="induction"; attribute :>> subjectPath="dev/refactoring/modern-c/models/lean/MapExpressionAst.lean"; attribute :>> subjectScope="Generated exact selected typed-IR AST: per-action, step, invariant, initial and nested simulation; parser/extractor trusted"; attribute :>> premise="Interpreted restricted AST proof is conditional on admitted official typed IR; no full Quint tool, Scheme runtime, native or performance proof"; }
part source:GambitAssuranceRouting::ModelNeed { ref part :>> owner=GambitBuildAssurance::planner.component; attribute :>> obligationId="RO-S"; attribute :>> kind="source-refinement"; attribute :>> subjectPath="dev/refactoring/modern-c/reti-ofd-semantics-design.org"; attribute :>> subjectScope="All actual register/root/GC/restore/OFD/retirement consumers and expression source extraction semantics OPEN"; attribute :>> premise="Interpreted restricted AST proof is conditional on admitted official typed IR; no full Quint tool, Scheme runtime, native or performance proof"; }
part platform:GambitAssuranceRouting::ModelNeed { ref part :>> owner=GambitBuildAssurance::planner.component; attribute :>> obligationId="RO-E"; attribute :>> kind="environment-refinement"; attribute :>> subjectPath="dev/refactoring/modern-c/reti-ofd-semantics-design.org"; attribute :>> subjectScope="C11, target macros, effective native code and loader final-use evidence OPEN"; attribute :>> premise="Interpreted restricted AST proof is conditional on admitted official typed IR; no full Quint tool, Scheme runtime, native or performance proof"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=expression; }
part dependency3:GambitAssuranceRouting::NeedDependency { ref part :>> dependent=source; ref part :>> prerequisite=platform; }
part dependency4:GambitAssuranceRouting::NeedDependency { ref part :>> dependent=source; ref part :>> prerequisite=GambitMapFrameAbi::source; }
}
