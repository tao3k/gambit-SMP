package GambitRootProducerClosure { private import ScalarValues::*;
part def Root { attribute key:String; attribute sourcePath:String; attribute needle:String; attribute identity:String; attribute worker:String; attribute condition:String; }
part root0:Root { attribute :>> key="vm-body"; attribute :>> sourcePath="vendor/gambit/lib/mem.c"; attribute :>> needle="mark_array (work, ___BODY0_AS(___VM_SCMOBJ(___vms),___tSUBTYPED),"; attribute :>> identity="VM body cells"; attribute :>> worker="worker 0"; attribute :>> condition="VM epoch and fixed body layout"; }
part root1:Root { attribute :>> key="resize-request"; attribute :>> sourcePath="vendor/gambit/lib/mem.c"; attribute :>> needle="mark_array (work, &___vms->resize.thunk, 1);"; attribute :>> identity="address of resize.thunk"; attribute :>> worker="worker 0"; attribute :>> condition="Keep current serialized request root"; }
part root2:Root { attribute :>> key="intern-tables"; attribute :>> sourcePath="vendor/gambit/lib/mem.c"; attribute :>> needle="mark_array (work, &___GSTATE->symbol_table, 1);"; attribute :>> identity="symbol and keyword table cells"; attribute :>> worker="worker 0"; attribute :>> condition="Both table roots; symbol names are derived graph fields"; }
part root3:Root { attribute :>> key="global-cells"; attribute :>> sourcePath="vendor/gambit/lib/mem.c"; attribute :>> needle="int lo = (id * ___GLO_SUBLIST_COUNT) / np;"; attribute :>> identity="GLOCELL or VM glos element"; attribute :>> worker="floor interval per worker"; attribute :>> condition="Single VM partitions sublists; not equal cell counts"; }
part root4:Root { attribute :>> key="stack-frames"; attribute :>> sourcePath="vendor/gambit/lib/mem.c"; attribute :>> needle="___frame_root_cursor cursor = ___frame_root_begin (frame);"; attribute :>> identity="descriptor-selected FP_STK addresses"; attribute :>> worker="context participant worker"; attribute :>> condition="RETI/RETN decode and monotone gcmap runs; link forwarding handled separately"; }
part root5:Root { attribute :>> key="context-registers"; attribute :>> sourcePath="vendor/gambit/lib/mem.c"; attribute :>> needle="mark_array (work, context->r, sizeof(context->r)/sizeof(*context->r));"; attribute :>> identity="r element"; attribute :>> worker="context participant worker"; attribute :>> condition="Every register slot rewritten; equal values do not merge slots"; }
part root6:Root { attribute :>> key="saved-and-cache"; attribute :>> sourcePath="vendor/gambit/lib/mem.c"; attribute :>> needle="mark_array (work, context->saved, sizeof(context->saved)/sizeof(*context->saved));"; attribute :>> identity="saved and type_cache elements"; attribute :>> worker="context participant worker"; attribute :>> condition="Disjoint arrays; physical layout qualification still required"; }
part root7:Root { attribute :>> key="context-startup"; attribute :>> sourcePath="vendor/gambit/lib/mem.c"; attribute :>> needle="mark_array (work, &context->startup_thunk, 1);"; attribute :>> identity="startup_thunk and entry_marker addresses"; attribute :>> worker="context participant worker"; attribute :>> condition="Existing startup and marker adapters retained"; }
part root8:Root { attribute :>> key="processor-body"; attribute :>> sourcePath="vendor/gambit/lib/mem.c"; attribute :>> needle="mark_array (work, ___BODY0_AS(___CONTEXT_PROCESSOR_SCMOBJ(context),___tSUBTYPED),"; attribute :>> identity="processor Scheme body cells"; attribute :>> worker="context participant worker"; attribute :>> condition="Current thread reaches denv through ordinary graph traversal"; }
part root9:Root { attribute :>> key="rc-data"; attribute :>> sourcePath="vendor/gambit/lib/mem.c"; attribute :>> needle="mark_array (work, &h->data, 1);"; attribute :>> identity="RC node data address"; attribute :>> worker="context participant worker"; attribute :>> condition="Each context list scanned; external writer freeze is a separate admission obligation"; }
part root10:Root { attribute :>> key="externally-held-still"; attribute :>> sourcePath="vendor/gambit/lib/mem.c"; attribute :>> needle="if (base[___STILL_REFCOUNT] == 0)"; attribute :>> identity="positive-refcount still object seed"; attribute :>> worker="context allocation-region worker"; attribute :>> condition="Not a synthetic Scheme slot; seed list produces object fields"; }
part root11:Root { attribute :>> key="continuation-graph"; attribute :>> sourcePath="vendor/gambit/lib/mem.c"; attribute :>> needle="mark_captured_continuation (work, &body[___CONTINUATION_FRAME]);"; attribute :>> identity="captured frame link and denv fields"; attribute :>> worker="winning copier or lock owner then chunk scanner"; attribute :>> condition="Graph roots are not a second flat root table; special frame copy lock applies"; }
part root12:Root { attribute :>> key="weak-and-local-roots"; attribute :>> sourcePath="vendor/gambit/lib/mem.c"; attribute :>> needle="mark_array (work, &will, 1);"; attribute :>> identity="temporary will and weak graph slots"; attribute :>> worker="weak phase worker"; attribute :>> condition="Strong root closure excludes later process_wills and foreign cleanup"; }
part def Flow { attribute key:String; attribute sourcePath:String; attribute needle:String; attribute nextNode:String; attribute custody:String; attribute diagramLabel:String; }
part flow0:Flow { attribute :>> key="forward"; attribute :>> sourcePath="vendor/gambit/lib/mem.c"; attribute :>> needle="___COMPARE_AND_SWAP_WORD(&body[-1],"; attribute :>> nextNode="copying"; attribute :>> custody="Winner retains initialization and first-field Tail; losers rewrite their own slot"; attribute :>> diagramLabel="winner owns payload"; }
part flow1:Flow { attribute :>> key="initialize"; attribute :>> sourcePath="vendor/gambit/lib/mem.c"; attribute :>> needle="*alloc++ = *body++;"; attribute :>> nextNode="publish"; attribute :>> custody="Payload initialized before completed chunk publication"; attribute :>> diagramLabel="initialized payload"; }
part flow2:Flow { attribute :>> key="publish"; attribute :>> sourcePath="vendor/gambit/lib/mem.c"; attribute :>> needle="heap_chunks_to_scan_tail = new_tail;"; attribute :>> nextNode="claim"; attribute :>> custody="FIFO lock plus content/link visibility; not forwarding CAS"; attribute :>> diagramLabel="release FIFO publish"; }
part flow3:Flow { attribute :>> key="claim"; attribute :>> sourcePath="vendor/gambit/lib/mem.c"; attribute :>> needle="scan_complete_heap_chunk (work, ptr+1);"; attribute :>> nextNode="scan"; attribute :>> custody="Dequeued chunk remains owned by active scanner after unlock"; attribute :>> diagramLabel="transfer scan custody"; }
part flow4:Flow { attribute :>> key="scan"; attribute :>> sourcePath="vendor/gambit/lib/mem.c"; attribute :>> needle="mark_array (work, body+1, words-1);"; attribute :>> nextNode="idle"; attribute :>> custody="Current generic movable scan skips first field assigned to winner Tail; prior direct PAIR macro is retired"; attribute :>> diagramLabel="skip Tail field"; }
part flow5:Flow { attribute :>> key="private"; attribute :>> sourcePath="vendor/gambit/lib/mem.c"; attribute :>> needle="ptr = alloc_heap_chunk_start;"; attribute :>> nextNode="idle"; attribute :>> custody="Private incomplete chunk scanned locally before idle"; attribute :>> diagramLabel="drain private work"; }
part flow6:Flow { attribute :>> key="idle"; attribute :>> sourcePath="vendor/gambit/lib/mem.c"; attribute :>> needle="if (--(*workers_count) == 0)"; attribute :>> nextNode="strong-cut"; attribute :>> custody="Last-use local drain and steal precede mutex count decrement"; attribute :>> diagramLabel="last active decrement"; }
part flow7:Flow { attribute :>> key="strong-cut"; attribute :>> sourcePath="vendor/gambit/lib/mem.c"; attribute :>> needle="process_wills (work);"; attribute :>> nextNode="weak-cut"; attribute :>> custody="Weak producers and second termination round remain mandatory"; attribute :>> diagramLabel="weak work reopens scan"; }
part flow8:Flow { attribute :>> key="weak-cut"; attribute :>> sourcePath="vendor/gambit/lib/mem.c"; attribute :>> needle="free_unmarked_still_objs (work);"; attribute :>> nextNode="cleanup"; attribute :>> custody="Foreign release side effects are outside strong termination proof"; attribute :>> diagramLabel="cleanup remains"; }
part flow9:Flow { attribute :>> key="frame-lock"; attribute :>> sourcePath="vendor/gambit/lib/mem.c"; attribute :>> needle="MISC_MEM_LOCK();\n\n      next_frame:"; attribute :>> nextNode="publish"; attribute :>> custody="Special frame-copy producer requires the MISC_MEM_LOCK path audited independently"; attribute :>> diagramLabel="frame copier lock"; }
part def Obligation { attribute key:String; attribute status:String; attribute scope:String; }
part obligation0:Obligation { attribute :>> key="slot-identity"; attribute :>> status="open"; attribute :>> scope="Source families enumerated; no exhaustive generated slot certificate or arbitrary FFI closure"; }
part obligation1:Obligation { attribute :>> key="alias-coverage"; attribute :>> status="conditional-proved"; attribute :>> scope="Physical slot quotient preserves updates; object-value dedup counterexample"; }
part obligation2:Obligation { attribute :>> key="worker-assignment"; attribute :>> status="conditional-proved"; attribute :>> scope="Disjoint exhaustive provider sets imply unique owner; current floor partitions preserved"; }
part obligation3:Obligation { attribute :>> key="producer-custody"; attribute :>> status="bounded-checked"; attribute :>> scope="One winner one chunk two roles; Tail and dequeued work remain active"; }
part obligation4:Obligation { attribute :>> key="c11-publication"; attribute :>> status="open"; attribute :>> scope="Current volatile barriers and lock macros need effective-config C11 refinement"; }
part obligation5:Obligation { attribute :>> key="typed-ir-bridge"; attribute :>> status="open"; attribute :>> scope="Actual Quint typed IR retained; manual Lean mirror not extraction proof"; }
part obligation6:Obligation { attribute :>> key="whole-gc-closure"; attribute :>> status="open"; attribute :>> scope="Still lists frame copier weak phases foreign release and external writers not fully simulated"; }
part def Gain { attribute key:String; attribute avoided:String; attribute added:String; attribute condition:String; }
part gain0:Gain { attribute :>> key="resize reuse"; attribute :>> avoided="0 extra general directory for existing request"; attribute :>> added="Retain existing VM thunk and context adapters"; attribute :>> condition="No new concurrent provider requirement"; }
part gain1:Gain { attribute :>> key="slot canonicalization"; attribute :>> avoided="D-C duplicate descriptors only; never equal-valued distinct slots"; attribute :>> added="O(D) expected indexing plus O(C) stable metadata and generation validation"; attribute :>> condition="Duplicate descriptors measured and avoided visits exceed index plus freeze cost"; }
part gain2:Gain { attribute :>> key="worker balance"; attribute :>> avoided="At most max(load_i)-ceil(total/W) removable unit-cost imbalance"; attribute :>> added="Enumeration scheduling and cross-worker locality cost"; attribute :>> condition="Existing globals already partitioned; recursive graph skew remains"; }
part gain3:Gain { attribute :>> key="publisher counter fusion"; attribute :>> avoided="0 additional counter RMW per synchronous publication"; attribute :>> added="Keep active worker until initialization Tail and local drain settle"; attribute :>> condition="Every publisher covered by active carrier; detached producers invalidate fusion"; }
part gain4:Gain { attribute :>> key="generic manifest"; attribute :>> avoided="Repeated independent provider discovery and N adapters can share one protocol"; attribute :>> added="Snapshot freeze pin generation and retirement per provider"; attribute :>> condition="R*(saved discovery+saved coordination) > setup+R*(freeze+index+leases+extra visits)"; }
part gain5:Gain { attribute :>> key="modern C baseline"; attribute :>> avoided="No second language needed for this protocol"; attribute :>> added="Generated descriptors C11 atomics and source qualifications remain"; attribute :>> condition="Zig not justified by root partitioning alone"; }
part def Binding { attribute actionName:String; attribute lemma:String; attribute condition:String; }
part binding0:Binding { attribute :>> actionName="publish"; attribute :>> lemma="publishPreserves"; attribute :>> condition="Payload before FIFO visibility"; }
part binding1:Binding { attribute :>> actionName="claim"; attribute :>> lemma="claimPreserves"; attribute :>> condition="Lock-step head removal transfers custody"; }
part binding2:Binding { attribute :>> actionName="idleProducer"; attribute :>> lemma="idlePreserves"; attribute :>> condition="Tail and private chunk block idle"; }
part history:GambitAssuranceRouting::ModelNeed { ref part :>> owner=GambitBuildAssurance::planner.component; attribute :>> obligationId="RPC-history"; attribute :>> kind="interleaving"; attribute :>> subjectPath="dev/refactoring/modern-c/models/quint/root_producer_closure.qnt"; attribute :>> subjectScope="one-copy two-role custody and two canonical root slots"; attribute :>> premise="Formal study only; no native acceptance"; }
part induction:GambitAssuranceRouting::ModelNeed { ref part :>> owner=GambitBuildAssurance::planner.component; attribute :>> obligationId="RPC-induction"; attribute :>> kind="induction"; attribute :>> subjectPath="dev/refactoring/modern-c/models/lean/RootProducerClosure.lean"; attribute :>> subjectScope="physical-slot coverage and three selected guarded transitions"; attribute :>> premise="Formal study only; no native acceptance"; }
part source:GambitAssuranceRouting::ModelNeed { ref part :>> owner=GambitBuildAssurance::planner.component; attribute :>> obligationId="RPC-source"; attribute :>> kind="source-refinement"; attribute :>> subjectPath="dev/refactoring/modern-c/root-producer-closure-design.org"; attribute :>> subjectScope="bounded source inventory; full runtime refinement unresolved"; attribute :>> premise="Formal study only; no native acceptance"; }
part bridge:GambitAssuranceRouting::ModelNeed { ref part :>> owner=GambitBuildAssurance::planner.component; attribute :>> obligationId="RPC-bridge"; attribute :>> kind="expression-refinement"; attribute :>> subjectPath="dev/refactoring/modern-c/models/quint/root_producer_closure.qnt"; attribute :>> subjectScope="actual typed IR to manual Lean semantic mirror unresolved"; attribute :>> premise="Formal study only; no native acceptance"; }
ref part roots:GambitRuntimeComposition::BlueprintModule=GambitRuntimeComposition::blueprintModule3;
ref part collector:GambitRuntimeComposition::BlueprintModule=GambitRuntimeComposition::blueprintModule4;
ref part control:GambitRuntimeComposition::BlueprintModule=GambitRuntimeComposition::blueprintModule5;

part def Parameter { attribute key:String; attribute sourcePath:String; attribute needle:String; attribute value:String; }
part parameter0:Parameter { attribute :>> key="registers"; attribute :>> sourcePath="vendor/gambit/include/gambit.h.in"; attribute :>> needle="#define ___NB_GVM_REGS 5"; attribute :>> value="5"; }
part parameter1:Parameter { attribute :>> key="saved"; attribute :>> sourcePath="vendor/gambit/include/gambit.h.in"; attribute :>> needle="___WORD saved[3];"; attribute :>> value="3"; }
part parameter2:Parameter { attribute :>> key="type-cache"; attribute :>> sourcePath="vendor/gambit/include/gambit.h.in"; attribute :>> needle="___WORD type_cache[2];"; attribute :>> value="2"; }
part parameter3:Parameter { attribute :>> key="processor-body"; attribute :>> sourcePath="vendor/gambit/include/gambit.h.in"; attribute :>> needle="#define ___PROCESSOR_SIZE 22"; attribute :>> value="22"; }
part parameter4:Parameter { attribute :>> key="vm-body"; attribute :>> sourcePath="vendor/gambit/include/gambit.h.in"; attribute :>> needle="#define ___VM_SIZE 20"; attribute :>> value="20"; }
part def DiagramEdge { attribute fromNode:String; attribute toNode:String; attribute label:String; }
part diagramedge0:DiagramEdge { attribute :>> fromNode="copying"; attribute :>> toNode="initialize"; attribute :>> label="winner copies payload"; }
part diagramedge1:DiagramEdge { attribute :>> fromNode="forward"; attribute :>> toNode="tail"; attribute :>> label="winner reserves first field"; }
part diagramedge2:DiagramEdge { attribute :>> fromNode="tail"; attribute :>> toNode="idle"; attribute :>> label="settled Tail required"; }
part diagramedge3:DiagramEdge { attribute :>> fromNode="publish"; attribute :>> toNode="tail"; attribute :>> label="Tail may remain pending"; }

part flow10:Flow { attribute :>> key="synchronous-binding"; attribute :>> sourcePath="vendor/gambit/lib/mem.c"; attribute :>> needle="if (work->context != ___ps->context || work->carrier != ___ps)"; attribute :>> nextNode="idle"; attribute :>> custody="Current runtime enforces worker context and native carrier identity"; attribute :>> diagramLabel="carrier binding"; }
part flow11:Flow { attribute :>> key="round-counters"; attribute :>> sourcePath="vendor/gambit/lib/mem.c"; attribute :>> needle="scan_workers_count[0] = np;"; attribute :>> nextNode="idle"; attribute :>> custody="Setup initializes separate strong and weak active counts"; attribute :>> diagramLabel="two round counters"; }

part flow12:Flow { attribute :>> key="object-ready"; attribute :>> sourcePath="vendor/gambit/lib/mem.c"; attribute :>> needle="publish_object_scan (work, copy_header);"; attribute :>> nextNode="publish"; attribute :>> custody="Current concurrent source separately publishes initialized-object scan authority; not proved by this study"; attribute :>> diagramLabel="publish scan readiness"; }
part flow13:Flow { attribute :>> key="object-authority"; attribute :>> sourcePath="vendor/gambit/lib/mem.c"; attribute :>> needle="GC_SCAN_OWNED,GC_SCAN_DONE"; attribute :>> nextNode="scan"; attribute :>> custody="Current object scan state transition excludes duplicate graph-field mutation; chunk ownership remains distinct"; attribute :>> diagramLabel="object scan completion"; }
part obligation7:Obligation { attribute :>> key="object-scan-authority"; attribute :>> status="open"; attribute :>> scope="New concurrent source READY OWNED DONE transitions and duplicate-task behavior need separate QNT refinement; current one-chunk model assumes one consumer"; }
part gain6:Gain { attribute :>> key="current scan authority"; attribute :>> avoided="Repeated graph-field mutation from duplicate chunk/frontier tasks"; attribute :>> added="Per-object UNPUBLISHED to READY to OWNED to DONE transitions plus section lookup and CAS retries"; attribute :>> condition="Current concurrent runtime change only; model-source refinement and performance remain unqualified"; }
}
