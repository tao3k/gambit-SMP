package GambitNativeBindingPlanRetirement { private import ScalarValues::*;
part def SourceRow { attribute key:String; attribute path:String; attribute needle:String; attribute obligation:String; }
part source0:SourceRow { attribute :>> key="begin"; attribute :>> path="vendor/gambit/gsc/_t-c-1.scm"; attribute :>> needle="(set! targ-glo-vars         (make-table 'test: eq?))"; attribute :>> obligation="Session reset replaces table identity"; }
part source1:SourceRow { attribute :>> key="end"; attribute :>> path="vendor/gambit/gsc/_t-c-1.scm"; attribute :>> needle="(set! targ-glo-vars #f)"; attribute :>> obligation="End is after normal heap-dump return; not a universal unwind guard"; }
part source2:SourceRow { attribute :>> key="entry"; attribute :>> path="vendor/gambit/gsc/_t-c-1.scm"; attribute :>> needle="(table-ref targ-glo-vars glo #f)"; attribute :>> obligation="Mutable table entry aliases resource and index cell"; }
part source3:SourceRow { attribute :>> key="demand"; attribute :>> path="vendor/gambit/gsc/_t-c-1.scm"; attribute :>> needle="(targ-rsrc-demanders-set! (cdr x) '(\"\"))"; attribute :>> obligation="First use can change resource value"; }
part source4:SourceRow { attribute :>> key="supplier"; attribute :>> path="vendor/gambit/gsc/_t-c-1.scm"; attribute :>> needle="(targ-rsrc-suppliers-set! (cdr x) '(\"\"))"; attribute :>> obligation="Separate supply writer"; }
part source5:SourceRow { attribute :>> key="insert"; attribute :>> path="vendor/gambit/gsc/_t-c-1.scm"; attribute :>> needle="(table-set! targ-glo-vars glo (cons y r))"; attribute :>> obligation="Missing entry means allocation and insertion, not readonly access"; }
part source6:SourceRow { attribute :>> key="resource-alias"; attribute :>> path="vendor/gambit/gsc/_t-c-1.scm"; attribute :>> needle="(cddr g)"; attribute :>> obligation="Entry list holds the same resource vector"; }
part source7:SourceRow { attribute :>> key="shallow"; attribute :>> path="vendor/gambit/gsc/_t-c-1.scm"; attribute :>> needle="(map targ-glo-rsrc glo-list)"; attribute :>> obligation="Roster snapshot retains same vectors"; }
part source8:SourceRow { attribute :>> key="header"; attribute :>> path="vendor/gambit/gsc/_t-c-1.scm"; attribute :>> needle="(targ-write-rsrc-names 'globals-s-nd"; attribute :>> obligation="Last direct demand-classification consumer in ordinary module emission"; }
part source9:SourceRow { attribute :>> key="layout"; attribute :>> path="vendor/gambit/gsc/_t-c-1.scm"; attribute :>> needle="(targ-cell-set! (cadr g) i)"; attribute :>> obligation="Resolved index must be copied by value"; }
part source10:SourceRow { attribute :>> key="loop"; attribute :>> path="vendor/gambit/gsc/_t-c-1.scm"; attribute :>> needle="(targ-use-glo (string->symbol name) #f)"; attribute :>> obligation="One lexical helper call executes in both binding loops"; }
part source11:SourceRow { attribute :>> key="prm"; attribute :>> path="vendor/gambit/gsc/_t-c-1.scm"; attribute :>> needle="(def-mod-prm-glo \"DEF_MOD_PRM\")"; attribute :>> obligation="First binding loop"; }
part source12:SourceRow { attribute :>> key="glo"; attribute :>> path="vendor/gambit/gsc/_t-c-1.scm"; attribute :>> needle="(def-mod-prm-glo \"DEF_MOD_GLO\")"; attribute :>> obligation="Second binding loop"; }
part source13:SourceRow { attribute :>> key="init-text"; attribute :>> path="vendor/gambit/gsc/_t-c-1.scm"; attribute :>> needle="(targ-display x)"; attribute :>> obligation="C initializer is output text here, not executing native C during compilation"; }
part source14:SourceRow { attribute :>> key="symbol-output"; attribute :>> path="vendor/gambit/gsc/_t-c-1.scm"; attribute :>> needle="(targ-code* (list \"DEF_MOD_SYM\""; attribute :>> obligation="Post-GLO name and symbol-cell output does not read demanders directly"; }
part source15:SourceRow { attribute :>> key="keyword-output"; attribute :>> path="vendor/gambit/gsc/_t-c-1.scm"; attribute :>> needle="(targ-code* (list \"DEF_MOD_KEY\""; attribute :>> obligation="Post-GLO keyword output independent of demander list directly"; }
part source16:SourceRow { attribute :>> key="cell"; attribute :>> path="vendor/gambit/gsc/_t-c-1.scm"; attribute :>> needle="((cell)        (targ-code tail))"; attribute :>> obligation="Deferred index-cell encoder reads cdr and may observe changed cell"; }
part source17:SourceRow { attribute :>> key="cell-write"; attribute :>> path="vendor/gambit/gsc/_t-c-1.scm"; attribute :>> needle="(set-cdr! x y)"; attribute :>> obligation="Cell object is mutable and shared; readonly plan copies resolved integer"; }
part source18:SourceRow { attribute :>> key="port"; attribute :>> path="vendor/gambit/gsc/_t-c-1.scm"; attribute :>> needle="(display x targ-port)"; attribute :>> obligation="Port execution is an exception/reentry boundary, not proven inert"; }
part source19:SourceRow { attribute :>> key="close"; attribute :>> path="vendor/gambit/gsc/_t-c-1.scm"; attribute :>> needle="(close-output-port targ-port)"; attribute :>> obligation="Close can fail; no successful receipt on unknown outcome"; }
part source20:SourceRow { attribute :>> key="header-read"; attribute :>> path="vendor/gambit/gsc/_t-c-1.scm"; attribute :>> needle="(read in)"; attribute :>> obligation="Linker re-reads serialized header rather than live compile resource vectors"; }
part source21:SourceRow { attribute :>> key="reconstruct"; attribute :>> path="vendor/gambit/gsc/_t-c-1.scm"; attribute :>> needle="(targ-make-rsrc glo '() (list file))"; attribute :>> obligation="Rebuilt linker resources retain header s-nd classification"; }
part source22:SourceRow { attribute :>> key="union"; attribute :>> path="vendor/gambit/gsc/_t-c-1.scm"; attribute :>> needle="(append (targ-rsrc-demanders r1)"; attribute :>> obligation="Union creates new overlap vector but may retain unmatched vectors"; }
part source23:SourceRow { attribute :>> key="difference"; attribute :>> path="vendor/gambit/gsc/_t-c-1.scm"; attribute :>> needle="(define (targ-difference-rsrc lst1 lst2)"; attribute :>> obligation="Difference can return shared list suffix"; }
part source24:SourceRow { attribute :>> key="warnings"; attribute :>> path="vendor/gambit/gsc/_t-c-1.scm"; attribute :>> needle="(targ-validate-rsrc glo-rsrc)"; attribute :>> obligation="Warnings depend on reconstructed demander/supplier lists, before link header"; }
part source25:SourceRow { attribute :>> key="warning-read"; attribute :>> path="vendor/gambit/gsc/_t-c-1.scm"; attribute :>> needle="(demanders (targ-rsrc-demanders r))"; attribute :>> obligation="Not evidence of a post-helper reader in ordinary module emission"; }
part source26:SourceRow { attribute :>> key="link-supply"; attribute :>> path="vendor/gambit/gsc/_t-c-1.scm"; attribute :>> needle="(list (if (targ-rsrc-supplied? r)"; attribute :>> obligation="Linkfile branch uses supplier role, not ordinary compile demand mutation"; }
part source27:SourceRow { attribute :>> key="exception"; attribute :>> path="vendor/gambit/gsc/_utils.scm"; attribute :>> needle="(set! throw-to-exception-handler cont)"; attribute :>> obligation="Compiler error handler itself captures continuation"; }
part source28:SourceRow { attribute :>> key="restore-handler"; attribute :>> path="vendor/gambit/gsc/_utils.scm"; attribute :>> needle="(set! throw-to-exception-handler old-exception-handler)"; attribute :>> obligation="Restoration is plain control-flow statement, not dynamic-wind"; }
part source29:SourceRow { attribute :>> key="arg-order"; attribute :>> path="vendor/gambit/gsc/_front.scm"; attribute :>> needle="(define (arg-eval-order oper nodes)"; attribute :>> obligation="Current compiler has explicit operand-order heuristic; do not infer host binary order"; }
part source30:SourceRow { attribute :>> key="throw"; attribute :>> path="vendor/gambit/gsc/_utils.scm"; attribute :>> needle="(define (compiler-abort)"; attribute :>> obligation="Trace error escape to captured handler"; }
part source31:SourceRow { attribute :>> key="compile-guard"; attribute :>> path="vendor/gambit/gsc/_front.scm"; attribute :>> needle="(with-exception-handling"; attribute :>> obligation="Top-level catches do not imply resource rollback"; }
part def ObserverRow { attribute key:String; attribute phase:String; attribute reads:String; attribute aliases:String; attribute conclusion:String; }
part observer0:ObserverRow { attribute :>> key="header"; attribute :>> phase="before helpers"; attribute :>> reads="names demanders suppliers"; attribute :>> aliases="glo-rsrc shares resource vectors"; attribute :>> conclusion="Must preserve original value snapshot"; }
part observer1:ObserverRow { attribute :>> key="layout"; attribute :>> phase="before helpers"; attribute :>> reads="supplier partition names index cells"; attribute :>> aliases="glo-list contains table entry pairs"; attribute :>> conclusion="Freeze after resolved indices; prohibit retained mutable cell"; }
part observer2:ObserverRow { attribute :>> key="ordinary-tail"; attribute :>> phase="during and after helpers"; attribute :>> reads="binding names labels indices; sym/key names; output state"; attribute :>> aliases="objs and cells remain reachable"; attribute :>> conclusion="No named direct demand-list reader found here; alias closure still OPEN"; }
part observer3:ObserverRow { attribute :>> key="linker"; attribute :>> phase="later invocation"; attribute :>> reads="header bytes then reconstructed records"; attribute :>> aliases="New maps; union/difference share within linker graph"; attribute :>> conclusion="Do not substitute post-helper canonical demand for header roles"; }
part observer4:ObserverRow { attribute :>> key="escaped"; attribute :>> phase="any output boundary"; attribute :>> reads="arbitrary backend tables/vector fields via exposed capability"; attribute :>> aliases="Global table raw vector and mutable strings"; attribute :>> conclusion="Must close capability or retain metadata effect/reject"; }
part observer5:ObserverRow { attribute :>> key="continuation"; attribute :>> phase="suspend/reenter/exception"; attribute :>> reads="saved locals plus process-global targ state"; attribute :>> aliases="Old locals can coexist with new global table"; attribute :>> conclusion="Epoch and operation identity plus cleanup and pinned plan required"; }
part def ClaimRow { attribute key:String; attribute mechanism:String; attribute condition:String; attribute result:String; attribute gap:String; }
part claim0:ClaimRow { attribute :>> key="elide"; attribute :>> mechanism="Unobserved metadata projection"; attribute :>> condition="Complete observer and writer closure; no fault-prefix change"; attribute :>> result="Readonly both loops may remove two demand writes"; attribute :>> gap="Whole-source and all exceptional observations OPEN"; }
part claim1:ClaimRow { attribute :>> key="preserve"; attribute :>> mechanism="First logical normalization outside emitter"; attribute :>> condition="Same cut and alias-visible state; no intervening writer"; attribute :>> result="Second normalization can be removed by exact value algebra"; attribute :>> gap="Moving first effect is not eliminating it; no rollback by assumption"; }
part claim2:ClaimRow { attribute :>> key="reentry"; attribute :>> mechanism="Pinned plan and generation-scoped operation"; attribute :>> condition="Retry distinct from genuine repeated execution"; attribute :>> result="Stale resume rejected; new operation gets new output context"; attribute :>> gap="Rejecting legacy unrestricted continuation is admission change, not equivalence"; }
part claim3:ClaimRow { attribute :>> key="errors"; attribute :>> mechanism="Typed deferred fault at equivalent cut"; attribute :>> condition="Original order and visible byte prefix established"; attribute :>> result="No success receipt for partial or unknown output"; attribute :>> gap="OOM timing and actual host argument order OPEN"; }
part def GainRow { attribute key:String; attribute avoided:String; attribute added:String; attribute condition:String; }
part gain0:GainRow { attribute :>> key="elision"; attribute :>> avoided="2P late table lookups and metadata setters; P=455 suggests 910 helper uses in matching artifact generation"; attribute :>> added="P owned plans; two readonly consumers; certification and lifetime costs"; attribute :>> condition="No alias observer or intervening writer; lookup/encoding work may move to planning"; }
part gain1:GainRow { attribute :>> key="preserve"; attribute :>> avoided="At most P second metadata normalizations after first retained"; attribute :>> added="P logical first effects plus plan ownership"; attribute :>> condition="No intervening mutation and exact list-value equality; physical identity not automatically covered"; }
part gain2:GainRow { attribute :>> key="allocation"; attribute :>> avoided="Repeated transient tuple/name work may be shared"; attribute :>> added="Owned name/label/index plus O(P) plan and O(C) byte verification"; attribute :>> condition="No measured allocation or speed saving; OOM order needs separate semantic choice"; }
part gain3:GainRow { attribute :>> key="incremental"; attribute :>> avoided="Stable immutable binding result can be reused across consumers"; attribute :>> added="Keys include header role cut, generator, ABI, target and session-affecting inputs"; attribute :>> condition="No mutable cell/address identity in persistent key; invalidation and complete writer closure external"; }
part gain4:GainRow { attribute :>> key="net"; attribute :>> avoided="Duplicate lookup/encoding work D plus certified redundant setters W"; attribute :>> added="Plan K + ownership S + verifier V + qualification A"; attribute :>> condition="Positive only if D+W>K+S+V+A; modern C23 baseline; not person-days"; }
part gain5:GainRow { attribute :>> key="darwin"; attribute :>> avoided="No direct compile-time saving established for same C bytes"; attribute :>> added="Toolchain capability admission and native artifact reuse design"; attribute :>> condition="Do not infer reduction of macro expansion or GCC cold latency from helper counts"; }
part def ContractRow { attribute fromNode:String; attribute toNode:String; attribute custody:String; }
part contract0:ContractRow { attribute :>> fromNode="Discovery"; attribute :>> toNode="Header snapshot"; attribute :>> custody="roles at cut"; }
part contract1:ContractRow { attribute :>> fromNode="Header snapshot"; attribute :>> toNode="Resolved layout"; attribute :>> custody="preserve header"; }
part contract2:ContractRow { attribute :>> fromNode="Resolved layout"; attribute :>> toNode="Owned binding plan"; attribute :>> custody="copy values"; }
part contract3:ContractRow { attribute :>> fromNode="Owned binding plan"; attribute :>> toNode="Elision admission"; attribute :>> custody="observer closure"; }
part contract4:ContractRow { attribute :>> fromNode="Owned binding plan"; attribute :>> toNode="Metadata adapter"; attribute :>> custody="retain first effect"; }
part contract5:ContractRow { attribute :>> fromNode="Elision admission"; attribute :>> toNode="Readonly PRM"; attribute :>> custody="first covered"; }
part contract6:ContractRow { attribute :>> fromNode="Metadata adapter"; attribute :>> toNode="Readonly PRM"; attribute :>> custody="same logical cut"; }
part contract7:ContractRow { attribute :>> fromNode="Readonly PRM"; attribute :>> toNode="C init text"; attribute :>> custody="ordered bytes"; }
part contract8:ContractRow { attribute :>> fromNode="C init text"; attribute :>> toNode="Readonly GLO"; attribute :>> custody="second covered"; }
part contract9:ContractRow { attribute :>> fromNode="Readonly GLO"; attribute :>> toNode="Completion guard"; attribute :>> custody="close + verify"; }
part contract10:ContractRow { attribute :>> fromNode="Completion guard"; attribute :>> toNode="Receipt"; attribute :>> custody="generation valid"; }
part contract11:ContractRow { attribute :>> fromNode="Owned binding plan"; attribute :>> toNode="Suspended context"; attribute :>> custody="pin lifetime"; }
part contract12:ContractRow { attribute :>> fromNode="Suspended context"; attribute :>> toNode="Completion guard"; attribute :>> custody="resume or retain"; }
part def BindingRow { attribute actionName:String; attribute lemma:String; attribute scope:String; }
part binding0:BindingRow { attribute :>> actionName="native_binding_plan_retirement.discover"; attribute :>> lemma="NativeBindingPlan.discoverPreserves"; attribute :>> scope="Actual typed IR action; source observer and fault equivalence external"; }
part binding1:BindingRow { attribute :>> actionName="native_binding_plan_retirement.resolve"; attribute :>> lemma="NativeBindingPlan.resolvePreserves"; attribute :>> scope="Actual typed IR action; source observer and fault equivalence external"; }
part binding2:BindingRow { attribute :>> actionName="native_binding_plan_retirement.closeWriters"; attribute :>> lemma="NativeBindingPlan.closeWritersPreserves"; attribute :>> scope="Actual typed IR action; source observer and fault equivalence external"; }
part binding3:BindingRow { attribute :>> actionName="native_binding_plan_retirement.admitElision"; attribute :>> lemma="NativeBindingPlan.admitElisionPreserves"; attribute :>> scope="Actual typed IR action; source observer and fault equivalence external"; }
part binding4:BindingRow { attribute :>> actionName="native_binding_plan_retirement.requireMetadata"; attribute :>> lemma="NativeBindingPlan.requireMetadataPreserves"; attribute :>> scope="Actual typed IR action; source observer and fault equivalence external"; }
part binding5:BindingRow { attribute :>> actionName="native_binding_plan_retirement.writeHeader"; attribute :>> lemma="NativeBindingPlan.writeHeaderPreserves"; attribute :>> scope="Actual typed IR action; source observer and fault equivalence external"; }
part binding6:BindingRow { attribute :>> actionName="native_binding_plan_retirement.sealPlan"; attribute :>> lemma="NativeBindingPlan.sealPlanPreserves"; attribute :>> scope="Actual typed IR action; source observer and fault equivalence external"; }
part binding7:BindingRow { attribute :>> actionName="native_binding_plan_retirement.firstElide"; attribute :>> lemma="NativeBindingPlan.firstElidePreserves"; attribute :>> scope="Actual typed IR action; source observer and fault equivalence external"; }
part binding8:BindingRow { attribute :>> actionName="native_binding_plan_retirement.firstPreserve"; attribute :>> lemma="NativeBindingPlan.firstPreservePreserves"; attribute :>> scope="Actual typed IR action; source observer and fault equivalence external"; }
part binding9:BindingRow { attribute :>> actionName="native_binding_plan_retirement.emitPrm"; attribute :>> lemma="NativeBindingPlan.emitPrmPreserves"; attribute :>> scope="Actual typed IR action; source observer and fault equivalence external"; }
part binding10:BindingRow { attribute :>> actionName="native_binding_plan_retirement.secondElide"; attribute :>> lemma="NativeBindingPlan.secondElidePreserves"; attribute :>> scope="Actual typed IR action; source observer and fault equivalence external"; }
part binding11:BindingRow { attribute :>> actionName="native_binding_plan_retirement.secondPreserve"; attribute :>> lemma="NativeBindingPlan.secondPreservePreserves"; attribute :>> scope="Actual typed IR action; source observer and fault equivalence external"; }
part binding12:BindingRow { attribute :>> actionName="native_binding_plan_retirement.emitGlo"; attribute :>> lemma="NativeBindingPlan.emitGloPreserves"; attribute :>> scope="Actual typed IR action; source observer and fault equivalence external"; }
part binding13:BindingRow { attribute :>> actionName="native_binding_plan_retirement.closeOutput"; attribute :>> lemma="NativeBindingPlan.closeOutputPreserves"; attribute :>> scope="Actual typed IR action; source observer and fault equivalence external"; }
part binding14:BindingRow { attribute :>> actionName="native_binding_plan_retirement.issue"; attribute :>> lemma="NativeBindingPlan.issuePreserves"; attribute :>> scope="Actual typed IR action; source observer and fault equivalence external"; }
part binding15:BindingRow { attribute :>> actionName="native_binding_plan_retirement.pause"; attribute :>> lemma="NativeBindingPlan.pausePreserves"; attribute :>> scope="Actual typed IR action; source observer and fault equivalence external"; }
part binding16:BindingRow { attribute :>> actionName="native_binding_plan_retirement.resumeSame"; attribute :>> lemma="NativeBindingPlan.resumeSamePreserves"; attribute :>> scope="Actual typed IR action; source observer and fault equivalence external"; }
part binding17:BindingRow { attribute :>> actionName="native_binding_plan_retirement.foreignReentry"; attribute :>> lemma="NativeBindingPlan.foreignReentryPreserves"; attribute :>> scope="Actual typed IR action; source observer and fault equivalence external"; }
part binding18:BindingRow { attribute :>> actionName="native_binding_plan_retirement.lateWriter"; attribute :>> lemma="NativeBindingPlan.lateWriterPreserves"; attribute :>> scope="Actual typed IR action; source observer and fault equivalence external"; }
part binding19:BindingRow { attribute :>> actionName="native_binding_plan_retirement.escapedObserver"; attribute :>> lemma="NativeBindingPlan.escapedObserverPreserves"; attribute :>> scope="Actual typed IR action; source observer and fault equivalence external"; }
part binding20:BindingRow { attribute :>> actionName="native_binding_plan_retirement.unknownExit"; attribute :>> lemma="NativeBindingPlan.unknownExitPreserves"; attribute :>> scope="Actual typed IR action; source observer and fault equivalence external"; }
part binding21:BindingRow { attribute :>> actionName="native_binding_plan_retirement.rejectResume"; attribute :>> lemma="NativeBindingPlan.rejectResumePreserves"; attribute :>> scope="Actual typed IR action; source observer and fault equivalence external"; }
part def ProofRow { attribute key:String; attribute lemma:String; }
part proof0:ProofRow { attribute :>> key="all-step"; attribute :>> lemma="NativeBindingPlan.stepPreserves"; }
part proof1:ProofRow { attribute :>> key="reachable"; attribute :>> lemma="NativeBindingPlan.reachableSafe"; }
part proof2:ProofRow { attribute :>> key="header"; attribute :>> lemma="NativeBindingPlan.headerUnaffectedByFirst"; }
part proof3:ProofRow { attribute :>> key="custody"; attribute :>> lemma="NativeBindingPlan.unknownKeepsCustody"; }
part proof4:ProofRow { attribute :>> key="close"; attribute :>> lemma="NativeBindingPlan.finalNeedsClose"; }
part proof5:ProofRow { attribute :>> key="public-first"; attribute :>> lemma="NativeBindingRefinement.firstPublicEquivalent"; }
part proof6:ProofRow { attribute :>> key="public-both"; attribute :>> lemma="NativeBindingRefinement.bothPublicEquivalent"; }
part proof7:ProofRow { attribute :>> key="second"; attribute :>> lemma="NativeBindingRefinement.secondMetadataEquivalent"; }
part proof8:ProofRow { attribute :>> key="first-canonical"; attribute :>> lemma="NativeBindingRefinement.firstMetadataRequiresCanonical"; }
part proof9:ProofRow { attribute :>> key="normalization"; attribute :>> lemma="NativeBindingRefinement.normalizationCanBePlannedOnce"; }
part proof10:ProofRow { attribute :>> key="alias-counterexample"; attribute :>> lemma="NativeBindingRefinement.aliasDistinguishes"; }
part proof11:ProofRow { attribute :>> key="writer-counterexample"; attribute :>> lemma="NativeBindingRefinement.interveningWriterBreaksSecond"; }
part proof12:ProofRow { attribute :>> key="error-prefix"; attribute :>> lemma="NativeBindingRefinement.errorPrefixNotEquivalent"; }
part proof13:ProofRow { attribute :>> key="replay"; attribute :>> lemma="NativeBindingRefinement.replayNotRetry"; }
part proof14:ProofRow { attribute :>> key="generation"; attribute :>> lemma="NativeBindingRefinement.generationIsPartOfIdentity"; }
part def MigrationRow { attribute key:String; attribute producerAnchor:String; attribute consumerAnchor:String; attribute actionName:String; attribute lemma:String; }
part migration0:MigrationRow { attribute :>> key="header-cut"; attribute :>> producerAnchor="demand"; attribute :>> consumerAnchor="header"; attribute :>> actionName="native_binding_plan_retirement.writeHeader"; attribute :>> lemma="NativeBindingPlan.headerUnaffectedByFirst"; }
part migration1:MigrationRow { attribute :>> key="resolved-copy"; attribute :>> producerAnchor="layout"; attribute :>> consumerAnchor="cell"; attribute :>> actionName="native_binding_plan_retirement.sealPlan"; attribute :>> lemma="NativeBindingPlan.sealPlanPreserves"; }
part migration2:MigrationRow { attribute :>> key="first-effect"; attribute :>> producerAnchor="demand"; attribute :>> consumerAnchor="prm"; attribute :>> actionName="native_binding_plan_retirement.firstPreserve"; attribute :>> lemma="NativeBindingRefinement.firstMetadataRequiresCanonical"; }
part migration3:MigrationRow { attribute :>> key="second-elision"; attribute :>> producerAnchor="prm"; attribute :>> consumerAnchor="glo"; attribute :>> actionName="native_binding_plan_retirement.secondElide"; attribute :>> lemma="NativeBindingRefinement.secondMetadataEquivalent"; }
part migration4:MigrationRow { attribute :>> key="unknown-custody"; attribute :>> producerAnchor="port"; attribute :>> consumerAnchor="close"; attribute :>> actionName="native_binding_plan_retirement.unknownExit"; attribute :>> lemma="NativeBindingPlan.unknownKeepsCustody"; }
part migration5:MigrationRow { attribute :>> key="reentry"; attribute :>> producerAnchor="exception"; attribute :>> consumerAnchor="end"; attribute :>> actionName="native_binding_plan_retirement.rejectResume"; attribute :>> lemma="NativeBindingPlan.rejectResumePreserves"; }
part def StandardRow { attribute key:String; attribute status:String; attribute authority:String; attribute relevance:String; attribute support:String; }
part standard0:StandardRow { attribute :>> key="language"; attribute :>> status="published baseline"; attribute :>> authority="https://www.iso.org/standard/82075.html"; attribute :>> relevance="C23 / ISO IEC 9899:2024; historical C11 memory-model provenance is not target language"; attribute :>> support="Per-feature compiler and libc qualification OPEN"; }
part standard1:StandardRow { attribute :>> key="future"; attribute :>> status="working draft"; attribute :>> authority="https://open-std.org/jtc1/sc22/wg14/www/projects.html"; attribute :>> relevance="C2y is research input, not mandatory shared contract"; attribute :>> support="No silent use of draft-only features"; }
part standard2:StandardRow { attribute :>> key="tailcalls"; attribute :>> status="TS under development"; attribute :>> authority="https://open-std.org/jtc1/sc22/wg14/www/projects.html"; attribute :>> relevance="Generalized calls may benefit tail calls; explicit runtime dispatcher remains required until qualified"; attribute :>> support="No portable tail-call guarantee assumed"; }
part standard3:StandardRow { attribute :>> key="cleanup"; attribute :>> status="TS under development"; attribute :>> authority="https://open-std.org/jtc1/sc22/wg14/www/projects.html"; attribute :>> relevance="Lexical defer does not prove Scheme continuation or asynchronous exit cleanup"; attribute :>> support="Completion guard needs its own semantic proof"; }
part standard4:StandardRow { attribute :>> key="provenance"; attribute :>> status="published TS 6010; separate from base standard"; attribute :>> authority="https://open-std.org/jtc1/sc22/wg14/www/projects.html"; attribute :>> relevance="Object lifetime and pointer provenance inform alias and descriptor design"; attribute :>> support="No claim that C23 atomics solve reclamation"; }
part standard5:StandardRow { attribute :>> key="clang"; attribute :>> status="implementation feature matrix"; attribute :>> authority="https://clang.llvm.org/c_status.html"; attribute :>> relevance="C23 and C2y support is feature-specific"; attribute :>> support="Upstream status is not Apple Clang or Darwin SDK qualification"; }
part standard6:StandardRow { attribute :>> key="gcc"; attribute :>> status="implementation language modes"; attribute :>> authority="https://gcc.gnu.org/onlinedocs/gcc/Standards.html"; attribute :>> relevance="Explicit C23 mode; C2y experimental"; attribute :>> support="Compiler version target ABI libc and atomics capability must be bound"; }
part history:GambitAssuranceRouting::ModelNeed { ref part :>> owner=GambitAssuranceRelations::modelUse2; attribute :>> obligationId="NB-history"; attribute :>> kind="interleaving"; attribute :>> subjectPath="dev/refactoring/modern-c/models/quint/native_binding_plan_retirement.qnt"; attribute :>> subjectScope="13 histories: elision metadata adapter suspension reentry failures counterexamples"; attribute :>> premise="Conditional study; C23 baseline; no native implementation"; }
part induction:GambitAssuranceRouting::ModelNeed { ref part :>> owner=GambitAssuranceRelations::modelUse2; attribute :>> obligationId="NB-induction"; attribute :>> kind="induction"; attribute :>> subjectPath="dev/refactoring/modern-c/models/lean/NativeBindingPlan.lean"; attribute :>> subjectScope="All typed IR steps preserve conditional admission and custody invariant"; attribute :>> premise="Conditional study; C23 baseline; no native implementation"; }
part refinement:GambitAssuranceRouting::ModelNeed { ref part :>> owner=GambitAssuranceRelations::modelUse2; attribute :>> obligationId="NB-refinement"; attribute :>> kind="induction"; attribute :>> subjectPath="dev/refactoring/modern-c/models/lean/NativeBindingRefinement.lean"; attribute :>> subjectScope="Observer-restricted equivalence and concrete distinguishing abstract histories; observer completeness external"; attribute :>> premise="Conditional study; C23 baseline; no native implementation"; }
part projection:GambitAssuranceRouting::ModelNeed { ref part :>> owner=GambitAssuranceRelations::modelUse2; attribute :>> obligationId="NB-projection"; attribute :>> kind="restricted-projection"; attribute :>> subjectPath="dev/refactoring/modern-c/models/lean/NativeBindingPlanAst.lean"; attribute :>> subjectScope="Binding IDs field kinds expressions roster checked; JSON and extractor trusted"; attribute :>> premise="Conditional study; C23 baseline; no native implementation"; }
part source:GambitAssuranceRouting::ModelNeed { ref part :>> owner=GambitAssuranceRelations::modelUse2; attribute :>> obligationId="NB-source"; attribute :>> kind="source-refinement"; attribute :>> subjectPath="dev/refactoring/modern-c/native-binding-plan-retirement-design.org"; attribute :>> subjectScope="All raw aliases indirect observers root/fault closures and actual host order OPEN"; attribute :>> premise="Conditional study; C23 baseline; no native implementation"; }
part exceptions:GambitAssuranceRouting::ModelNeed { ref part :>> owner=GambitAssuranceRelations::modelUse2; attribute :>> obligationId="NB-exceptions"; attribute :>> kind="exception-equivalence"; attribute :>> subjectPath="dev/refactoring/modern-c/native-binding-plan-retirement-design.org"; attribute :>> subjectScope="Visible output prefix OOM error ordering and multi-shot operation identity OPEN"; attribute :>> premise="Conditional study; C23 baseline; no native implementation"; }
part platform:GambitAssuranceRouting::ModelNeed { ref part :>> owner=GambitAssuranceRelations::modelUse2; attribute :>> obligationId="NB-platform"; attribute :>> kind="c23-platform-qualification"; attribute :>> subjectPath="dev/refactoring/modern-c/language-baseline-design.org"; attribute :>> subjectScope="C23 capability profile publication lifetime and native ABI qualification OPEN"; attribute :>> premise="Conditional study; C23 baseline; no native implementation"; }
part emission:GambitAssuranceRouting::ModelNeed { ref part :>> owner=GambitAssuranceRelations::modelUse2; attribute :>> obligationId="NB-emission"; attribute :>> kind="emitter-fidelity"; attribute :>> subjectPath="dev/refactoring/modern-c/native-binding-plan-retirement-design.org"; attribute :>> subjectScope="Full byte correspondence and output operation retry/refinement OPEN"; attribute :>> premise="Conditional study; C23 baseline; no native implementation"; }

part source32:SourceRow { attribute :>> key="table-gambit"; attribute :>> path="vendor/gambit/lib/_system.scm"; attribute :>> needle="(##table-foldl rcons '() cons table)"; attribute :>> obligation="Table-to-list constructs pairs without deep copying values"; }
part source33:SourceRow { attribute :>> key="table-universal"; attribute :>> path="vendor/gambit/lib/_system.scm"; attribute :>> needle="(cons key (##univ-table-ref hashtable key))"; attribute :>> obligation="Alternative table backend also retains value identity"; }
part source34:SourceRow { attribute :>> key="sort"; attribute :>> path="vendor/gambit/gsc/_utils.scm"; attribute :>> needle="(define (sort-list lst <?)"; attribute :>> obligation="Sorted spine is not a deep resource snapshot"; }
part source35:SourceRow { attribute :>> key="c-id-alias"; attribute :>> path="vendor/gambit/gsc/_t-c-1.scm"; attribute :>> needle="(cons 'c-id-glo name)"; attribute :>> obligation="Tagged C-name object retains original string alias"; }
part def InventoryRow { attribute key:String; attribute path:String; attribute pattern:String; attribute count:String; attribute scope:String; }
part inventory0:InventoryRow { attribute :>> key="table-alias"; attribute :>> path="vendor/gambit/gsc/_t-c-1.scm"; attribute :>> pattern="targ\\-glo\\-vars(?![A-Za-z0-9?!-])"; attribute :>> count="6"; attribute :>> scope="Exact lexical identifier occurrences including definitions; not indirect Scheme alias closure"; }
part inventory1:InventoryRow { attribute :>> key="vector-alias"; attribute :>> path="vendor/gambit/gsc/_t-c-1.scm"; attribute :>> pattern="targ\\-glo\\-rsrc(?![A-Za-z0-9?!-])"; attribute :>> count="4"; attribute :>> scope="Exact lexical identifier occurrences including definitions; not indirect Scheme alias closure"; }
part inventory2:InventoryRow { attribute :>> key="demand-access"; attribute :>> path="vendor/gambit/gsc/_t-c-1.scm"; attribute :>> pattern="targ\\-rsrc\\-demanders(?![A-Za-z0-9?!-])"; attribute :>> count="6"; attribute :>> scope="Exact lexical identifier occurrences including definitions; not indirect Scheme alias closure"; }
part inventory3:InventoryRow { attribute :>> key="supply-access"; attribute :>> path="vendor/gambit/gsc/_t-c-1.scm"; attribute :>> pattern="targ\\-rsrc\\-suppliers(?![A-Za-z0-9?!-])"; attribute :>> count="6"; attribute :>> scope="Exact lexical identifier occurrences including definitions; not indirect Scheme alias closure"; }
}
