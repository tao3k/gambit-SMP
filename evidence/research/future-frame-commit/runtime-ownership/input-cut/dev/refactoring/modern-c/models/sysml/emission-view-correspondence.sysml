package GambitEmissionViewCorrespondence { private import ScalarValues::*;
part def SourceRow { attribute key:String; attribute path:String; attribute needle:String; attribute obligation:String; }
part source0:SourceRow { attribute :>> key="heap-state"; attribute :>> path="vendor/gambit/gsc/_t-c-1.scm"; attribute :>> needle="(define targ-glo-vars #f)"; attribute :>> obligation="Request-local tables must replace shared mutable backend globals"; }
part source1:SourceRow { attribute :>> key="state-reset"; attribute :>> path="vendor/gambit/gsc/_t-c-1.scm"; attribute :>> needle="(set! targ-prc-objs-to-scan (queue-empty))"; attribute :>> obligation="Reset/end lifecycle is a writer; no two sessions can own same state"; }
part source2:SourceRow { attribute :>> key="initial-drain"; attribute :>> path="vendor/gambit/gsc/_t-c-1.scm"; attribute :>> needle="(queue-get! targ-prc-objs-to-scan)"; attribute :>> obligation="Initial procedure drain precedes late descriptor/C-object registration"; }
part source3:SourceRow { attribute :>> key="descriptor-late"; attribute :>> path="vendor/gambit/gsc/_t-c-1.scm"; attribute :>> needle="(targ-use-obj module-descr)"; attribute :>> obligation="Descriptor root added after initial drain"; }
part source4:SourceRow { attribute :>> key="c-object-late"; attribute :>> path="vendor/gambit/gsc/_t-c-1.scm"; attribute :>> needle="(map (lambda (x) (cons (car x) (targ-use-obj (cdr x)))) c-objs)"; attribute :>> obligation="Actual late C-object arguments register before heap-dump enters"; }
part source5:SourceRow { attribute :>> key="object-recursion"; attribute :>> path="vendor/gambit/gsc/_t-c-1.scm"; attribute :>> needle="(targ-use-obj (cdr obj))"; attribute :>> obligation="Pair/subtyped traversal can grow resource closure"; }
part source6:SourceRow { attribute :>> key="procedure-path"; attribute :>> path="vendor/gambit/gsc/_t-c-1.scm"; attribute :>> needle="(targ-use-prc obj #f)"; attribute :>> obligation="Generic use-obj can enqueue a previously unseen procedure"; }
part source7:SourceRow { attribute :>> key="queue-enqueue"; attribute :>> path="vendor/gambit/gsc/_t-c-1.scm"; attribute :>> needle="(queue-put! targ-prc-objs-to-scan z)"; attribute :>> obligation="Closure must account for new queued work"; }
part source8:SourceRow { attribute :>> key="number-intern"; attribute :>> path="vendor/gambit/gsc/_t-c-1.scm"; attribute :>> needle="(table-set! targ-num-objs obj obj)"; attribute :>> obligation="Numeric interning identity and encoded bits belong to sealed view"; }
part source9:SourceRow { attribute :>> key="resource-flags"; attribute :>> path="vendor/gambit/gsc/_t-c-1.scm"; attribute :>> needle="(targ-rsrc-demanders-set! (cdr x) '(\"\"))"; attribute :>> obligation="Existing global lookup may still write demander metadata"; }
part source10:SourceRow { attribute :>> key="resource-vector"; attribute :>> path="vendor/gambit/gsc/_t-c-1.scm"; attribute :>> needle="(vector-set! r 1 demanders)"; attribute :>> obligation="Shallow resource records remain mutable"; }
part source11:SourceRow { attribute :>> key="literal-bind"; attribute :>> path="vendor/gambit/gsc/_t-c-1.scm"; attribute :>> needle="(c-inits (c-intf-inits c-intf))"; attribute :>> obligation="List binding aliases original fragments"; }
part source12:SourceRow { attribute :>> key="interface-clear"; attribute :>> path="vendor/gambit/gsc/_t-c-1.scm"; attribute :>> needle="(c-intf-inits-set! c-intf '())"; attribute :>> obligation="Clearing interface field does not deep-copy payloads"; }
part source13:SourceRow { attribute :>> key="list-snapshot"; attribute :>> path="vendor/gambit/gsc/_t-c-1.scm"; attribute :>> needle="(queue->list targ-prc-objs)"; attribute :>> obligation="Procedure snapshot is queue spine alias"; }
part source14:SourceRow { attribute :>> key="sorted-resources"; attribute :>> path="vendor/gambit/gsc/_t-c-1.scm"; attribute :>> needle="(targ-sort (table->list targ-glo-vars) symbol->string)"; attribute :>> obligation="Sorted list still contains mutable entries/cells"; }
part source15:SourceRow { attribute :>> key="symbol-backfill"; attribute :>> path="vendor/gambit/gsc/_t-c-1.scm"; attribute :>> needle="(targ-cell-set! (cdr s) i)"; attribute :>> obligation="Heap dump performs layout mutation"; }
part source16:SourceRow { attribute :>> key="keyword-backfill"; attribute :>> path="vendor/gambit/gsc/_t-c-1.scm"; attribute :>> needle="(targ-cell-set! (cdr k) i)"; attribute :>> obligation="Keyword index cell assigned during dump"; }
part source17:SourceRow { attribute :>> key="global-backfill"; attribute :>> path="vendor/gambit/gsc/_t-c-1.scm"; attribute :>> needle="(targ-cell-set! (cadr g) i)"; attribute :>> obligation="Global index cell assigned during dump"; }
part source18:SourceRow { attribute :>> key="primitive-late-helper"; attribute :>> path="vendor/gambit/gsc/_t-c-1.scm"; attribute :>> needle="(targ-use-glo (string->symbol name) #f)"; attribute :>> obligation="Dump-mod still invokes potentially mutating helper twice through def-mod-prm-glo"; }
part source19:SourceRow { attribute :>> key="unique-name-write"; attribute :>> path="vendor/gambit/gsc/_t-c-1.scm"; attribute :>> needle="(vector-set! state 0 count+1)"; attribute :>> obligation="Name allocation and retroactive conflict-cell update must complete before freeze"; }
part source20:SourceRow { attribute :>> key="cell-representation"; attribute :>> path="vendor/gambit/gsc/_t-c-1.scm"; attribute :>> needle="(cons 'cell x)"; attribute :>> obligation="Cells are shared pairs referenced by IR nodes"; }
part source21:SourceRow { attribute :>> key="cell-mutation"; attribute :>> path="vendor/gambit/gsc/_t-c-1.scm"; attribute :>> needle="(set-cdr! x y)"; attribute :>> obligation="Cell payload is mutable through aliases"; }
part source22:SourceRow { attribute :>> key="cell-render"; attribute :>> path="vendor/gambit/gsc/_t-c-1.scm"; attribute :>> needle="((cell)        (targ-code tail))"; attribute :>> obligation="Renderer dereferences current cell contents"; }
part source23:SourceRow { attribute :>> key="string-reference"; attribute :>> path="vendor/gambit/gsc/_t-c-1.scm"; attribute :>> needle="(cons 'c-string str)"; attribute :>> obligation="C-string wrapper retains original mutable Scheme string"; }
part source24:SourceRow { attribute :>> key="init-output"; attribute :>> path="vendor/gambit/gsc/_t-c-1.scm"; attribute :>> needle="    c-inits)"; attribute :>> obligation="Opaque C init fragments are emitted in stored order"; }
part source25:SourceRow { attribute :>> key="decl-output"; attribute :>> path="vendor/gambit/gsc/_t-c-1.scm"; attribute :>> needle="        c-decls)))"; attribute :>> obligation="C declarations can be append/cell IR, not only strings"; }
part source26:SourceRow { attribute :>> key="stream-open"; attribute :>> path="vendor/gambit/gsc/_t-c-1.scm"; attribute :>> needle="(set! targ-port (open-output-file-preserving-case filename))"; attribute :>> obligation="Legacy output opens final path before all output succeeds"; }
part source27:SourceRow { attribute :>> key="stream-close"; attribute :>> path="vendor/gambit/gsc/_t-c-1.scm"; attribute :>> needle="(close-output-port targ-port)"; attribute :>> obligation="Known completion needed; no rollback/paired-publication guarantee follows"; }
part source28:SourceRow { attribute :>> key="source-map-write"; attribute :>> path="vendor/gambit/gsc/_t-c-1.scm"; attribute :>> needle="(set! targ-source-line-number (cadr x))"; attribute :>> obligation="Emission-only cursor state must remain private"; }
part source29:SourceRow { attribute :>> key="link-read"; attribute :>> path="vendor/gambit/gsc/_t-c-1.scm"; attribute :>> needle="(read in))))"; attribute :>> obligation="Link metadata parsing not an immutable whole-artifact snapshot"; }
part source30:SourceRow { attribute :>> key="link-header-check"; attribute :>> path="vendor/gambit/gsc/_t-c-1.scm"; attribute :>> needle="(equal? (car info) (compiler-version))"; attribute :>> obligation="Header identity check does not establish complete schema/content correspondence"; }
part source31:SourceRow { attribute :>> key="link-vector-copy"; attribute :>> path="vendor/gambit/gsc/_t-c-1.scm"; attribute :>> needle="(link-info (list->vector (caddr file-and-flags-and-link-info)))"; attribute :>> obligation="Only top-level list->vector; nested lists and strings remain shared"; }
part source32:SourceRow { attribute :>> key="link-flag-merge"; attribute :>> path="vendor/gambit/gsc/_t-c-1.scm"; attribute :>> needle="(append flags1 flags2)"; attribute :>> obligation="Append reuses tail; ordered inherited flags must remain stable"; }
part source33:SourceRow { attribute :>> key="link-order"; attribute :>> path="vendor/gambit/gsc/_t-c-1.scm"; attribute :>> needle="(append old-mods-and-flags new-mods-and-flags)"; attribute :>> obligation="Dedup ownership cannot dedup initializer sequence"; }
part source34:SourceRow { attribute :>> key="scan-record-update"; attribute :>> path="vendor/gambit/gsc/_t-c-2.scm"; attribute :>> needle="(set-car! p"; attribute :>> obligation="Procedure record shared with queue/table is filled by scanner"; }
part source35:SourceRow { attribute :>> key="scan-label-write"; attribute :>> path="vendor/gambit/gsc/_t-c-2.scm"; attribute :>> needle="(set! targ-lbl-alloc (+ targ-lbl-alloc (+ i 1)))"; attribute :>> obligation="Label count changes during closure completion"; }
part source36:SourceRow { attribute :>> key="scan-debug-root"; attribute :>> path="vendor/gambit/gsc/_t-c-2.scm"; attribute :>> needle="(targ-use-obj info)"; attribute :>> obligation="Debug metadata generation creates additional object roots"; }
part source37:SourceRow { attribute :>> key="scan-code-write"; attribute :>> path="vendor/gambit/gsc/_t-c-2.scm"; attribute :>> needle="(stretchable-vector-set! targ-proc-code targ-proc-code-length code)"; attribute :>> obligation="Procedure instruction vector mutates before sealing"; }
part source38:SourceRow { attribute :>> key="scan-rc-map"; attribute :>> path="vendor/gambit/gsc/_t-c-2.scm"; attribute :>> needle="(stretchable-vector-set! targ-module-rd-res i #t)"; attribute :>> obligation="Module/procedure resource bitmaps share mutable state"; }
part source39:SourceRow { attribute :>> key="scan-decl-append"; attribute :>> path="vendor/gambit/gsc/_t-c-2.scm"; attribute :>> needle="(queue-put! c-decls-queue"; attribute :>> obligation="Out-of-line C procedure scan appends generated declaration IR"; }
part source40:SourceRow { attribute :>> key="queue-alias"; attribute :>> path="vendor/gambit/gsc/_utils.scm"; attribute :>> needle="(define (queue->list queue)"; attribute :>> obligation="Implementation returns underlying car, not a copy"; }
part source41:SourceRow { attribute :>> key="queue-append-alias"; attribute :>> path="vendor/gambit/gsc/_utils.scm"; attribute :>> needle="(set-cdr! (cdr queue) entry)"; attribute :>> obligation="Appending changes previously returned list spine"; }
part source42:SourceRow { attribute :>> key="ordered-entry-alias"; attribute :>> path="vendor/gambit/gsc/_utils.scm"; attribute :>> needle="(cons (stretchable-vector-ref (vector-ref ot 1) i) lst)"; attribute :>> obligation="Fresh outer list retains stored key/result entry pairs"; }
part source43:SourceRow { attribute :>> key="ordered-producer"; attribute :>> path="vendor/gambit/gsc/_utils.scm"; attribute :>> needle="(stretchable-vector-set! (vector-ref ot 1) i (cons key result))"; attribute :>> obligation="Entry storage and returned result may alias mutable cells"; }
part source44:SourceRow { attribute :>> key="parse-init"; attribute :>> path="vendor/gambit/gsc/_ptree1.scm"; attribute :>> needle="(add-c-init body)"; attribute :>> obligation="Two parser paths retain original source string"; }
part source45:SourceRow { attribute :>> key="parse-decl"; attribute :>> path="vendor/gambit/gsc/_ptree1.scm"; attribute :>> needle="(add-c-decl body)"; attribute :>> obligation="Declarations share source payload identity"; }
part source46:SourceRow { attribute :>> key="fragment-add"; attribute :>> path="vendor/gambit/gsc/_ptree2.scm"; attribute :>> needle="(cons initialization-code-string c-interface-inits)"; attribute :>> obligation="No deep payload copy on native init capture"; }
part source47:SourceRow { attribute :>> key="fragment-end"; attribute :>> path="vendor/gambit/gsc/_ptree2.scm"; attribute :>> needle="(reverse c-interface-inits)"; attribute :>> obligation="Fresh list spine does not own mutable string contents"; }
part source48:SourceRow { attribute :>> key="interface-vector"; attribute :>> path="vendor/gambit/gsc/_ptree2.scm"; attribute :>> needle="(define (c-intf-inits-set! c-intf x) (vector-set! c-intf 2 x))"; attribute :>> obligation="Interface setter only replaces vector slot"; }
part source49:SourceRow { attribute :>> key="actual-c-object"; attribute :>> path="vendor/gambit/gsc/_ptree2.scm"; attribute :>> needle="(add-c-obj name tag-list)"; attribute :>> obligation="Only named call found in bounded gsc Scheme inventory uses tag-list"; }
part source50:SourceRow { attribute :>> key="tag-check"; attribute :>> path="vendor/gambit/gsc/_ptree2.scm"; attribute :>> needle="(symbol-object? tag)"; attribute :>> obligation="Checked native type tags restrict ordinary caller payload domain"; }
part source51:SourceRow { attribute :>> key="tag-list-check"; attribute :>> path="vendor/gambit/gsc/_ptree2.scm"; attribute :>> needle="(proper-length tag)"; attribute :>> obligation="Proper tag lists checked elementwise for symbols; exact checker scope matters"; }
part source52:SourceRow { attribute :>> key="debug-sharing"; attribute :>> path="vendor/gambit/gsc/_gvm.scm"; attribute :>> needle="(define (debug-info-compact-using-sharing sharing-table obj)"; attribute :>> obligation="Compactor mutates sharing table and builds cyclic payload graph"; }
part source53:SourceRow { attribute :>> key="debug-string-alias"; attribute :>> path="vendor/gambit/gsc/_gvm.scm"; attribute :>> needle="(table-set! sharing-table obj obj)"; attribute :>> obligation="String branch deliberately shares original string"; }
part source54:SourceRow { attribute :>> key="host-case-profile"; attribute :>> path="vendor/gambit/gsc/_host.scm"; attribute :>> needle="(define (open-input-file*-preserving-case path)"; attribute :>> obligation="Host branches differ; Gambit branch constructs standard case-preserving readtable"; }
part source55:SourceRow { attribute :>> key="host-write-profile"; attribute :>> path="vendor/gambit/gsc/_host.scm"; attribute :>> needle="(define (write-returning-len-without-read-macros obj port)"; attribute :>> obligation="Host-dependent writer and encoding must be bound to pair receipt"; }
part source56:SourceRow { attribute :>> key="native-abi-macro"; attribute :>> path="vendor/gambit/include/gambit.h.in"; attribute :>> needle="#define ___BEGIN_MOD_SYM_KEY"; attribute :>> obligation="C text correspondence differs from macro-expanded native layout proof"; }
part def InventoryRow { attribute key:String; attribute path:String; attribute pattern:String; attribute count:String; attribute scope:String; }
part inventory0:InventoryRow { attribute :>> key="backend-global-writes"; attribute :>> path="vendor/gambit/gsc/_t-c-1.scm"; attribute :>> pattern="\\(set!\\s+targ-[\\w!?-]+"; attribute :>> count="64"; attribute :>> scope="Exact lexical file scope; includes reset/lifecycle forms and is not whole-program alias/semantic closure"; }
part inventory1:InventoryRow { attribute :>> key="scanner-global-writes"; attribute :>> path="vendor/gambit/gsc/_t-c-2.scm"; attribute :>> pattern="\\(set!\\s+targ-[\\w!?-]+"; attribute :>> count="42"; attribute :>> scope="Exact lexical file scope; includes reset/lifecycle forms and is not whole-program alias/semantic closure"; }
part inventory2:InventoryRow { attribute :>> key="layout-cell-write-calls"; attribute :>> path="vendor/gambit/gsc/_t-c-1.scm"; attribute :>> pattern="\\(targ-cell-set!\\s"; attribute :>> count="5"; attribute :>> scope="Exact lexical file scope; includes reset/lifecycle forms and is not whole-program alias/semantic closure"; }
part inventory3:InventoryRow { attribute :>> key="scanner-cell-write-calls"; attribute :>> path="vendor/gambit/gsc/_t-c-2.scm"; attribute :>> pattern="\\(targ-cell-set!\\s"; attribute :>> count="8"; attribute :>> scope="Exact lexical file scope; includes reset/lifecycle forms and is not whole-program alias/semantic closure"; }
part inventory4:InventoryRow { attribute :>> key="parser-init-callers"; attribute :>> path="vendor/gambit/gsc/_ptree1.scm"; attribute :>> pattern="\\(add-c-init body\\)"; attribute :>> count="2"; attribute :>> scope="Exact lexical file scope; includes reset/lifecycle forms and is not whole-program alias/semantic closure"; }
part inventory5:InventoryRow { attribute :>> key="c-object-tag-caller"; attribute :>> path="vendor/gambit/gsc/_ptree2.scm"; attribute :>> pattern="\\(add-c-obj name tag-list\\)"; attribute :>> count="1"; attribute :>> scope="Exact lexical file scope; includes reset/lifecycle forms and is not whole-program alias/semantic closure"; }
part inventory6:InventoryRow { attribute :>> key="dump-global-helper"; attribute :>> path="vendor/gambit/gsc/_t-c-1.scm"; attribute :>> pattern="\\(targ-use-glo \\(string->symbol name\\) #f\\)"; attribute :>> count="1"; attribute :>> scope="Exact lexical file scope; includes reset/lifecycle forms and is not whole-program alias/semantic closure"; }
part inventory7:InventoryRow { attribute :>> key="ordered-entry-exposure"; attribute :>> path="vendor/gambit/gsc/_utils.scm"; attribute :>> pattern="\\(cons \\(stretchable-vector-ref \\(vector-ref ot 1\\) i\\) lst\\)"; attribute :>> count="1"; attribute :>> scope="Exact lexical file scope; includes reset/lifecycle forms and is not whole-program alias/semantic closure"; }
part def WriterRow { attribute key:String; attribute storage:String; attribute writers:String; attribute aliasing:String; attribute sealing:String; }
part writer0:WriterRow { attribute :>> key="backend-lifecycle"; attribute :>> storage="targ heap tables queues resource masks config"; attribute :>> writers="heap-begin/end and target setup"; attribute :>> aliasing="Process globals may be visible to nested/concurrent compile"; attribute :>> sealing="Request-private owner; no reset/rebind while a capsule lease exists"; }
part writer1:WriterRow { attribute :>> key="recursive-object-graph"; attribute :>> storage="pairs vectors boxes symbols numeric objects"; attribute :>> writers="use-obj ordered-table entry and recursive children"; attribute :>> aliasing="eq identity table keys reference original payloads"; attribute :>> sealing="Owned graph or complete stable borrow; preserve sharing cycles symbol identity and numeric bits"; }
part writer2:WriterRow { attribute :>> key="procedure-work"; attribute :>> storage="prc seen/table queues and proc payload"; attribute :>> writers="use-prc enqueue; scan-procedure set-car and code/labels/FrameSpec writes"; attribute :>> aliasing="queue->list is shared spine; result records shared in seen table"; attribute :>> sealing="Seed late roots and drain to fixed point before layout"; }
part writer3:WriterRow { attribute :>> key="index-cells"; attribute :>> storage="symbol key global procedure label cells"; attribute :>> writers="scan and dump-sym-key-glo callbacks"; attribute :>> aliasing="cell setter mutates pair observed by renderer"; attribute :>> sealing="Resolve every used cell to immutable indices before C/Spec emission"; }
part writer4:WriterRow { attribute :>> key="global-flags"; attribute :>> storage="resource demander/supplier vectors"; attribute :>> writers="use-glo even on existing entry; dump-mod primitive helper"; attribute :>> aliasing="Sorted resource lists share vector payloads"; attribute :>> sealing="Capture separate header/native-use roles before readonly lookup; do not blindly hoist writes"; }
part writer5:WriterRow { attribute :>> key="unique-names"; attribute :>> storage="name table conflict cells and per-proc mappings"; attribute :>> writers="scan and emission call unique-name"; attribute :>> aliasing="Second same-name proc patches first name cell"; attribute :>> sealing="Close all proc identity/name assignments; emission cannot allocate missing name"; }
part writer6:WriterRow { attribute :>> key="debug-graph"; attribute :>> storage="sharing table and compacted pairs boxes vectors strings"; attribute :>> writers="debug-info-generate/compact and scanner use-obj"; attribute :>> aliasing="String branch keeps original; containers may be rebuilt/shared"; attribute :>> sealing="Copy/own string bytes and graph identities; compaction is not deep freeze"; }
part writer7:WriterRow { attribute :>> key="C-interface"; attribute :>> storage="decl/proc/init/object vectors lists bodies"; attribute :>> writers="parse/extract defs add-c-*; interface-end; dump captures and clears"; attribute :>> aliasing="Clearing fields/reversing list leaves mutable bodies aliased"; attribute :>> sealing="Ordered immutable fragment bytes/IR plus provenance; no universal effect inference"; }
part writer8:WriterRow { attribute :>> key="resource-maps-scratch"; attribute :>> storage="module/proc rd/wr maps FP/representation scratch"; attribute :>> writers="scanner resource writes and temporary lowering"; attribute :>> aliasing="Final code may refer to unresolved cells and mutable maps"; attribute :>> sealing="Materialize finalized code/maps; discard private scratch without aliasing capsule"; }
part writer9:WriterRow { attribute :>> key="linker-inputs"; attribute :>> storage="link-info nested lists metadata names flags"; attribute :>> writers="file read get-mod combine-meta-info resource merge"; attribute :>> aliasing="Top-level vector copy and append tail reuse retain aliases"; attribute :>> sealing="Parse owned input bytes; deep typed snapshot preserving order and duplicate flags"; }
part writer10:WriterRow { attribute :>> key="output-private"; attribute :>> storage="port macro formatting source cursor"; attribute :>> writers="start-dump code/display line tracking close"; attribute :>> aliasing="Globals are mutable but need not belong to frozen semantic view"; attribute :>> sealing="Per-output private state; known close and pair publication receipt"; }
part writer11:WriterRow { attribute :>> key="profile-and-ABI"; attribute :>> storage="target options c-id prefix host writer gambit.h definitions"; attribute :>> writers="target setup compiler config and host-specific encoders"; attribute :>> aliasing="Equal resource counts may still encode different bytes/layouts"; attribute :>> sealing="Bind complete effective profile and distinguish text macro-layout and ownership receipts"; }
part def ConsumerRow { attribute key:String; attribute callers:String; attribute custody:String; attribute gap:String; }
part consumer0:ConsumerRow { attribute :>> key="late-use-obj"; attribute :>> callers="initial scan loop -> descriptor/C-object use -> heap-dump"; attribute :>> custody="All late roots and any resulting work must enter closure"; attribute :>> gap="Generic procedure possibility is not an established legal late-proc witness"; }
part consumer1:ConsumerRow { attribute :>> key="ordinary-C-tags"; attribute :>> callers="check-c-type -> converter -> add-c-obj tag-list"; attribute :>> custody="Checked symbol/list domain explains current named caller"; attribute :>> gap="Compiler extension/mutable alias/cycle domain still requires qualification"; }
part consumer2:ConsumerRow { attribute :>> key="layout-render"; attribute :>> callers="dump-sym/key/glo and unique-name -> targ-code cell"; attribute :>> custody="Mutable cells must be resolved before immutable snapshot"; attribute :>> gap="Current dump is not a readonly pass"; }
part consumer3:ConsumerRow { attribute :>> key="C-fragments"; attribute :>> callers="parser -> c-interface-end -> dump-mod/prc"; attribute :>> custody="Ordered exact payload and source/host encoding"; attribute :>> gap="Opaque effect metadata is separate from exact text coverage"; }
part consumer4:ConsumerRow { attribute :>> key="link-input"; attribute :>> callers="link-info read -> get-mod shallow copy -> linker output"; attribute :>> custody="Own bytes plus nested schema identities and flags"; attribute :>> gap="Actual input snapshot stability and complete encoder proof OPEN"; }
part consumer5:ConsumerRow { attribute :>> key="pair-publication"; attribute :>> callers="start-dump -> end-dump -> planned ModuleSpec service"; attribute :>> custody="Same epoch and complete artifacts before pair receipt"; attribute :>> gap="Close/output error and postclose visibility not an atomic pair today"; }
part def ClaimRow { attribute key:String; attribute mechanism:String; attribute condition:String; attribute result:String; attribute gap:String; }
part claim0:ClaimRow { attribute :>> key="two-cuts"; attribute :>> mechanism="Discovery fixed point then layout/name/flag resolution then immutable capsule"; attribute :>> condition="All root seeds accepted writers aliases and future registration helpers covered"; attribute :>> result="Previous pre-heap-dump location alone cannot certify immutability"; attribute :>> gap="No current controlled capsule or complete writer closure"; }
part claim1:ClaimRow { attribute :>> key="readonly-emission"; attribute :>> mechanism="Preassigned ResourceId PointId names indices and ordered native fragments"; attribute :>> condition="Emission helper cannot allocate or mutate resource; preserve temporal header/native roles"; attribute :>> result="C and ModuleSpec can run as independent consumers of same capsule"; attribute :>> gap="Prove use-glo and unique-name existing lookup behavior for admitted domain"; }
part claim2:ClaimRow { attribute :>> key="pair-fidelity"; attribute :>> mechanism="Same capsule epoch plus per-constructor emission/witness proof and known I/O close"; attribute :>> condition="Structured witness covers all C regions in exact order with payload and profile"; attribute :>> result="Hashes/counts identify artifacts but do not prove correspondence"; attribute :>> gap="Actual full C encoder/ModuleSpec schema proof OPEN"; }
part claim3:ClaimRow { attribute :>> key="opaque-separation"; attribute :>> mechanism="Record opaque fragments verbatim without pretending to infer their native effects"; attribute :>> condition="Text receipt cannot become native ownership receipt without adapter"; attribute :>> result="Unqualified native effects need not prohibit byte-faithful text recording"; attribute :>> gap="Open-world dependency envelope and native ABI layout still unqualified"; }
part claim4:ClaimRow { attribute :>> key="input-ownership"; attribute :>> mechanism="Owned input artifact bytes plus nested typed projection"; attribute :>> condition="Host readtable/encoding path errors and metadata semantics preserved"; attribute :>> result="Top-level list->vector is insufficient for freeze"; attribute :>> gap="Content/profile/schema/source-map reflection obligation OPEN"; }
part claim5:ClaimRow { attribute :>> key="close-custody"; attribute :>> mechanism="Close admits completion only for previously accepted writers/work"; attribute :>> condition="Unknown writer/output retains operation and artifacts until reconciliation"; attribute :>> result="Queue empty does not mean all producers are closed"; attribute :>> gap="Actual service C11/GC/exception refinement OPEN"; }
part def MemoryRow { attribute key:String; attribute publication:String; attribute consumer:String; attribute gap:String; }
part memory0:MemoryRow { attribute :>> key="writer-close"; attribute :>> publication="Same authority orders writer reservation and close"; attribute :>> consumer="Accepted writer credit persists through publish/known return; unknown remains debt"; attribute :>> gap="No native implementation or actual producer exclusion proof"; }
part memory1:MemoryRow { attribute :>> key="root-fixpoint"; attribute :>> publication="Capture descriptor C objects and debug roots then complete all work"; attribute :>> consumer="Closure requires empty queue AND no accepted publishers and complete late seed set"; attribute :>> gap="Finite-source termination and exact canonical task accounting OPEN"; }
part memory2:MemoryRow { attribute :>> key="capsule"; attribute :>> publication="Private graph owned/rooted through copying and layout resolution"; attribute :>> consumer="Release-publish immutable capsule; acquire both emitters; no exported mutable alias"; attribute :>> gap="GC root/movement and semantic identity preservation OPEN"; }
part memory3:MemoryRow { attribute :>> key="paired-output"; attribute :>> publication="Immutable capsule generation attached to each full output and witness"; attribute :>> consumer="Both closes known successful before visible pair receipt"; attribute :>> gap="Independent raw final-path files and unknown closes cannot certify pair"; }
part memory4:MemoryRow { attribute :>> key="revocation"; attribute :>> publication="Before receipt known premise failure quarantines the operation"; attribute :>> consumer="Do not delete unknown output or parent work; no semantic reexecution from transport retry"; attribute :>> gap="Post-consumption raw mutation cannot be repaired by retroactive revocation"; }
part def GainRow { attribute key:String; attribute avoided:String; attribute added:String; attribute condition:String; }
part gain0:GainRow { attribute :>> key="parallel-emit"; attribute :>> avoided="Repeated discovery/layout and unrelated emission serialization"; attribute :>> added="Request-private capsule one-time graph ownership and index assignment"; attribute :>> condition="Independent readonly C/Spec consumers; current globals prevent assuming safe concurrency"; }
part gain1:GainRow { attribute :>> key="incremental"; attribute :>> avoided="Repeated closure/resource derivation for identical sealed producer result"; attribute :>> added="Input/profile digests and immutable capsule storage/verification"; attribute :>> condition="Unchanged complete source inputs; repeated genuine init effects not removed"; }
part gain2:GainRow { attribute :>> key="lowering"; attribute :>> avoided="Mutable backfill lookup during each output serialization"; attribute :>> added="One normalized cell/name/global plan plus readonly accessors"; attribute :>> condition="Only replace when baseline final bytes flags names and failures are reflected"; }
part gain3:GainRow { attribute :>> key="native-fragments"; attribute :>> avoided="Reparsing or regenerating unchanged exact C text"; attribute :>> added="Owned ordered fragments byte encoding and opaque-capability entries"; attribute :>> condition="Text caching is distinct from full native ownership qualification"; }
part gain4:GainRow { attribute :>> key="pair-assurance"; attribute :>> avoided="False reuse based solely on equal counts or one output success"; attribute :>> added="Structured coverage witness full close/outcome and source refinements"; attribute :>> condition="Current actual pair receipt stays unqualified"; }
part gain5:GainRow { attribute :>> key="shared-modern-C"; attribute :>> avoided="Multiple ad hoc layout/member contracts across C and runtime services"; attribute :>> added="Shared typed emission ABI and generation keys"; attribute :>> condition="No Zig-specific savings or measured runtime/build speedup established"; }
part def ContractRow { attribute fromNode:String; attribute toNode:String; attribute custody:String; }
part contract0:ContractRow { attribute :>> fromNode="request-owner"; attribute :>> toNode="discovery-work"; attribute :>> custody="Own mutable backend state and accepted producers"; }
part contract1:ContractRow { attribute :>> fromNode="late-root-seeds"; attribute :>> toNode="discovery-work"; attribute :>> custody="Descriptor and C objects plus debug roots join fixed point"; }
part contract2:ContractRow { attribute :>> fromNode="discovery-work"; attribute :>> toNode="layout-resolution"; attribute :>> custody="All seeds included queue drained and writers settled"; }
part contract3:ContractRow { attribute :>> fromNode="mutable-aliases"; attribute :>> toNode="closure-or-rejection"; attribute :>> custody="Shallow list or shared string is not a frozen view"; }
part contract4:ContractRow { attribute :>> fromNode="closure-or-rejection"; attribute :>> toNode="layout-resolution"; attribute :>> custody="Own graph and fragments or retain unqualified request"; }
part contract5:ContractRow { attribute :>> fromNode="owned-link-inputs"; attribute :>> toNode="layout-resolution"; attribute :>> custody="Bind input bytes nested flags metadata host profile"; }
part contract6:ContractRow { attribute :>> fromNode="layout-resolution"; attribute :>> toNode="immutable-capsule"; attribute :>> custody="Resolve cells names primitive globals and FrameSpec references"; }
part contract7:ContractRow { attribute :>> fromNode="immutable-capsule"; attribute :>> toNode="C-output"; attribute :>> custody="C"; }
part contract8:ContractRow { attribute :>> fromNode="immutable-capsule"; attribute :>> toNode="ModuleSpec-output"; attribute :>> custody="Spec"; }
part contract9:ContractRow { attribute :>> fromNode="C-output"; attribute :>> toNode="coverage-and-known-close"; attribute :>> custody="C spans"; }
part contract10:ContractRow { attribute :>> fromNode="ModuleSpec-output"; attribute :>> toNode="coverage-and-known-close"; attribute :>> custody="Spec spans"; }
part contract11:ContractRow { attribute :>> fromNode="coverage-and-known-close"; attribute :>> toNode="text-pair-receipt"; attribute :>> custody="Qualified verifier and both full outputs; hashes alone insufficient"; }
part contract12:ContractRow { attribute :>> fromNode="text-pair-receipt"; attribute :>> toNode="native-ownership-gate"; attribute :>> custody="Separate effective ABI and opaque effect adapter obligations"; }
part contract13:ContractRow { attribute :>> fromNode="unknown-writer-or-output"; attribute :>> toNode="stable-request-custodian"; attribute :>> custody="Parent responsibility and partial artifacts survive caller exit"; }
part contract14:ContractRow { attribute :>> fromNode="native-ownership-gate"; attribute :>> toNode="retained-or-controlled-generation"; attribute :>> custody="Current native ownership and source correspondence remain OPEN"; }
part def BindingRow { attribute actionName:String; attribute lemma:String; attribute scope:String; }
part binding0:BindingRow { attribute :>> actionName="emission_view_correspondence.captureFront"; attribute :>> lemma="EmissionView.captureFrontPreserves"; attribute :>> scope="Actual typed IR step; complete native source writers/aliases and verifier qualification remain external"; }
part binding1:BindingRow { attribute :>> actionName="emission_view_correspondence.captureLate"; attribute :>> lemma="EmissionView.captureLatePreserves"; attribute :>> scope="Actual typed IR step; complete native source writers/aliases and verifier qualification remain external"; }
part binding2:BindingRow { attribute :>> actionName="emission_view_correspondence.discoverChild"; attribute :>> lemma="EmissionView.discoverChildPreserves"; attribute :>> scope="Actual typed IR step; complete native source writers/aliases and verifier qualification remain external"; }
part binding3:BindingRow { attribute :>> actionName="emission_view_correspondence.drainOne"; attribute :>> lemma="EmissionView.drainOnePreserves"; attribute :>> scope="Actual typed IR step; complete native source writers/aliases and verifier qualification remain external"; }
part binding4:BindingRow { attribute :>> actionName="emission_view_correspondence.reserveWriter"; attribute :>> lemma="EmissionView.reserveWriterPreserves"; attribute :>> scope="Actual typed IR step; complete native source writers/aliases and verifier qualification remain external"; }
part binding5:BindingRow { attribute :>> actionName="emission_view_correspondence.writerPublish"; attribute :>> lemma="EmissionView.writerPublishPreserves"; attribute :>> scope="Actual typed IR step; complete native source writers/aliases and verifier qualification remain external"; }
part binding6:BindingRow { attribute :>> actionName="emission_view_correspondence.writerDone"; attribute :>> lemma="EmissionView.writerDonePreserves"; attribute :>> scope="Actual typed IR step; complete native source writers/aliases and verifier qualification remain external"; }
part binding7:BindingRow { attribute :>> actionName="emission_view_correspondence.unknownWriter"; attribute :>> lemma="EmissionView.unknownWriterPreserves"; attribute :>> scope="Actual typed IR step; complete native source writers/aliases and verifier qualification remain external"; }
part binding8:BindingRow { attribute :>> actionName="emission_view_correspondence.escapeAlias"; attribute :>> lemma="EmissionView.escapeAliasPreserves"; attribute :>> scope="Actual typed IR step; complete native source writers/aliases and verifier qualification remain external"; }
part binding9:BindingRow { attribute :>> actionName="emission_view_correspondence.beginClose"; attribute :>> lemma="EmissionView.beginClosePreserves"; attribute :>> scope="Actual typed IR step; complete native source writers/aliases and verifier qualification remain external"; }
part binding10:BindingRow { attribute :>> actionName="emission_view_correspondence.closeAliases"; attribute :>> lemma="EmissionView.closeAliasesPreserves"; attribute :>> scope="Actual typed IR step; complete native source writers/aliases and verifier qualification remain external"; }
part binding11:BindingRow { attribute :>> actionName="emission_view_correspondence.freezeInputs"; attribute :>> lemma="EmissionView.freezeInputsPreserves"; attribute :>> scope="Actual typed IR step; complete native source writers/aliases and verifier qualification remain external"; }
part binding12:BindingRow { attribute :>> actionName="emission_view_correspondence.declareOpaque"; attribute :>> lemma="EmissionView.declareOpaquePreserves"; attribute :>> scope="Actual typed IR step; complete native source writers/aliases and verifier qualification remain external"; }
part binding13:BindingRow { attribute :>> actionName="emission_view_correspondence.copyFragments"; attribute :>> lemma="EmissionView.copyFragmentsPreserves"; attribute :>> scope="Actual typed IR step; complete native source writers/aliases and verifier qualification remain external"; }
part binding14:BindingRow { attribute :>> actionName="emission_view_correspondence.qualifyNative"; attribute :>> lemma="EmissionView.qualifyNativePreserves"; attribute :>> scope="Actual typed IR step; complete native source writers/aliases and verifier qualification remain external"; }
part binding15:BindingRow { attribute :>> actionName="emission_view_correspondence.qualifyVerifier"; attribute :>> lemma="EmissionView.qualifyVerifierPreserves"; attribute :>> scope="Actual typed IR step; complete native source writers/aliases and verifier qualification remain external"; }
part binding16:BindingRow { attribute :>> actionName="emission_view_correspondence.resolveLayout"; attribute :>> lemma="EmissionView.resolveLayoutPreserves"; attribute :>> scope="Actual typed IR step; complete native source writers/aliases and verifier qualification remain external"; }
part binding17:BindingRow { attribute :>> actionName="emission_view_correspondence.lateLayoutWrite"; attribute :>> lemma="EmissionView.lateLayoutWritePreserves"; attribute :>> scope="Actual typed IR step; complete native source writers/aliases and verifier qualification remain external"; }
part binding18:BindingRow { attribute :>> actionName="emission_view_correspondence.freeze"; attribute :>> lemma="EmissionView.freezePreserves"; attribute :>> scope="Actual typed IR step; complete native source writers/aliases and verifier qualification remain external"; }
part binding19:BindingRow { attribute :>> actionName="emission_view_correspondence.emitC"; attribute :>> lemma="EmissionView.emitCPreserves"; attribute :>> scope="Actual typed IR step; complete native source writers/aliases and verifier qualification remain external"; }
part binding20:BindingRow { attribute :>> actionName="emission_view_correspondence.emitSpec"; attribute :>> lemma="EmissionView.emitSpecPreserves"; attribute :>> scope="Actual typed IR step; complete native source writers/aliases and verifier qualification remain external"; }
part binding21:BindingRow { attribute :>> actionName="emission_view_correspondence.verifyCoverage"; attribute :>> lemma="EmissionView.verifyCoveragePreserves"; attribute :>> scope="Actual typed IR step; complete native source writers/aliases and verifier qualification remain external"; }
part binding22:BindingRow { attribute :>> actionName="emission_view_correspondence.closeOutputs"; attribute :>> lemma="EmissionView.closeOutputsPreserves"; attribute :>> scope="Actual typed IR step; complete native source writers/aliases and verifier qualification remain external"; }
part binding23:BindingRow { attribute :>> actionName="emission_view_correspondence.issue"; attribute :>> lemma="EmissionView.issuePreserves"; attribute :>> scope="Actual typed IR step; complete native source writers/aliases and verifier qualification remain external"; }
part binding24:BindingRow { attribute :>> actionName="emission_view_correspondence.nativePermit"; attribute :>> lemma="EmissionView.nativePermitPreserves"; attribute :>> scope="Actual typed IR step; complete native source writers/aliases and verifier qualification remain external"; }
part binding25:BindingRow { attribute :>> actionName="emission_view_correspondence.rejectSnapshot"; attribute :>> lemma="EmissionView.rejectSnapshotPreserves"; attribute :>> scope="Actual typed IR step; complete native source writers/aliases and verifier qualification remain external"; }
part binding26:BindingRow { attribute :>> actionName="emission_view_correspondence.unknownOutput"; attribute :>> lemma="EmissionView.unknownOutputPreserves"; attribute :>> scope="Actual typed IR step; complete native source writers/aliases and verifier qualification remain external"; }
part binding27:BindingRow { attribute :>> actionName="emission_view_correspondence.rejectLateWriter"; attribute :>> lemma="EmissionView.rejectLateWriterPreserves"; attribute :>> scope="Actual typed IR step; complete native source writers/aliases and verifier qualification remain external"; }
part def ProofRow { attribute key:String; attribute lemma:String; }
part proof0:ProofRow { attribute :>> key="all-step"; attribute :>> lemma="EmissionView.stepPreserves"; }
part proof1:ProofRow { attribute :>> key="reachable"; attribute :>> lemma="EmissionView.reachableSafe"; }
part proof2:ProofRow { attribute :>> key="same-view"; attribute :>> lemma="EmissionView.receiptSameView"; }
part proof3:ProofRow { attribute :>> key="coverage-close"; attribute :>> lemma="EmissionView.receiptCoverageAndClose"; }
part proof4:ProofRow { attribute :>> key="unknown-custody"; attribute :>> lemma="EmissionView.unknownWriterKeepsCustody"; }
part proof5:ProofRow { attribute :>> key="native-qualifier"; attribute :>> lemma="EmissionView.nativeNeedsQualification"; }
part proof6:ProofRow { attribute :>> key="ordered-bytes"; attribute :>> lemma="EmissionViewComposition.orderedWitnessReplaysBytes"; }
part proof7:ProofRow { attribute :>> key="count-counterexample"; attribute :>> lemma="EmissionViewComposition.matchingCountsDoNotProveBytes"; }
part proof8:ProofRow { attribute :>> key="parent-qualifier"; attribute :>> lemma="EmissionViewComposition.nativeQualifierFitsParent"; }
part proof9:ProofRow { attribute :>> key="text-not-native"; attribute :>> lemma="EmissionViewComposition.textReceiptIsNotNativePermission"; }
part def MigrationRow { attribute key:String; attribute producerAnchor:String; attribute consumerAnchor:String; attribute actionName:String; attribute lemma:String; }
part migration0:MigrationRow { attribute :>> key="late-root-frontier"; attribute :>> producerAnchor="initial-drain"; attribute :>> consumerAnchor="c-object-late"; attribute :>> actionName="emission_view_correspondence.captureLate"; attribute :>> lemma="EmissionView.captureLatePreserves"; }
part migration1:MigrationRow { attribute :>> key="queue-alias"; attribute :>> producerAnchor="queue-alias"; attribute :>> consumerAnchor="list-snapshot"; attribute :>> actionName="emission_view_correspondence.closeAliases"; attribute :>> lemma="EmissionView.closeAliasesPreserves"; }
part migration2:MigrationRow { attribute :>> key="layout-cells"; attribute :>> producerAnchor="cell-mutation"; attribute :>> consumerAnchor="symbol-backfill"; attribute :>> actionName="emission_view_correspondence.resolveLayout"; attribute :>> lemma="EmissionView.resolveLayoutPreserves"; }
part migration3:MigrationRow { attribute :>> key="emission-write-helper"; attribute :>> producerAnchor="resource-flags"; attribute :>> consumerAnchor="primitive-late-helper"; attribute :>> actionName="emission_view_correspondence.lateLayoutWrite"; attribute :>> lemma="EmissionView.lateLayoutWritePreserves"; }
part migration4:MigrationRow { attribute :>> key="C-fragment-payload"; attribute :>> producerAnchor="parse-init"; attribute :>> consumerAnchor="init-output"; attribute :>> actionName="emission_view_correspondence.copyFragments"; attribute :>> lemma="EmissionView.copyFragmentsPreserves"; }
part migration5:MigrationRow { attribute :>> key="linker-payload"; attribute :>> producerAnchor="link-read"; attribute :>> consumerAnchor="link-vector-copy"; attribute :>> actionName="emission_view_correspondence.freezeInputs"; attribute :>> lemma="EmissionView.freezeInputsPreserves"; }
part migration6:MigrationRow { attribute :>> key="paired-close"; attribute :>> producerAnchor="stream-open"; attribute :>> consumerAnchor="stream-close"; attribute :>> actionName="emission_view_correspondence.issue"; attribute :>> lemma="EmissionView.receiptCoverageAndClose"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse6; attribute :>> contract="emission-pair-member-contract"; attribute :>> actionName="emission_view_correspondence.issue"; attribute :>> lemma="EmissionView.receiptSameView"; }
part seam1:SeamRow { ref part :>> producer=GambitAssuranceRelations::modelUse4; ref part :>> consumer=GambitAssuranceRelations::modelUse2; attribute :>> contract="capsule-root-and-borrow-closure"; attribute :>> actionName="emission_view_correspondence.closeAliases"; attribute :>> lemma="EmissionView.closeAliasesPreserves"; }
part seam2:SeamRow { ref part :>> producer=GambitAssuranceRelations::modelUse5; ref part :>> consumer=GambitAssuranceRelations::modelUse2; attribute :>> contract="FrameSpec-and-resolved-cells"; attribute :>> actionName="emission_view_correspondence.resolveLayout"; attribute :>> lemma="EmissionView.resolveLayoutPreserves"; }
part seam3:SeamRow { ref part :>> producer=GambitAssuranceRelations::modelUse2; ref part :>> consumer=GambitAssuranceRelations::modelUse6; attribute :>> contract="text-versus-native-qualification"; attribute :>> actionName="emission_view_correspondence.nativePermit"; attribute :>> lemma="EmissionViewComposition.nativeQualifierFitsParent"; }
part history:GambitAssuranceRouting::ModelNeed { ref part :>> owner=GambitAssuranceRelations::modelUse2; attribute :>> obligationId="EV-history"; attribute :>> kind="interleaving"; attribute :>> subjectPath="dev/refactoring/modern-c/models/quint/emission_view_correspondence.qnt"; attribute :>> subjectScope="Late roots accepted writers alias closure layout output epoch and unknown close histories"; attribute :>> premise="Conditional research; no source emitter or native admission"; }
part induction:GambitAssuranceRouting::ModelNeed { ref part :>> owner=GambitAssuranceRelations::modelUse2; attribute :>> obligationId="EV-induction"; attribute :>> kind="induction"; attribute :>> subjectPath="dev/refactoring/modern-c/models/lean/EmissionView.lean"; attribute :>> subjectScope="All extracted sequential steps; complete producer closure and verifier qualification external"; attribute :>> premise="Conditional research; no source emitter or native admission"; }
part composition:GambitAssuranceRouting::ModelNeed { ref part :>> owner=GambitAssuranceRelations::modelUse2; attribute :>> obligationId="EV-composition"; attribute :>> kind="induction"; attribute :>> subjectPath="dev/refactoring/modern-c/models/lean/EmissionViewComposition.lean"; attribute :>> subjectScope="Ordered symbolic chunks count counterexample and preceding native qualifier only"; attribute :>> premise="Conditional research; no source emitter or native admission"; }
part projection:GambitAssuranceRouting::ModelNeed { ref part :>> owner=GambitAssuranceRelations::modelUse2; attribute :>> obligationId="EV-projection"; attribute :>> kind="restricted-projection"; attribute :>> subjectPath="dev/refactoring/modern-c/models/lean/EmissionViewAst.lean"; attribute :>> subjectScope="Typed state binding field kinds supported expressions and full action roster"; attribute :>> premise="Conditional research; no source emitter or native admission"; }
part source:GambitAssuranceRouting::ModelNeed { ref part :>> owner=GambitAssuranceRelations::modelUse2; attribute :>> obligationId="EV-source"; attribute :>> kind="source-refinement"; attribute :>> subjectPath="dev/refactoring/modern-c/emission-view-correspondence-design.org"; attribute :>> subjectScope="Actual entire writer/alias/input/GC/exception closure and legal-domain reflection OPEN"; attribute :>> premise="Conditional research; no source emitter or native admission"; }
part platform:GambitAssuranceRouting::ModelNeed { ref part :>> owner=GambitAssuranceRelations::modelUse2; attribute :>> obligationId="EV-platform"; attribute :>> kind="native-memory-order"; attribute :>> subjectPath="dev/refactoring/modern-c/emission-view-correspondence-design.org"; attribute :>> subjectScope="Concrete C11 producer close capsule ownership publication and I/O outcome refinement OPEN"; attribute :>> premise="Conditional research; no source emitter or native admission"; }
part emission:GambitAssuranceRouting::ModelNeed { ref part :>> owner=GambitAssuranceRelations::modelUse2; attribute :>> obligationId="EV-emission"; attribute :>> kind="emitter-fidelity"; attribute :>> subjectPath="dev/refactoring/modern-c/emission-view-correspondence-design.org"; attribute :>> subjectScope="Full per-constructor C encoder ModuleSpec span and profile/macro-layout fidelity OPEN"; attribute :>> premise="Conditional research; no source emitter or native admission"; }
}
