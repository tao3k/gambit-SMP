package GambitHeaderDelivery {
  private import ScalarValues::*;
  part def Unit { attribute id:String; attribute stage:String; }
  part unit:Unit { attribute :>> id="header-organization"; attribute :>> stage="organization"; }
  ref part partition = GambitHeaderOrganization::h_platform;
  attribute baseRevision:String="dfec5508118afef2dc9bd1ade5c928930e63c0fa";
  attribute candidateTree:String="3eea42fc9bbbfd427a39e91c9bef556964fb8097";
  attribute evidence:String="evidence/research/header-delivery/results.json";
  attribute scope:String="One complete structural unit:40 private header templates and4 configure/Make publication inputs. Configured public header is byte-identical to the pre-role frame baseline. All Scheme, native C bodies, runtime layouts, GC, FFI, scheduler and memory sources are unchanged.";
  attribute process:String="Deliver the header unit before memory organization and before the unpublished role prototype. Preserve the original role commit, staged research, working research and all failed observations in explicit Git/evidence custody before reordering local unpublished history. Header acceptance does not accept the whole organization stage or any runtime prototype.";
  attribute formalDuty:String="Native SysML owns the partition and selected five-gate scope. Actual ASCENT checks bound source/profile/artifact evidence and negative controls. Exact whole-public-header equality is deterministic representation refinement; no concurrent transition or new mathematical runtime law is introduced, so QNT and Lean are neither duplicated nor used to restate byte comparisons.";
  attribute benefit:String="One15240-line maintenance unit becomes40 responsibility templates while consumers still read one flat public header. All40 rebuild and distribution edges become explicit. There is no runtime speedup, new GC, independent worker or SMP milestone claim.";
  attribute addedCost:String="40 source files, one ordered inventory and explicit configure/Make publication. Object code, public header path and runtime ABI are unchanged relative to the selected baseline; broader role/binary migrations are not accepted.";
  attribute validationBoundary:String="This unit qualifies source/configuration/consumer equivalence. Native checks use the retained Bazel profile substitutions, GCC C23 and Clang preprocessing, an original C object pair and the existing frame producer/consumer. It does not claim a fresh configure-probe campaign, linked runtime, complete bootstrap, Gerbil test suite or twelve-SMP acceptance. Prototype bootstrap failures stay failed in their original scope, rather than being repaired in a byte-preserving unit.";
  attribute status:String="BLOCKED-TEMPLATE-WRITERS-AND-ALTERNATIVE-CONFIGURATORS";
  part def Need { ref part gate:GambitCommitGates::Gate; attribute id:String; attribute method:String; attribute artifact:String; attribute scope:String; }
  part bytes:Need { ref part :>> gate=GambitCommitGates::tests; attribute :>> id="H-BYTES"; attribute :>> method="source-refinement"; attribute :>> artifact="evidence/research/header-delivery/candidate-tree.json"; attribute :>> scope="all40-ordered-payloads-exactly-reconstruct490621-HEAD-baseline-bytes-only44-header-publication-paths-change"; }
  part configuration:Need { ref part :>> gate=GambitCommitGates::tests; attribute :>> id="H-CONFIG"; attribute :>> method="native"; attribute :>> artifact="vendor/gambit/configure.ac"; attribute :>> scope="byte-identical-flat-header-under-recorded-profile-substitutions-and-both-shipped-configure-data-maps-no-generator-upgrade"; }
  part consumers:Need { ref part :>> gate=GambitCommitGates::tests; attribute :>> id="H-CONSUMERS"; attribute :>> method="native"; attribute :>> artifact="vendor/gambit/include/gambit.h.in"; attribute :>> scope="GCC-C23-header-GCC-Clang-preprocessing-original-memory-object-byte-equality-and-native-frame-consumers-at3-5-25-registers"; }
  part dependencies:Need { ref part :>> gate=GambitCommitGates::tests; attribute :>> id="H-DEPENDENCIES"; attribute :>> method="native"; attribute :>> artifact="vendor/gambit/include/makefile.in"; attribute :>> scope="unchanged-header-is-up-to-date-all40-independent-edits-rebuild-and-all40-relative-distribution-paths-preserve-bytes"; }
  part templateConsumers:Need { ref part :>> gate=GambitCommitGates::tests; attribute :>> id="H-TEMPLATE-CONSUMERS"; attribute :>> method="source-refinement"; attribute :>> artifact="vendor/gambit/include/gambit.h.in"; attribute :>> scope="change-gvm-regs-changev-configure-probe-and-Windows-template-renderers-preserve-all-original-inputs-and-writes"; }
  part learning:Need { ref part :>> gate=GambitCommitGates::learning; attribute :>> id="H-LESSON"; attribute :>> method="source-analysis"; attribute :>> artifact="dev/refactoring/modern-c/header-delivery.org"; attribute :>> scope="source-responsibility-retirement-cost-and-why-no-runtime-performance-or-SMP-gain-is-inferred"; }
  part processNeed:Need { ref part :>> gate=GambitCommitGates::process; attribute :>> id="H-PROCESS"; attribute :>> method="source-analysis"; attribute :>> artifact="dev/refactoring/modern-c/models/sysml/header-delivery.sysml"; attribute :>> scope="header-unit-before-memory-unit-and-role-prototype-exact44-path-tree-with-retained-unpublished-research-and-failures"; }
  part models:Need { ref part :>> gate=GambitCommitGates::models; attribute :>> id="H-MODELS"; attribute :>> method="native-model-projection"; attribute :>> artifact="dev/refactoring/modern-c/models/sysml/header-delivery.sysml"; attribute :>> scope="actual-native-partition-projection-and-ASCENT-positive-stale-tree-wrong-artifact-missing-test-and-wrong-evidence-class-controls"; }
  part questions:Need { ref part :>> gate=GambitCommitGates::questions; attribute :>> id="H-QUESTIONS"; attribute :>> method="source-analysis"; attribute :>> artifact="dev/refactoring/modern-c/header-delivery.org"; attribute :>> scope="Gambit-C-portability-tail-multishot-invariants-preserved-by-unchanged-public-bytes-organization-not-runtime-ownership-and-why-later-prototype-failures-remain-unaccepted"; }
}
