package GambitModernCBootstrapCohort {
  private import ScalarValues::*;
  ref part target = GambitRuntimeRoleRealization::cut0;
  ref part submissionGate = GambitModernCCommitAdmission::tests;
  attribute nativeAcceptance : Boolean = false;
  attribute referencePatchSourceImported : Boolean = false;
  part def Boundary { attribute id:String; attribute route:String; attribute invariant:String; attribute benefit:String; attribute cost:String; }
  part host : Boundary { attribute :>> id="host"; attribute :>> route="complete current compiler source graph -> independent AOT host ABI -> emitter for target ABI; interpreted igsc retained as a diagnostic"; attribute :>> invariant="Compile all compiler modules together, not a partial backend overlay. Host native ABI and emitted target ABI are distinct; host runtime is never linked into target. Source/SDK/argv and dependency assumptions remain explicit."; attribute :>> benefit="Break old-C/new-header bootstrap cycle and remove interpreted compiler execution from each target emission without restoring carrier aliases or importing repair runtime"; attribute :>> cost="One whole host compiler AOT build and host SDK storage; no automatic cache-reuse claim without complete source/effect dependency closure"; }
  part argv : Boundary { attribute :>> id="argv"; attribute :>> route="process.scm command-line/script-command-line -> igsc canonical processed argv -> main.scm command-args"; attribute :>> invariant="Strip Make runtime aliases from effective script argv, clear the obsolete script view, and preserve all compiler argument words"; attribute :>> benefit="Eliminate two inconsistent option views; real Make prelude/warnings/source arguments produce C instead of zero-output returns"; attribute :>> cost="One normalization per invocation; no general shell string decoder or global FFI rewrite claim"; }
  part inventory : Boundary { attribute :>> id="inventory"; attribute :>> route="leased source-state inputs -> all top-level lib/gsi/gsc _*.c -> bootclean -> complete generated hash inventory"; attribute :>> invariant="Required module and linker C units are known before deletion; failed emission cannot shrink the required set to zero"; attribute :>> benefit="Old module metadata cannot silently survive a changed FrameSpec/ModuleSpec/runtime ABI"; attribute :>> cost="All affected C products must be regenerated; correctness work is added, not an incremental-build speedup"; }
  part targetNative : Boundary { attribute :>> id="target-native"; attribute :>> route="same Bazel configure profile -> generated C -> target libgambit/gsi/gsc"; attribute :>> invariant="Existing O1 modules/O3 runtime and SMP/multiple-VM/threaded-VM flags; exact effective argv/headers recorded; artifact success and quiescence required"; attribute :>> benefit="One explicit target cohort replaces accidental reuse of old generated carrier accesses"; attribute :>> cost="No old C shortcut across incompatible layout; canonical compiler/root/lifetime consumers still need native acceptance"; }
  part temporaryRoots : Boundary { attribute :>> id="temporary-roots"; attribute :>> route="GC_SAVE/RESTORE1..3 and os_setup six service families -> execution_context.saved -> mark_execution_roots -> reload/clear"; attribute :>> invariant="All raw temporary-root consumers migrate with their scanner. 78 os_setup accesses retain existing conversion/result/error clearing behavior. No carrier alias is restored; fixed three-slot capacity is not arbitrary nested-FFI admission."; attribute :>> benefit="Source-complete execution-root ownership covers generated allocation helpers and OS service constructors instead of only six previously compiled C units"; attribute :>> cost="Existing context indirection at each access; no additional root slots or root-scan range; native GC/FFI progress remains to qualify"; }
  part selfPass : Boundary { attribute :>> id="self"; attribute :>> route="new target gsc -> fresh bootclean -> target self-source pass -> hash/identity receipt"; attribute :>> invariant="hostedSource and regeneration checkpoints are distinct; a host pass cannot suppress the real self pass"; attribute :>> benefit="Compiler/runtime agreement is checked through an actual target compiler invocation"; attribute :>> cost="Second source generation/compilation pass; no model or first-pass result substitutes for it"; }
  part semantics : Boundary { attribute :>> id="semantics"; attribute :>> route="new target gsc -exe -> tests/frame-continuation-roots.scm -> real map capture, two restores, GC and native call"; attribute :>> invariant="Original, 20 and 200 restored map results; 80 retained roots; expected wind/visit history; 11 completed forced GCs; native call count 3"; attribute :>> benefit="Exercise Gambit multi-shot semantics together with frame/GC/native consumers"; attribute :>> cost="Independent carrier retirement, all FFI callbacks and failed membership remain separate open gates"; }
  part startupCapacity : Boundary { attribute :>> id="startup-capacity"; attribute :>> route="current_vm_resize -> vm_resize_pstate -> GC resize_heap -> setup_pstate/setup_mem_pstate -> two physical startup sections per new context"; attribute :>> invariant="GC membership is the closed existing set; requested contexts are future consumers. A grant must cover already assigned physical sections plus two per pending context and bounded resume reserve. Unknown allocation or capped capacity below the floor cannot publish a grant. Proposed planner is not implemented."; attribute :>> benefit="Replace nominal global minimum with a physical reservation contract before member/thread publication; source and native evidence explain the host-budget p11 startup failure"; attribute :>> cost="Explicit growth reservation can increase peak physical sections; interval/allocator/rollback and C refinement remain open. No larger heap or forced p1 setting qualifies the failed SMP lane."; }
  part def Link { ref part producer:Boundary; ref part consumer:Boundary; }
  part e0:Link { ref part :>> producer=host; ref part :>> consumer=argv; }
  part e1:Link { ref part :>> producer=argv; ref part :>> consumer=inventory; }
  part e2:Link { ref part :>> producer=inventory; ref part :>> consumer=temporaryRoots; }
  part er:Link { ref part :>> producer=temporaryRoots; ref part :>> consumer=targetNative; }
  part e3:Link { ref part :>> producer=targetNative; ref part :>> consumer=selfPass; }
  part e4:Link { ref part :>> producer=selfPass; ref part :>> consumer=startupCapacity; }
  part ec:Link { ref part :>> producer=startupCapacity; ref part :>> consumer=semantics; }
  part def Obligation { ref part boundary:Boundary; attribute id:String; attribute method:String; attribute artifact:String; attribute premise:String; }
  part hostCheck:Obligation { ref part :>> boundary=host; attribute :>> id="BC-HOST"; attribute :>> method="native-host"; attribute :>> artifact="evidence/research/modern-c-bootstrap/hash-index-host.json"; attribute :>> premise="Whole 34-module host, stable source/SDK inputs, real Make-shaped emission; host qualification only"; }
  part argvCheck:Obligation { ref part :>> boundary=argv; attribute :>> id="BC-ARGV"; attribute :>> method="native-host"; attribute :>> artifact="vendor/gambit/gsc/igsc.scm"; attribute :>> premise="Effective script/process compiler argv and a real generated C output; no exit-zero-only success"; }
  part products:Obligation { ref part :>> boundary=targetNative; attribute :>> id="BC-PRODUCTS"; attribute :>> method="native-first-pass"; attribute :>> artifact="evidence/research/modern-c-bootstrap/hash-index-reviewed-bootstrap.recipe.json"; attribute :>> premise="All 51 generated products and three linked target artifacts with stable source and quiescent successful first pass; not complete self bootstrap or GC semantics"; }
  part rootControl:Obligation { ref part :>> boundary=temporaryRoots; attribute :>> id="BC-TEMP"; attribute :>> method="native-control"; attribute :>> artifact="vendor/gambit/tests/runtime-roles.c"; attribute :>> premise="All three scratch-root macro families reload collector-updated roots, clear them and isolate contexts; old macro compilation fails; projection only, not linked GC"; }
  part qnt:Obligation { ref part :>> boundary=inventory; attribute :>> id="BC-QNT"; attribute :>> method="quint"; attribute :>> artifact="dev/refactoring/modern-c/models/quint/bootstrap_cohort.qnt"; attribute :>> premise="Two abstract coverage classes require universal coverage of all 51 native filenames, including 5 linker products; argv agreement, self-pass distinction and no host linkage; finite safety is not native success"; }
  part coverage:Obligation { ref part :>> boundary=inventory; attribute :>> id="BC-COVER"; attribute :>> method="lean"; attribute :>> artifact="dev/refactoring/modern-c/models/lean/BootstrapCohort.lean"; attribute :>> premise="Universal per-class coverage reflects complete filename coverage only under total required-name mapping. One representative per class is insufficient. Actual source manifest/compilation correctness remains a native refinement obligation."; }
  part lean:Obligation { ref part :>> boundary=temporaryRoots; attribute :>> id="BC-REFINE"; attribute :>> method="lean-source-refinement"; attribute :>> artifact="dev/refactoring/modern-c/models/lean/RuntimeRoles.lean"; attribute :>> premise="OPEN: prove actual generated FrameSpec/root consumers and C barriers preserve the existing conditional root laws; host compiler semantic trust stays explicit"; }
  part native:Obligation { ref part :>> boundary=selfPass; attribute :>> id="BC-NATIVE"; attribute :>> method="native"; attribute :>> artifact="evidence/research/modern-c-bootstrap/hash-index-reviewed-bootstrap.recipe.json"; attribute :>> premise="Actual source and self passes plus real semantic case required. Complete official bootstrap additionally needs two occurrences of each phase1..4. Known pre-generated/uncanonical argv failures and interpreted timeout remain retained."; }
  part earlyGC:Obligation { ref part :>> boundary=semantics; attribute :>> id="BC-EARLY-GC"; attribute :>> method="native"; attribute :>> artifact="vendor/gambit/lib/mem.c"; attribute :>> premise="Default-heap new compiler must initialize primitive tables across real GC before any map admission. Larger initial heap is diagnostic only. Five observed collections and a heap-sensitive outcome do not prove the exact lost root or responsible refactoring."; }
  part ascent:Obligation { ref part :>> boundary=semantics; attribute :>> id="BC-ADMISSION"; attribute :>> method="ascent"; attribute :>> artifact="dev/modeling/ascent/commit-admission.rules.scm"; attribute :>> premise="T-COHORT/T-MAP/T-SMP and M-REFINE stay missing until exact current-source observations exist; no synthetic or historical score transfer"; }
  part capacityQnt:Obligation { ref part :>> boundary=startupCapacity; attribute :>> id="BC-CAP-QNT"; attribute :>> method="quint"; attribute :>> artifact="dev/refactoring/modern-c/models/quint/context_startup_capacity.qnt"; attribute :>> premise="Proposed growth grant/initialization conservation; old unclamped floor, dense live regions, closed-census-as-target and unknown-as-grant counterexamples; not current C correctness"; }
  part capacityLean:Obligation { ref part :>> boundary=startupCapacity; attribute :>> id="BC-CAP-LEAN"; attribute :>> method="lean"; attribute :>> artifact="dev/refactoring/modern-c/models/lean/ContextStartupCapacity.lean"; attribute :>> premise="Physical-section arithmetic is conditional on allocator correspondence, checked bounds, complete roots and actual successful reservation"; }
  part capacityNative:Obligation { ref part :>> boundary=startupCapacity; attribute :>> id="BC-CAP-NATIVE"; attribute :>> method="native"; attribute :>> artifact="vendor/gambit/lib/setup.c"; attribute :>> premise="OPEN: unchanged profile host-budget p11 GSC and compiled program must initialize without fatal heap overflow; single-context map success cannot close this gap"; }
}
