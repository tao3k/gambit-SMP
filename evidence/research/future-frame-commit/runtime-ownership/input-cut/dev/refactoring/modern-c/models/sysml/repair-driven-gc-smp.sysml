/* Research bridge from retained repair evidence to existing canonical owners. No native satisfaction. */
package GambitRepairDrivenRefactor { private import ScalarValues::*;
part def SourceRow { attribute key:String; attribute path:String; attribute needle:String; attribute limit:String; }
part source0:SourceRow { attribute :>> key="milestone"; attribute :>> path="evidence/research/processor-interrupt-collective-wait/repair-9-12-native-observation.json"; attribute :>> needle="\"milestone\": \"8/12\""; attribute :>> limit="registered historical milestone; not a live monitor"; }
part source1:SourceRow { attribute :>> key="gate-audit"; attribute :>> path="docs/current-repair-obligation-map.md"; attribute :>> needle="lifecycle failure/rollback"; attribute :>> limit="four separate acceptance contracts; row order is not ordinal identity"; }
part source2:SourceRow { attribute :>> key="repair-cut"; attribute :>> path="docs/current-repair-research.md"; attribute :>> needle="c38e coherent wait-return integration"; attribute :>> limit="documentary cut on 2026-10-26; no claim of latest in-flight repair state"; }
part source3:SourceRow { attribute :>> key="wait-gain"; attribute :>> path="evidence/research/smp-retirement-study/delivery-048b-select-return.json"; attribute :>> needle="048b7f9f8c247e8a35056ccdb3b1979f5810b89cd6da1858c50b4752225cb9fd"; attribute :>> limit="short-work gain and original failure remain independent"; }
part source4:SourceRow { attribute :>> key="wait-current"; attribute :>> path="evidence/research/smp-retirement-study/delivery-c38e-wait-handoff.json"; attribute :>> needle="c38e034363550cdeeea0e04bb70c0799f97eaf84340bc70626501eee0f2c1f45"; attribute :>> limit="unexplained first GC-pair timeout remains; no original started in this snapshot"; }
part source5:SourceRow { attribute :>> key="first-error"; attribute :>> path="evidence/research/smp-retirement-study/delivery-2fe7-first-cause.json"; attribute :>> needle="thread-state-normally-terminated"; attribute :>> limit="focused diagnosis only; not the cause of every later outer join error"; }
part source6:SourceRow { attribute :>> key="parallel-cost"; attribute :>> path="evidence/research/smp-retirement-study/delivery-60b3-cost-attribution.json"; attribute :>> needle="0.518624"; attribute :>> limit="same-work topology amplification; negative p1 allocation is invalid, not zero"; }
part source7:SourceRow { attribute :>> key="memory-wrapper"; attribute :>> path="vendor/gambit/lib/mem.c"; attribute :>> needle="#include \"_mem/collection-round.inc\""; attribute :>> limit="working modular tree; inclusion order and #line are diagnostic mapping, not frozen native identity"; }
part source8:SourceRow { attribute :>> key="root-task"; attribute :>> path="vendor/gambit/lib/_mem/collection-round.inc"; attribute :>> needle="___gc_root_task_claim(task,vm->gc_round.epoch,phase,owner)"; attribute :>> limit="working tree already splits context and worker; not a qualified successor of repair image"; }
part source9:SourceRow { attribute :>> key="rc-domain"; attribute :>> path="vendor/gambit/lib/_mem/rc-roots.inc"; attribute :>> needle="RC root task requires a closed context domain"; attribute :>> limit="closed writer domain and root task must compose; not old P0-only baseline"; }
part source10:SourceRow { attribute :>> key="resize-roots"; attribute :>> path="vendor/gambit/lib/_mem/root-origins.inc"; attribute :>> needle="resize_requests[i].thunk"; attribute :>> limit="retained request roots stay VM-owned across origin removal"; }
part source11:SourceRow { attribute :>> key="chunk-publish"; attribute :>> path="vendor/gambit/lib/_mem/heap-sections.inc"; attribute :>> needle="require_chunk_transition(work,alloc_heap_chunk_start,0,1);"; attribute :>> limit="actual private/public queue handoff needs full C23 and termination refinement"; }
part source12:SourceRow { attribute :>> key="frame-map"; attribute :>> path="vendor/gambit/lib/_mem/continuation-roots.inc"; attribute :>> needle="mark_array (work, orig_ptr, 1);"; attribute :>> limit="captured frames and caller root slot map remain part of moving-root contract"; }
part source13:SourceRow { attribute :>> key="generated-frame"; attribute :>> path="vendor/gambit/include/_gambit/gvm_operations.h.in"; attribute :>> needle="#define ___FRAME_STORE_RA(ra)"; attribute :>> limit="mechanical frame operation, not automatic proof of all native entry coverage"; }
part source14:SourceRow { attribute :>> key="scheme-stress"; attribute :>> path="vendor/gambit/tests/unit-tests/06-thread/thread_interrupt2_stress.scm"; attribute :>> needle="(thread-sleep! 1000)"; attribute :>> limit="ten million calls per target, original deadlines and per-target fairness are semantic constraints"; }
part source15:SourceRow { attribute :>> key="feeley-pvm"; attribute :>> path="dev/refactoring/modern-c/modernization-target.org"; attribute :>> needle="Feeley and Miller"; attribute :>> limit="retained local literature synthesis; no new external paper read or borrowed speedup"; }
part source16:SourceRow { attribute :>> key="ocaml-learning"; attribute :>> path="dev/architecture/runtime/gc/modern-c-generational-design.org"; attribute :>> needle="Retrofitting Parallelism onto OCaml"; attribute :>> limit="mechanism learning and tradeoffs, not a selected Gambit algorithm or imported speedup"; }
part def GateRow { attribute key:String; attribute definition:String; attribute required:String; attribute status:String; attribute limit:String; }
part gate0:GateRow { attribute :>> key="lifecycle"; attribute :>> definition="lifecycle failure/rollback"; attribute :>> required="Real same-owner/incarnation joinable failure, recovery, reentry and old handler quiescence"; attribute :>> status="open; historical 8/12 only"; attribute :>> limit="Not a synthesized pre-join refusal or drop counters forced to zero"; }
part gate1:GateRow { attribute :>> key="gc-ffi"; attribute :>> definition="complete GC/FFI"; attribute :>> required="Both applicable unchanged full inventories plus original pressure and exact generated/root ABI"; attribute :>> status="open; historical 8/12 only"; attribute :>> limit="A selected bridge or short GC control is insufficient"; }
part gate2:GateRow { attribute :>> key="gerbil"; attribute :>> definition="Gerbil correctness"; attribute :>> required="Source-causal binding/object repair and complete downstream build/tests on matching runtime"; attribute :>> status="open; historical 8/12 only"; attribute :>> limit="No assumption that non-symbol binding or typeid failure is uniquely a GC error"; }
part gate3:GateRow { attribute :>> key="release"; attribute :>> definition="release performance"; attribute :>> required="Matched complete original campaigns, useful work, CPU/wall/GC/memory and retained failures"; attribute :>> status="open; historical 8/12 only"; attribute :>> limit="Short speedups, changed topology and diagnostic timing do not earn release"; }
part def EdgeRow { attribute fromNode:String; attribute toNode:String; attribute contract:String; }
part edge0:EdgeRow { attribute :>> fromNode="generated-boundary"; attribute :>> toNode="native-roots"; attribute :>> contract="effect-complete entries publish roots before allocation or sync"; }
part edge1:EdgeRow { attribute :>> fromNode="native-roots"; attribute :>> toNode="collector-work"; attribute :>> contract="freeze writers; publish complete root tasks; scanner updates actual slots"; }
part edge2:EdgeRow { attribute :>> fromNode="scheduler-participation"; attribute :>> toNode="collector-work"; attribute :>> contract="old cohort remains serviceable; avoid holder/collector wait cycle"; }
part edge3:EdgeRow { attribute :>> fromNode="collector-work"; attribute :>> toNode="generational-heap"; attribute :>> contract="producer and root closure precede selective-scan retirement"; }
part edge4:EdgeRow { attribute :>> fromNode="request-control"; attribute :>> toNode="generational-heap"; attribute :>> contract="semantic stores and true retained request graph define remembered edges"; }
part edge5:EdgeRow { attribute :>> fromNode="request-control"; attribute :>> toNode="retirement-recovery"; attribute :>> contract="original result/exception and accepted responsibility survive owner exit"; }
part edge6:EdgeRow { attribute :>> fromNode="collector-work"; attribute :>> toNode="retirement-recovery"; attribute :>> contract="no private/weak work or scan borrower before reclaim"; }
part edge7:EdgeRow { attribute :>> fromNode="generated-boundary"; attribute :>> toNode="artifact-qualification"; attribute :>> contract="FrameSpec/ABI changes invalidate all dependent generated and native products"; }
part edge8:EdgeRow { attribute :>> fromNode="artifact-qualification"; attribute :>> toNode="gc-ffi"; attribute :>> contract="same-image original inventories"; }
part edge9:EdgeRow { attribute :>> fromNode="retirement-recovery"; attribute :>> toNode="lifecycle"; attribute :>> contract="natural failure and recovery; no cross-credit"; }
part edge10:EdgeRow { attribute :>> fromNode="request-control"; attribute :>> toNode="release"; attribute :>> contract="same-work measurements; normal and enabled observation modes"; }
part edge11:EdgeRow { attribute :>> fromNode="generational-heap"; attribute :>> toNode="release"; attribute :>> contract="net tracing saved exceeds barrier/promotion/synchronization costs"; }
part def RefactorCut { ref part owner:GambitRuntimeComposition::BlueprintModule; ref part seam:GambitRuntimeComposition::BlueprintInterface; ref part history:GambitAssuranceRouting::ModelNeed; ref part induction:GambitAssuranceRouting::ModelNeed; attribute key:String; attribute evidence:String; attribute observation:String; attribute replacement:String; attribute retirement:String; attribute avoided:String; attribute added:String; attribute sourceGap:String; attribute actionName:String; attribute lemmaName:String; attribute projection:String; attribute status:String; }
part need0Q:GambitAssuranceRouting::ModelNeed { ref part :>> owner=GambitRuntimeAssurance::roots.component; attribute :>> obligationId="REPAIR-REFACTOR-generated-boundary-Q"; attribute :>> kind="interleaving"; attribute :>> subjectPath="models/gambit/ffi_gc_frame_protocol.qnt"; attribute :>> subjectScope="repair-driven:generated-boundary:source-composition-open"; attribute :>> premise="Complete primitive/FFI effect closure, generated label mapping and selected-GC-inside-startup witness; existing fragment is not whole-source refinement or a timing theorem"; }
part need0L:GambitAssuranceRouting::ModelNeed { ref part :>> owner=GambitRuntimeAssurance::roots.component; attribute :>> obligationId="REPAIR-REFACTOR-generated-boundary-L"; attribute :>> kind="induction"; attribute :>> subjectPath="models/gambit/lean/SavedStackRootClosure.lean"; attribute :>> subjectScope="repair-driven:generated-boundary:source-composition-open"; attribute :>> premise="Complete primitive/FFI effect closure, generated label mapping and selected-GC-inside-startup witness; existing fragment is not whole-source refinement or a timing theorem"; }
part cut0:RefactorCut { ref part :>> owner=GambitRuntimeComposition::blueprintModule0; ref part :>> seam=GambitRuntimeComposition::generatedEntryInterface; ref part :>> history=need0Q; ref part :>> induction=need0L; attribute :>> key="generated-boundary"; attribute :>> evidence="repair-cut"; attribute :>> observation="Startup collective can collect while generated entry lacks full writeback/reload evidence"; attribute :>> replacement="Scheme effect/FrameSpec contract emits every GC-capable call bridge, return and exceptional checkpoint"; attribute :>> retirement="Retire handwritten per-site W_ALL/RA choreography after all entries and generated consumers migrate"; attribute :>> avoided="Eliminate repeated discovery of hidden GC-capable calls"; attribute :>> added="Frame metadata, writeback/reload and ABI invalidation"; attribute :>> sourceGap="Complete primitive/FFI effect closure, generated label mapping and selected-GC-inside-startup witness"; attribute :>> actionName="publishRegisters"; attribute :>> lemmaName="declaredClosureCoversActualConsumers"; attribute :>> projection="Concrete generated RA store and register writeback map to saveReturnAddress/publishRegisters; cachedFrame/cachedRoot and processorFrame/processorRoot encode the pre/post root view; relocateRoots then reloadRegisters must update the same frame epoch. Full label/slot coverage remains a premise."; attribute :>> status="source-refinement-open; no new QNT or Lean run"; }
part need1Q:GambitAssuranceRouting::ModelNeed { ref part :>> owner=GambitRuntimeAssurance::roots.component; attribute :>> obligationId="REPAIR-REFACTOR-scheduler-participation-Q"; attribute :>> kind="interleaving"; attribute :>> subjectPath="models/gambit/delivery_service_roots.qnt"; attribute :>> subjectScope="repair-driven:scheduler-participation:source-composition-open"; attribute :>> premise="Actual park/unlock overlap, pending SYNC and contention; weak fairness gives no deadline bound; existing fragment is not whole-source refinement or a timing theorem"; }
part need1L:GambitAssuranceRouting::ModelNeed { ref part :>> owner=GambitRuntimeAssurance::roots.component; attribute :>> obligationId="REPAIR-REFACTOR-scheduler-participation-L"; attribute :>> kind="induction"; attribute :>> subjectPath="models/gambit/lean/WorkAccounting.lean"; attribute :>> subjectScope="repair-driven:scheduler-participation:source-composition-open"; attribute :>> premise="Actual park/unlock overlap, pending SYNC and contention; weak fairness gives no deadline bound; existing fragment is not whole-source refinement or a timing theorem"; }
part cut1:RefactorCut { ref part :>> owner=GambitRuntimeComposition::blueprintModule2; ref part :>> seam=GambitRuntimeComposition::blueprintInterface3; ref part :>> history=need1Q; ref part :>> induction=need1L; attribute :>> key="scheduler-participation"; attribute :>> evidence="wait-current"; attribute :>> observation="Internal wake, true EINTR, IO readiness and EOF previously shared retry behavior"; attribute :>> replacement="Typed private WaitResult and P-locked runnable decision; safe root publication before participating in sync"; attribute :>> retirement="Retire internal-wake-as-EINTR retry and scattered repark guesses after both wait backends qualify"; attribute :>> avoided="Avoid false sleeps, redundant wake/service and lost runnable progress"; attribute :>> added="Reason classification, admission recheck and one nonblocking service slice"; attribute :>> sourceGap="Actual park/unlock overlap, pending SYNC and contention; weak fairness gives no deadline bound"; attribute :>> actionName="readInternalWake"; attribute :>> lemmaName="announcementWithoutAcknowledgementIsNotReady"; attribute :>> projection="Concrete positive internal byte/event maps to notified/readInternalWake and wakeRead; true signal maps to ordinarySignal; runnable work and unlock/dispatch map to runnable/serviceOwner/locks/phase. The retained model already rejects retryAfterInternalWake, reparkQueued and deadlineRevision changes. Its finite wait fallback and action fairness do not prove full source/C23 or throughput."; attribute :>> status="source-refinement-open; no new QNT or Lean run"; }
part need2Q:GambitAssuranceRouting::ModelNeed { ref part :>> owner=GambitRuntimeAssurance::work.component; attribute :>> obligationId="REPAIR-REFACTOR-collector-work-Q"; attribute :>> kind="interleaving"; attribute :>> subjectPath="models/gambit/gc_work_closure.qnt"; attribute :>> subjectScope="repair-driven:collector-work:source-composition-open"; attribute :>> premise="All producer enumeration, partial copy/frame publication, weak work and native C23 memory model; existing fragment is not whole-source refinement or a timing theorem"; }
part need2L:GambitAssuranceRouting::ModelNeed { ref part :>> owner=GambitRuntimeAssurance::work.component; attribute :>> obligationId="REPAIR-REFACTOR-collector-work-L"; attribute :>> kind="induction"; attribute :>> subjectPath="models/gambit/lean/WorkAccounting.lean"; attribute :>> subjectScope="repair-driven:collector-work:source-composition-open"; attribute :>> premise="All producer enumeration, partial copy/frame publication, weak work and native C23 memory model; existing fragment is not whole-source refinement or a timing theorem"; }
part cut2:RefactorCut { ref part :>> owner=GambitRuntimeComposition::blueprintModule4; ref part :>> seam=GambitRuntimeComposition::blueprintInterface4; ref part :>> history=need2Q; ref part :>> induction=need2L; attribute :>> key="collector-work"; attribute :>> evidence="chunk-publish"; attribute :>> observation="GC private work, root tasks and resize owners require different lifetimes"; attribute :>> replacement="VM epoch owns participant cut; worker owns scan/copy/Tail custody independent of execution carrier"; attribute :>> retirement="Retire residual PSTATE/cursor aliases only after private, queued, claimed and weak producers all discharge"; attribute :>> avoided="Reduce repeated ownership reconstruction and incorrect empty-queue conclusions"; attribute :>> added="Explicit task state, root cut and transfer/termination synchronization"; attribute :>> sourceGap="All producer enumeration, partial copy/frame publication, weak work and native C23 memory model"; attribute :>> actionName="finishScan"; attribute :>> lemmaName="zeroCountAndEmptyQueuesExcludeHiddenWork"; attribute :>> projection="Concrete work descriptors project to work 2 private-copy, 4 queued, 5 scanning, 6 scanned with owner/visible/active/count. finishScan may discover a child before the parent disappears; ProducerLifetimeSafe needs all actual Tail/copy/weak producers. Physical chunks and variable frame regions are not one-to-one objects."; attribute :>> status="source-refinement-open; no new QNT or Lean run"; }
part need3Q:GambitAssuranceRouting::ModelNeed { ref part :>> owner=GambitRuntimeAssurance::roots.component; attribute :>> obligationId="REPAIR-REFACTOR-native-roots-Q"; attribute :>> kind="interleaving"; attribute :>> subjectPath="models/gambit/host_roots_contract.qnt"; attribute :>> subjectScope="repair-driven:native-roots:source-composition-open"; attribute :>> premise="Nonzero processor, indirect FFI setters, nested callback and failed/unknown join consumers; existing fragment is not whole-source refinement or a timing theorem"; }
part need3L:GambitAssuranceRouting::ModelNeed { ref part :>> owner=GambitRuntimeAssurance::roots.component; attribute :>> obligationId="REPAIR-REFACTOR-native-roots-L"; attribute :>> kind="induction"; attribute :>> subjectPath="models/gambit/lean/HostRootParticipation.lean"; attribute :>> subjectScope="repair-driven:native-roots:source-composition-open"; attribute :>> premise="Nonzero processor, indirect FFI setters, nested callback and failed/unknown join consumers; existing fragment is not whole-source refinement or a timing theorem"; }
part cut3:RefactorCut { ref part :>> owner=GambitRuntimeComposition::blueprintModule3; ref part :>> seam=GambitRuntimeComposition::blueprintInterface1; ref part :>> history=need3Q; ref part :>> induction=need3L; attribute :>> key="native-roots"; attribute :>> evidence="rc-domain"; attribute :>> observation="Borrowed RC payloads and retained resize requests outlive original processor execution"; attribute :>> replacement="VM-scoped root registration and closed writable domains; scanner updates then execution reloads"; attribute :>> retirement="Retire donor-list-only root transfer and allocating marker before protected ingress only after every caller maps"; attribute :>> avoided="Avoid rescanning/rebuilding ad hoc ownership and lost moving-root coverage"; attribute :>> added="Slot registration, writer closure, GC update and grace-period retention"; attribute :>> sourceGap="Nonzero processor, indirect FFI setters, nested callback and failed/unknown join consumers"; attribute :>> actionName="freeze"; attribute :>> lemmaName="frozenHandoffComposesRelocation"; attribute :>> projection="Concrete protected ingress and RC slot domain map to registered; closed writer domain maps to closing/frozen; claimed root task maps to acquired; moving updates map to moved and owner reload to reloaded. Equal values or a list splice alone cannot establish the relation."; attribute :>> status="source-refinement-open; no new QNT or Lean run"; }
part need4Q:GambitAssuranceRouting::ModelNeed { ref part :>> owner=GambitRuntimeAssurance::control.component; attribute :>> obligationId="REPAIR-REFACTOR-request-control-Q"; attribute :>> kind="interleaving"; attribute :>> subjectPath="models/gambit/delivery_pass_cleanup_composition.qnt"; attribute :>> subjectScope="repair-driven:request-control:source-composition-open"; attribute :>> premise="Dynamic allocation attribution; no pooling while roots, waiters or multishot continuations retain a request; existing fragment is not whole-source refinement or a timing theorem"; }
part need4L:GambitAssuranceRouting::ModelNeed { ref part :>> owner=GambitRuntimeAssurance::control.component; attribute :>> obligationId="REPAIR-REFACTOR-request-control-L"; attribute :>> kind="induction"; attribute :>> subjectPath="models/gambit/lean/WorkAccounting.lean"; attribute :>> subjectScope="repair-driven:request-control:source-composition-open"; attribute :>> premise="Dynamic allocation attribution; no pooling while roots, waiters or multishot continuations retain a request; existing fragment is not whole-source refinement or a timing theorem"; }
part cut4:RefactorCut { ref part :>> owner=GambitRuntimeComposition::blueprintModule5; ref part :>> seam=GambitRuntimeComposition::blueprintInterface6; ref part :>> history=need4Q; ref part :>> induction=need4L; attribute :>> key="request-control"; attribute :>> evidence="parallel-cost"; attribute :>> observation="Per-request pass/hint/catcher machinery and disabled-observer atomics remain reviewable costs"; attribute :>> replacement="One semantic request/result/control plan with context-local representation and exact exceptional suffix"; attribute :>> retirement="Retire duplicate success-path catchers, diagnostic roots and memberships only with equivalent multishot/unwind behavior"; attribute :>> avoided="Potentially reduce allocations, atomics and scheduler handoffs per useful request"; attribute :>> added="Generation tagging, slow-path fallback, preserved exception and continuation capability"; attribute :>> sourceGap="Dynamic allocation attribution; no pooling while roots, waiters or multishot continuations retain a request"; attribute :>> actionName="finish"; attribute :>> lemmaName="balancedNestedExitsCompose"; attribute :>> projection="Concrete accepted pass, publication, payload visibility, VM-lock try, last borrower and completion debit map to handed/visible/claim/ticketBorrow/done/roots/debits in delivery_pass_cleanup_composition. balancedNestedExitsCompose constrains acquired effects only; it does not prove arbitrary Scheme thunk or multishot semantic equivalence."; attribute :>> status="source-refinement-open; no new QNT or Lean run"; }
part need5Q:GambitAssuranceRouting::ModelNeed { ref part :>> owner=GambitRuntimeAssurance::work.component; attribute :>> obligationId="REPAIR-REFACTOR-generational-heap-Q"; attribute :>> kind="interleaving"; attribute :>> subjectPath="models/gambit/generational_barrier.qnt"; attribute :>> subjectScope="repair-driven:generational-heap:source-composition-open"; attribute :>> premise="Barrier writer completeness, log overflow, post-forward failure custody and all-root cut; existing fragment is not whole-source refinement or a timing theorem"; }
part need5L:GambitAssuranceRouting::ModelNeed { ref part :>> owner=GambitRuntimeAssurance::work.component; attribute :>> obligationId="REPAIR-REFACTOR-generational-heap-L"; attribute :>> kind="induction"; attribute :>> subjectPath="models/gambit/lean/GenerationalBarrier.lean"; attribute :>> subjectScope="repair-driven:generational-heap:source-composition-open"; attribute :>> premise="Barrier writer completeness, log overflow, post-forward failure custody and all-root cut; existing fragment is not whole-source refinement or a timing theorem"; }
part cut5:RefactorCut { ref part :>> owner=GambitRuntimeComposition::blueprintModule4; ref part :>> seam=GambitRuntimeComposition::blueprintInterface2; ref part :>> history=need5Q; ref part :>> induction=need5L; attribute :>> key="generational-heap"; attribute :>> evidence="wait-current"; attribute :>> observation="Roughly 598 MB and 110 GC cycles in the retained c38e 120k sample; this does not identify all allocators"; attribute :>> replacement="Young allocation plus bounded noncollecting barriers, remembered mature edges, promotion budget and complete major route"; attribute :>> retirement="Retire full mature graph scan in minor only after continuation/denv/FFI mutation closure; retain sound fallback"; attribute :>> avoided="Reduce repeated mature tracing conditionally on real survival and mutation population"; attribute :>> added="Write barriers, remembered storage, promotion reserve, major cycles and rendezvous"; attribute :>> sourceGap="Barrier writer completeness, log overflow, post-forward failure custody and all-root cut"; attribute :>> actionName="commitStore"; attribute :>> lemmaName="sourceSlotsCovered"; attribute :>> projection="Concrete slot/card store projects to pending/dirty/hints and commitStore; young edges must be represented before the collector cut. Forwarding/init progress/promotion reserve project separately. sourceSlotsCovered assumes card mapping and log completeness, not a discovered census of every FFI or frame writer."; attribute :>> status="source-refinement-open; no new QNT or Lean run"; }
part need6Q:GambitAssuranceRouting::ModelNeed { ref part :>> owner=GambitRuntimeAssurance::release.component; attribute :>> obligationId="REPAIR-REFACTOR-retirement-recovery-Q"; attribute :>> kind="interleaving"; attribute :>> subjectPath="models/gambit/native_entry_close_cleanup.qnt"; attribute :>> subjectScope="repair-driven:retirement-recovery:source-composition-open"; attribute :>> premise="Actual joinable error/recovery, owner thread/epoch, old handler quiescence and no waits on own obligations; existing fragment is not whole-source refinement or a timing theorem"; }
part need6L:GambitAssuranceRouting::ModelNeed { ref part :>> owner=GambitRuntimeAssurance::release.component; attribute :>> obligationId="REPAIR-REFACTOR-retirement-recovery-L"; attribute :>> kind="induction"; attribute :>> subjectPath="models/gambit/lean/NativeEntryCloseCleanup.lean"; attribute :>> subjectScope="repair-driven:retirement-recovery:source-composition-open"; attribute :>> premise="Actual joinable error/recovery, owner thread/epoch, old handler quiescence and no waits on own obligations; existing fragment is not whole-source refinement or a timing theorem"; }
part cut6:RefactorCut { ref part :>> owner=GambitRuntimeComposition::blueprintModule7; ref part :>> seam=GambitRuntimeComposition::blueprintInterface5; ref part :>> history=need6Q; ref part :>> induction=need6L; attribute :>> key="retirement-recovery"; attribute :>> evidence="first-error"; attribute :>> observation="An original exception precedes cleanup refusal; outstanding responsibility is not automatically a leak"; attribute :>> replacement="Separate execution, GC participation, native return and release drains with stable outcome owner"; attribute :>> retirement="Retire destructive monolithic cleanup only after join, scan, callback, descendant and descriptor users close"; attribute :>> avoided="Avoid recovery-by-reinitialization, double drop and blanket forever retention"; attribute :>> added="Per-resource custody, completion records and bounded retention under unknown results"; attribute :>> sourceGap="Actual joinable error/recovery, owner thread/epoch, old handler quiescence and no waits on own obligations"; attribute :>> actionName="loseDropResult"; attribute :>> lemmaName="unknownRetainsRunRoot"; attribute :>> projection="Concrete uncertain marker drop maps to runUnknown via loseDropResult; stable protected marker/root maps to runRoot and remains until authoritative reconciliation. This fragment does not simulate OS join, callback affinity or all descendant release tasks; they need composed relations."; attribute :>> status="source-refinement-open; no new QNT or Lean run"; }
part need7Q:GambitAssuranceRouting::ModelNeed { ref part :>> owner=GambitAssuranceRelations::modelUse0; attribute :>> obligationId="REPAIR-REFACTOR-artifact-qualification-Q"; attribute :>> kind="interleaving"; attribute :>> subjectPath="models/build/incremental_build.qnt"; attribute :>> subjectScope="repair-driven:artifact-qualification:source-composition-open"; attribute :>> premise="Build result is not runtime acceptance; original child identity and complete inventories remain separate; existing fragment is not whole-source refinement or a timing theorem"; }
part need7L:GambitAssuranceRouting::ModelNeed { ref part :>> owner=GambitAssuranceRelations::modelUse0; attribute :>> obligationId="REPAIR-REFACTOR-artifact-qualification-L"; attribute :>> kind="induction"; attribute :>> subjectPath="models/build/IncrementalBuild.lean"; attribute :>> subjectScope="repair-driven:artifact-qualification:source-composition-open"; attribute :>> premise="Build result is not runtime acceptance; original child identity and complete inventories remain separate; existing fragment is not whole-source refinement or a timing theorem"; }
part cut7:RefactorCut { ref part :>> owner=GambitRuntimeComposition::blueprintModule8; ref part :>> seam=GambitRuntimeComposition::blueprintInterface7; ref part :>> history=need7Q; ref part :>> induction=need7L; attribute :>> key="artifact-qualification"; attribute :>> evidence="wait-gain"; attribute :>> observation="Selected-object updates and passing probes do not bind all generated/header/runtime consumers"; attribute :>> replacement="Content/ABI-bound dependency closure for generated C, headers, objects, archives and child executable"; attribute :>> retirement="Retire manual archive patching and mtime-only success after every consumer has exact dependency receipt"; attribute :>> avoided="Reuse unaffected products and prevent false evidence across images"; attribute :>> added="Dependency hashing, ABI propagation and transactional artifact publication"; attribute :>> sourceGap="Build result is not runtime acceptance; original child identity and complete inventories remain separate"; attribute :>> actionName="reuse"; attribute :>> lemmaName="receiptReuseMatchesClean"; attribute :>> projection="Concrete source/header/generator/ABI dependency cut projects to complete input keys and reuse; all generated/native consumers must agree under receiptReuseMatchesClean. Existing small graph does not enumerate all linked archive members; an object mtime is not a cut witness."; attribute :>> status="source-refinement-open; no new QNT or Lean run"; }
part source17:SourceRow { attribute :>> key="wait-model-receipt"; attribute :>> path="evidence/model-results/research/delivery-wait-refinement/receipt.json"; attribute :>> needle="bounded-protocol-extensions-not-source-refinement"; attribute :>> limit="Existing published protocol receipt, source hash checked; no TLC rerun, native credit or deadline proof"; }
}
