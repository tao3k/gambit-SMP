package GambitDefaultLeaseAdmission { private import ScalarValues::*;
part def SourceRow { attribute key:String; attribute path:String; attribute needle:String; attribute obligation:String; }
part source0:SourceRow { attribute :>> key="fresh"; attribute :>> path="vendor/gambit/lib/mem.c"; attribute :>> needle="result = alloc_msection->next;"; attribute :>> obligation="Serialized fresh cursor must advance monotonically in fixed manifest"; }
part source1:SourceRow { attribute :>> key="advance"; attribute :>> path="vendor/gambit/lib/mem.c"; attribute :>> needle="nb_msections_assigned++;"; attribute :>> obligation="Unique fresh token consumed at each successful list advance"; }
part source2:SourceRow { attribute :>> key="fallback"; attribute :>> path="vendor/gambit/lib/mem.c"; attribute :>> needle="result = ms;"; attribute :>> obligation="Fallback parameter is the requesting worker stack in heap wrapper"; }
part source3:SourceRow { attribute :>> key="already-shared"; attribute :>> path="vendor/gambit/lib/mem.c"; attribute :>> needle="if (stack_msection == heap_msection)"; attribute :>> obligation="Repeat fallback terminates rather than granting another visit"; }
part source4:SourceRow { attribute :>> key="shared-space"; attribute :>> path="vendor/gambit/lib/mem.c"; attribute :>> needle="space = (space - 2*___MSECTION_FUDGE) >> 2;"; attribute :>> obligation="Two sharing directions use same quarter arithmetic, different ownership"; }
part source5:SourceRow { attribute :>> key="heap-split"; attribute :>> path="vendor/gambit/lib/mem.c"; attribute :>> needle="alloc_heap_limit = alloc_heap_ptr + (3*space + ___MSECTION_FUDGE);"; attribute :>> obligation="Heap sharing grants low interval; preserve two marker words"; }
part source6:SourceRow { attribute :>> key="stack-split"; attribute :>> path="vendor/gambit/lib/mem.c"; attribute :>> needle="alloc_stack_limit = alloc_stack_ptr - (space + ___MSECTION_FUDGE);"; attribute :>> obligation="Future restored stack must fit this high interval"; }
part source7:SourceRow { attribute :>> key="markers"; attribute :>> path="vendor/gambit/lib/mem.c"; attribute :>> needle="work->context->mem.alloc_heap_limit_ -= 2;"; attribute :>> obligation="Terminal and possible empty terminal are in same leased allocation"; }
part source8:SourceRow { attribute :>> key="stack-reset"; attribute :>> path="vendor/gambit/lib/mem.c"; attribute :>> needle="stack_msection = ms;"; attribute :>> obligation="All direct and indirect stack rebinding paths need epoch authorization"; }
part source9:SourceRow { attribute :>> key="heap-reset"; attribute :>> path="vendor/gambit/lib/mem.c"; attribute :>> needle="heap_msection = ms;"; attribute :>> obligation="Heap-limit free-list reuse also rewinds allocator address"; }
part source10:SourceRow { attribute :>> key="free-list-pop"; attribute :>> path="vendor/gambit/lib/mem.c"; attribute :>> needle="msection_free_list = ___CAST(___msection*,ms->base[0]);"; attribute :>> obligation="Runtime heap/stack limits can reuse earlier sections outside GC profile"; }
part source11:SourceRow { attribute :>> key="free-list-push"; attribute :>> path="vendor/gambit/lib/mem.c"; attribute :>> needle="stack_msection->base[0] = ___CAST(___WORD,msection_free_list);"; attribute :>> obligation="Overflow undo is a real rebinding path omitted by next-stack-only census"; }
part source12:SourceRow { attribute :>> key="custom"; attribute :>> path="vendor/gambit/lib/mem.c"; attribute :>> needle="return custom_msection_alloc ();"; attribute :>> obligation="A null snapshot without exclusive hook ownership is insufficient"; }
part source13:SourceRow { attribute :>> key="container"; attribute :>> path="vendor/gambit/lib/mem.c"; attribute :>> needle="container = ___ALLOC_MEM_HEAP(extra + (words+modulus) * ___WS);"; attribute :>> obligation="Distinct live allocations plus checked alignment bounds establish separate blocks"; }
part source14:SourceRow { attribute :>> key="append"; attribute :>> path="vendor/gambit/lib/mem.c"; attribute :>> needle="s->next = 0;"; attribute :>> obligation="Successful new section appends to chronological list"; }
part source15:SourceRow { attribute :>> key="sorted"; attribute :>> path="vendor/gambit/lib/mem.c"; attribute :>> needle="ms->sections[i] = s;"; attribute :>> obligation="Address-sorted table is not the chronological allocation frontier"; }
part source16:SourceRow { attribute :>> key="table-replace"; attribute :>> path="vendor/gambit/lib/mem.c"; attribute :>> needle="free_mem_aligned (ms);"; attribute :>> obligation="Expansion may invalidate the msections metadata pointer before total demand succeeds"; }
part source17:SourceRow { attribute :>> key="partial"; attribute :>> path="vendor/gambit/lib/mem.c"; attribute :>> needle="ms->nb_sections = ++ns;"; attribute :>> obligation="Use actual count after partial allocation; do not sign requested N"; }
part source18:SourceRow { attribute :>> key="contract"; attribute :>> path="vendor/gambit/lib/mem.c"; attribute :>> needle="free_mem_aligned_heap (s);"; attribute :>> obligation="Contraction frees physical blocks; manifest pointer readers must drain"; }
part source19:SourceRow { attribute :>> key="restore-length"; attribute :>> path="vendor/gambit/lib/mem.c"; attribute :>> needle="length = (___ps->context->stack_break + ___FIRST_BREAK_FRAME_SPACE) - start;"; attribute :>> obligation="Future restore length must be a stable frozen input"; }
part source20:SourceRow { attribute :>> key="restore-loop"; attribute :>> path="vendor/gambit/lib/mem.c"; attribute :>> needle="*--p2 = *--p1;"; attribute :>> obligation="No explicit shared-interval fit check here"; }
part source21:SourceRow { attribute :>> key="resize-call"; attribute :>> path="vendor/gambit/lib/mem.c"; attribute :>> needle="adjust_msections (&m->the_msections_, required);"; attribute :>> obligation="Growth mutates list/table, cannot overlap admitted allocator epoch"; }
part source22:SourceRow { attribute :>> key="resize-rollback"; attribute :>> path="vendor/gambit/lib/mem.c"; attribute :>> needle="adjust_msections (&m->the_msections_, r->base_capacity);"; attribute :>> obligation="Rollback also mutates physical ownership; unknown joins prohibit release"; }
part source23:SourceRow { attribute :>> key="resize-request"; attribute :>> path="vendor/gambit/lib/setup.c"; attribute :>> needle="r->phase = ___RESIZE_REQUESTED;"; attribute :>> obligation="Requested grow can collect under old cohort before reserve"; }
part source24:SourceRow { attribute :>> key="gc-before-reserve"; attribute :>> path="vendor/gambit/lib/setup.c"; attribute :>> needle="r->result = ___reserve_vm_resize (___ps);"; attribute :>> obligation="Real outer path reserves after collective GC result consumption"; }
part source25:SourceRow { attribute :>> key="gc-resize-admit"; attribute :>> path="vendor/gambit/lib/mem.c"; attribute :>> needle="___vms->resize.phase != ___RESIZE_REQUESTED"; attribute :>> obligation="GC allows requested and isolated retained cases; they need distinct qualification"; }
part source26:SourceRow { attribute :>> key="roots-frozen"; attribute :>> path="vendor/gambit/lib/mem.c"; attribute :>> needle="participant->phase = ___GC_ROOTS_FROZEN;"; attribute :>> obligation="New plan collective belongs after frozen acknowledgement before setup effects"; }
part source27:SourceRow { attribute :>> key="setup"; attribute :>> path="vendor/gambit/lib/mem.c"; attribute :>> needle="garbage_collect_setup_phase (work);"; attribute :>> obligation="Every member must consume same admitted generation before setup"; }
part source28:SourceRow { attribute :>> key="foreign"; attribute :>> path="vendor/gambit/lib/mem.c"; attribute :>> needle="___release_foreign"; attribute :>> obligation="Cleanup can invoke arbitrary native destructor; full-epoch reentry closure needed"; }
part source29:SourceRow { attribute :>> key="adjust-hook"; attribute :>> path="vendor/gambit/lib/mem.c"; attribute :>> needle="___GSTATE->setup_params.adjust_heap_hook (live)"; attribute :>> obligation="Resize-time hook may execute native code after tracing; lifetime scope is larger"; }
part source30:SourceRow { attribute :>> key="frame-address"; attribute :>> path="vendor/gambit/include/gambit.h.in"; attribute :>> needle="#define ___FP_SET_STK(fp,fpo,val)fp[-(fpo)]=(val);"; attribute :>> obligation="Break metadata writes upward from restored fp; prove they remain in restore interval"; }
part source31:SourceRow { attribute :>> key="signed-size"; attribute :>> path="vendor/gambit/include/gambit.h.in"; attribute :>> needle="#define ___SIZE_TS ___SSIZE_T"; attribute :>> obligation="Current signed temporary type requires native range proof"; }
part source32:SourceRow { attribute :>> key="alloc-lock"; attribute :>> path="vendor/gambit/lib/mem.c"; attribute :>> needle="#define ALLOC_MEM_LOCK()"; attribute :>> obligation="List selection lock is not complete admission exclusion for all writers"; }
part source33:SourceRow { attribute :>> key="heap-backend"; attribute :>> path="vendor/gambit/lib/os_base.c"; attribute :>> needle="return ___alloc_mem_code (bytes);"; attribute :>> obligation="Low-level-exec branch uses code allocator rather than ordinary malloc; bind effective profile"; }
part source34:SourceRow { attribute :>> key="malloc-backend"; attribute :>> path="vendor/gambit/lib/os_base.c"; attribute :>> needle="ptr = malloc (bytes);"; attribute :>> obligation="Separate live-block guarantee belongs to qualified native allocation contract and range checks"; }
part def CallRow { attribute key:String; attribute path:String; attribute callerName:String; attribute callee:String; attribute siteCount:String; attribute scope:String; }
part call0:CallRow { attribute :>> key="0"; attribute :>> path="vendor/gambit/lib/mem.c"; attribute :>> callerName="___cleanup_mem_vmstate"; attribute :>> callee="free_msections"; attribute :>> siteCount="1"; attribute :>> scope="Literal sites only; no effective-preprocessor or external alias closure"; }
part call1:CallRow { attribute :>> key="1"; attribute :>> path="vendor/gambit/lib/mem.c"; attribute :>> callerName="___garbage_collect_pstate"; attribute :>> callee="resize_heap"; attribute :>> siteCount="1"; attribute :>> scope="Literal sites only; no effective-preprocessor or external alias closure"; }
part call2:CallRow { attribute :>> key="2"; attribute :>> path="vendor/gambit/lib/mem.c"; attribute :>> callerName="___heap_limit"; attribute :>> callee="next_heap_msection_without_locking"; attribute :>> siteCount="1"; attribute :>> scope="Literal sites only; no effective-preprocessor or external alias closure"; }
part call3:CallRow { attribute :>> key="3"; attribute :>> path="vendor/gambit/lib/mem.c"; attribute :>> callerName="___heap_limit"; attribute :>> callee="set_heap_msection"; attribute :>> siteCount="1"; attribute :>> scope="Literal sites only; no effective-preprocessor or external alias closure"; }
part call4:CallRow { attribute :>> key="4"; attribute :>> path="vendor/gambit/lib/mem.c"; attribute :>> callerName="___reserve_vm_resize"; attribute :>> callee="adjust_msections"; attribute :>> siteCount="2"; attribute :>> scope="Literal sites only; no effective-preprocessor or external alias closure"; }
part call5:CallRow { attribute :>> key="5"; attribute :>> path="vendor/gambit/lib/mem.c"; attribute :>> callerName="___rollback_vm_resize"; attribute :>> callee="adjust_msections"; attribute :>> siteCount="1"; attribute :>> scope="Literal sites only; no effective-preprocessor or external alias closure"; }
part call6:CallRow { attribute :>> key="6"; attribute :>> path="vendor/gambit/lib/mem.c"; attribute :>> callerName="___setup_mem_pstate"; attribute :>> callee="next_stack_msection"; attribute :>> siteCount="1"; attribute :>> scope="Literal sites only; no effective-preprocessor or external alias closure"; }
part call7:CallRow { attribute :>> key="7"; attribute :>> path="vendor/gambit/lib/mem.c"; attribute :>> callerName="___setup_mem_pstate"; attribute :>> callee="set_heap_msection"; attribute :>> siteCount="1"; attribute :>> scope="Literal sites only; no effective-preprocessor or external alias closure"; }
part call8:CallRow { attribute :>> key="8"; attribute :>> path="vendor/gambit/lib/mem.c"; attribute :>> callerName="___setup_mem_pstate"; attribute :>> callee="set_stack_msection"; attribute :>> siteCount="1"; attribute :>> scope="Literal sites only; no effective-preprocessor or external alias closure"; }
part call9:CallRow { attribute :>> key="9"; attribute :>> path="vendor/gambit/lib/mem.c"; attribute :>> callerName="___setup_mem_vmstate"; attribute :>> callee="adjust_msections"; attribute :>> siteCount="1"; attribute :>> scope="Literal sites only; no effective-preprocessor or external alias closure"; }
part call10:CallRow { attribute :>> key="10"; attribute :>> path="vendor/gambit/lib/mem.c"; attribute :>> callerName="___stack_limit"; attribute :>> callee="next_stack_msection_without_locking"; attribute :>> siteCount="1"; attribute :>> scope="Literal sites only; no effective-preprocessor or external alias closure"; }
part call11:CallRow { attribute :>> key="11"; attribute :>> path="vendor/gambit/lib/mem.c"; attribute :>> callerName="___stack_limit"; attribute :>> callee="set_stack_msection"; attribute :>> siteCount="1"; attribute :>> scope="Literal sites only; no effective-preprocessor or external alias closure"; }
part call12:CallRow { attribute :>> key="12"; attribute :>> path="vendor/gambit/lib/mem.c"; attribute :>> callerName="___stack_overflow_undo_if_possible"; attribute :>> callee="set_stack_msection"; attribute :>> siteCount="1"; attribute :>> scope="Literal sites only; no effective-preprocessor or external alias closure"; }
part call13:CallRow { attribute :>> key="13"; attribute :>> path="vendor/gambit/lib/mem.c"; attribute :>> callerName="___stack_overflow_undo_if_possible"; attribute :>> callee="stack_msection_resume_using"; attribute :>> siteCount="1"; attribute :>> scope="Literal sites only; no effective-preprocessor or external alias closure"; }
part call14:CallRow { attribute :>> key="14"; attribute :>> path="vendor/gambit/lib/mem.c"; attribute :>> callerName="free_still_objs"; attribute :>> callee="___release_foreign"; attribute :>> siteCount="1"; attribute :>> scope="Literal sites only; no effective-preprocessor or external alias closure"; }
part call15:CallRow { attribute :>> key="15"; attribute :>> path="vendor/gambit/lib/mem.c"; attribute :>> callerName="free_unmarked_still_objs"; attribute :>> callee="___release_foreign"; attribute :>> siteCount="1"; attribute :>> scope="Literal sites only; no effective-preprocessor or external alias closure"; }
part call16:CallRow { attribute :>> key="16"; attribute :>> path="vendor/gambit/lib/mem.c"; attribute :>> callerName="next_heap_msection"; attribute :>> callee="next_msection_without_locking"; attribute :>> siteCount="1"; attribute :>> scope="Literal sites only; no effective-preprocessor or external alias closure"; }
part call17:CallRow { attribute :>> key="17"; attribute :>> path="vendor/gambit/lib/mem.c"; attribute :>> callerName="next_heap_msection_without_locking"; attribute :>> callee="next_msection_without_locking"; attribute :>> siteCount="1"; attribute :>> scope="Literal sites only; no effective-preprocessor or external alias closure"; }
part call18:CallRow { attribute :>> key="18"; attribute :>> path="vendor/gambit/lib/mem.c"; attribute :>> callerName="next_stack_msection"; attribute :>> callee="next_msection_without_locking"; attribute :>> siteCount="1"; attribute :>> scope="Literal sites only; no effective-preprocessor or external alias closure"; }
part call19:CallRow { attribute :>> key="19"; attribute :>> path="vendor/gambit/lib/mem.c"; attribute :>> callerName="next_stack_msection_without_locking"; attribute :>> callee="next_msection_without_locking"; attribute :>> siteCount="1"; attribute :>> scope="Literal sites only; no effective-preprocessor or external alias closure"; }
part call20:CallRow { attribute :>> key="20"; attribute :>> path="vendor/gambit/lib/mem.c"; attribute :>> callerName="resize_heap"; attribute :>> callee="adjust_msections"; attribute :>> siteCount="1"; attribute :>> scope="Literal sites only; no effective-preprocessor or external alias closure"; }
part call21:CallRow { attribute :>> key="21"; attribute :>> path="vendor/gambit/lib/mem.c"; attribute :>> callerName="set_heap_msection_possibly_sharing_with_stack"; attribute :>> callee="set_heap_msection"; attribute :>> siteCount="1"; attribute :>> scope="Literal sites only; no effective-preprocessor or external alias closure"; }
part call22:CallRow { attribute :>> key="22"; attribute :>> path="vendor/gambit/lib/mem.c"; attribute :>> callerName="set_stack_msection_possibly_sharing_with_heap"; attribute :>> callee="set_stack_msection"; attribute :>> siteCount="1"; attribute :>> scope="Literal sites only; no effective-preprocessor or external alias closure"; }
part call23:CallRow { attribute :>> key="23"; attribute :>> path="vendor/gambit/lib/mem.c"; attribute :>> callerName="setup_stack_heap_vmstate"; attribute :>> callee="set_heap_msection"; attribute :>> siteCount="1"; attribute :>> scope="Literal sites only; no effective-preprocessor or external alias closure"; }
part call24:CallRow { attribute :>> key="24"; attribute :>> path="vendor/gambit/lib/mem.c"; attribute :>> callerName="setup_stack_heap_vmstate"; attribute :>> callee="set_stack_msection"; attribute :>> siteCount="1"; attribute :>> scope="Literal sites only; no effective-preprocessor or external alias closure"; }
part call25:CallRow { attribute :>> key="25"; attribute :>> path="vendor/gambit/lib/setup.c"; attribute :>> callerName="___vm_resize_pstate"; attribute :>> callee="___reserve_vm_resize"; attribute :>> siteCount="1"; attribute :>> scope="Literal sites only; no effective-preprocessor or external alias closure"; }
part call26:CallRow { attribute :>> key="26"; attribute :>> path="vendor/gambit/lib/setup.c"; attribute :>> callerName="___vm_resize_pstate"; attribute :>> callee="___rollback_vm_resize"; attribute :>> siteCount="1"; attribute :>> scope="Literal sites only; no effective-preprocessor or external alias closure"; }
part call27:CallRow { attribute :>> key="27"; attribute :>> path="vendor/gambit/lib/setup.c"; attribute :>> callerName="setup_os_and_mem_pstate"; attribute :>> callee="___setup_mem_pstate"; attribute :>> siteCount="1"; attribute :>> scope="Literal sites only; no effective-preprocessor or external alias closure"; }
part def ClaimRow { attribute key:String; attribute mechanism:String; attribute condition:String; attribute result:String; attribute gap:String; }
part claim0:ClaimRow { attribute :>> key="L-bound"; attribute :>> mechanism="Initial P heaps plus fresh F plus private stack fallbacks S"; attribute :>> condition="F<=N-2P and S<=P; distinct manifest tokens; no stack rebinding"; attribute :>> result="L=P+F+S<=N"; attribute :>> gap="Symbolic arithmetic and two-worker identity slice proved; source-wide injection open"; }
part claim1:ClaimRow { attribute :>> key="fresh-uniqueness"; attribute :>> mechanism="Chronological next cursor under ALLOC_MEM_LOCK"; attribute :>> condition="No hook or table mutation and exclusive init/setup roster"; attribute :>> result="Never hand same fresh section to two workers"; attribute :>> gap="C allocator/list construction provenance and native lock refinement open"; }
part claim2:ClaimRow { attribute :>> key="shared-layout"; attribute :>> mechanism="H=4q+2F+r; heap end 3q+F; stack limit H-(q+F)"; attribute :>> condition="r in 0..3 and stable base/top; reserve two terminal words"; attribute :>> result="Gap is r; heap markers stay below declared stack limit"; attribute :>> gap="Restore length must independently fit; quarter split alone is insufficient"; }
part claim3:ClaimRow { attribute :>> key="restore-fit"; attribute :>> mechanism="Future move_continuation writes [H-R,H)"; attribute :>> condition="R>=3 and R<=q+F; metadata at restored fp+2"; attribute :>> result="Disjoint actual restore writes under stated bounds"; attribute :>> gap="No legal-input proof of R bound or explicit check at restore endpoint"; }
part claim4:ClaimRow { attribute :>> key="exclusions"; attribute :>> mechanism="Native epoch lease on setup, limits, undo, resize, hooks and callback ingress"; attribute :>> condition="Guard before first pointer/roster write; defer conflicting work"; attribute :>> result="Future modern-C design can enforce finite visits and non-reuse"; attribute :>> gap="Existing GC phase check does not guard all these entry points"; }
part def PolicyRow { attribute key:String; attribute sourcePath:String; attribute policyAction:String; attribute why:String; attribute migration:String; }
part policy0:PolicyRow { attribute :>> key="stack-limit"; attribute :>> sourcePath="vendor/gambit/lib/mem.c"; attribute :>> policyAction="Defer or refuse while collector owns allocator intervals"; attribute :>> why="Free-list path can rebind stack without next_stack_msection"; attribute :>> migration="Check before pointer recovery/free-list mutation"; }
part policy1:PolicyRow { attribute :>> key="stack-undo"; attribute :>> sourcePath="vendor/gambit/lib/mem.c"; attribute :>> policyAction="Require mutator execution lease, not collector lease"; attribute :>> why="Continuation return path restores prior stack and updates free list"; attribute :>> migration="Guard emitted/runtime entrance before any list or context write"; }
part policy2:PolicyRow { attribute :>> key="heap-limit"; attribute :>> sourcePath="vendor/gambit/lib/mem.c"; attribute :>> policyAction="Defer or route to next epoch"; attribute :>> why="Can reuse free list and reset heap ptr before a GC attempt"; attribute :>> migration="Do not rely solely on nested GC phase check"; }
part policy3:PolicyRow { attribute :>> key="pstate-setup"; attribute :>> sourcePath="vendor/gambit/lib/setup.c"; attribute :>> policyAction="Exclude during allocator epoch; support after collective close"; attribute :>> why="Processor setup binds slots and stack/heap sections"; attribute :>> migration="Retain real grow support; serialize existing stage boundary"; }
part policy4:PolicyRow { attribute :>> key="resize-requested"; attribute :>> sourcePath="vendor/gambit/lib/setup.c"; attribute :>> policyAction="Conditionally support inner GC under old frozen roster"; attribute :>> why="Outer resize waits for GC result before reserve"; attribute :>> migration="Bind request generation and finish old storage users before reserve"; }
part policy5:PolicyRow { attribute :>> key="resize-retained"; attribute :>> sourcePath="vendor/gambit/lib/mem.c"; attribute :>> policyAction="No tight receipt until quarantined ownership is isolated in manifest"; attribute :>> why="Current GC guard admits abort_isolated but not complete lease closure"; attribute :>> migration="Keep quarantine tokens; do not credit them as generally free sections"; }
part policy6:PolicyRow { attribute :>> key="cleanup-callback"; attribute :>> sourcePath="vendor/gambit/lib/mem.c"; attribute :>> policyAction="Reentry needs new epoch/capability or explicit refusal"; attribute :>> why="Foreign destructors and adjust hook remain real native entry producers"; attribute :>> migration="No blanket no-callback assumption; separate trace and reclaim lifetimes"; }
part def ReceiptRow { attribute key:String; attribute issuer:String; attribute prerequisite:String; attribute failure:String; attribute gap:String; }
part receipt0:ReceiptRow { attribute :>> key="manifest"; attribute :>> issuer="Storage owner"; attribute :>> prerequisite="Actual N; pinned live containers; stable chronological list; per-worker stack token and R"; attribute :>> failure="Partial growth uses actual published count; unknown pin retains metadata"; attribute :>> gap="Current code has no consolidated immutable manifest issuer"; }
part receipt1:ReceiptRow { attribute :>> key="vote"; attribute :>> issuer="Every frozen participant"; attribute :>> prerequisite="Matching generation/digest; supported split including restore fit; known local guards"; attribute :>> failure="Any known reject chooses one collective failure; unknown member blocks release"; attribute :>> gap="No native vote transport for this plan"; }
part receipt2:ReceiptRow { attribute :>> key="decision"; attribute :>> issuer="Coordinator under closed roster"; attribute :>> prerequisite="All scoped votes consumed; immutable accept or reject published"; attribute :>> failure="Decision never changes after acknowledgement; no coordinator-only return"; attribute :>> gap="C11 publication and exception completion guard open"; }
part receipt3:ReceiptRow { attribute :>> key="delivery"; attribute :>> issuer="Every participant plus lifecycle coordinator"; attribute :>> prerequisite="Consume same decision and acknowledge last reader; all acknowledgements before setup"; attribute :>> failure="Missing ack retains old context/pool; no timeout-forged completion"; attribute :>> gap="Two-member model only; arbitrary roster refinement open"; }
part receipt4:ReceiptRow { attribute :>> key="post-accept"; attribute :>> issuer="Stable setup completion coordinator"; attribute :>> prerequisite="Accepted slot writes and corresponding published roots remain owned"; attribute :>> failure="Partial flip cannot be returned as old parity rejection; retain unfinished setup"; attribute :>> gap="Native non-abandonable setup recovery not designed as runtime implementation"; }
part receipt5:ReceiptRow { attribute :>> key="reject-free"; attribute :>> issuer="Pool lifecycle coordinator"; attribute :>> prerequisite="Both result delivery and reader retirement established; no flip occurred"; attribute :>> failure="Incomplete failure delivery retains pool and old frozen roots"; attribute :>> gap="Once-only native free and generation reclamation still open"; }
part def MemoryRow { attribute key:String; attribute obligation:String; attribute reuse:String; attribute cost:String; }
part memory0:MemoryRow { attribute :>> key="fresh"; attribute :>> obligation="Same native allocation lock serializes selection and cursor write"; attribute :>> reuse="Reuse existing gate for fresh list only"; attribute :>> cost="No new atomic per copied word"; }
part memory1:MemoryRow { attribute :>> key="snapshot"; attribute :>> obligation="Freeze membership and guarded pointer writers before ordinary manifest reads"; attribute :>> reuse="Existing phase barriers are candidates, not proven acquire/release receipts"; attribute :>> cost="O(N+P) manifest/snapshot work plus stable storage pins"; }
part memory2:MemoryRow { attribute :>> key="decision"; attribute :>> obligation="Initialize immutable plan before release; votes/acks acquire exact generation"; attribute :>> reuse="Coordinator observes every member release before setup release"; attribute :>> cost="Per-member O(1) receipts; collective latency not measured"; }
part memory3:MemoryRow { attribute :>> key="reclamation"; attribute :>> obligation="Last dereference before acknowledgement; no new reader after admission close"; attribute :>> reuse="Separate header-table and block lifetimes"; attribute :>> cost="Late observers can retain memory indefinitely"; }
part memory4:MemoryRow { attribute :>> key="arithmetic"; attribute :>> obligation="Checked signed counts, alignment additions and native size multiplications"; attribute :>> reuse="Mathematical Int cannot justify ___SIZE_TS or pointer provenance"; attribute :>> cost="Explicit range/ABI qualification remains necessary"; }
part def GainRow { attribute key:String; attribute avoided:String; attribute added:String; attribute condition:String; }
part gain0:GainRow { attribute :>> key="finite-plan"; attribute :>> avoided="Use 258N+D candidate rather than dense per-word record ceiling"; attribute :>> added="Immutable manifest and exclusive epoch admission"; attribute :>> condition="Only when L<=N and physical restore bounds both qualify"; }
part gain1:GainRow { attribute :>> key="heap-scan"; attribute :>> avoided="Keep ordinary C object/header reads"; attribute :>> added="Independent records and existing FIFO synchronization"; attribute :>> condition="Do not count the old allocation lock as a new saving"; }
part gain2:GainRow { attribute :>> key="shared-space"; attribute :>> avoided="Reuse otherwise available stack section without live overlap"; attribute :>> added="Per-context R check and whole-footprint split proof"; attribute :>> condition="Reject or reschedule unsupported fallback; no native reachability claim"; }
part gain3:GainRow { attribute :>> key="parallelism"; attribute :>> avoided="Defer conflicting mutation instead of globally disabling SMP/resize"; attribute :>> added="One admission lease and explicit queued lifecycle operations"; attribute :>> condition="No unfair gate or callback can be assumed to terminate"; }
part gain4:GainRow { attribute :>> key="cost"; attribute :>> avoided="Avoid pool wait inside irreversible forwarding"; attribute :>> added="O(N+P) plan plus votes/acks, stable pins, failure coordination"; attribute :>> condition="Positive net benefit not yet established or measured"; }
part def ContractRow { attribute fromNode:String; attribute toNode:String; attribute custody:String; }
part contract0:ContractRow { attribute :>> fromNode="root-freeze"; attribute :>> toNode="writer-exclusion"; attribute :>> custody="Close mutation entry points before first manifest read"; }
part contract1:ContractRow { attribute :>> fromNode="writer-exclusion"; attribute :>> toNode="manifest"; attribute :>> custody="Pin actual section identities list and future restore lengths"; }
part contract2:ContractRow { attribute :>> fromNode="manifest"; attribute :>> toNode="lease-budget"; attribute :>> custody="Unique fresh and one stack token per worker"; }
part contract3:ContractRow { attribute :>> fromNode="manifest"; attribute :>> toNode="physical-split"; attribute :>> custody="Include heap markers restore interval and break metadata"; }
part contract4:ContractRow { attribute :>> fromNode="lease-budget"; attribute :>> toNode="participant-votes"; attribute :>> custody="Publish same generation and digest"; }
part contract5:ContractRow { attribute :>> fromNode="physical-split"; attribute :>> toNode="participant-votes"; attribute :>> custody="Each owner validates its interval and restoration footprint"; }
part contract6:ContractRow { attribute :>> fromNode="participant-votes"; attribute :>> toNode="decision"; attribute :>> custody="Any reject prevents setup; unknown vote retains cohort"; }
part contract7:ContractRow { attribute :>> fromNode="decision"; attribute :>> toNode="last-reader-acks"; attribute :>> custody="Every member consumes same immutable outcome"; }
part contract8:ContractRow { attribute :>> fromNode="last-reader-acks"; attribute :>> toNode="collective-release"; attribute :>> custody="All readers retired before setup or failure return"; }
part contract9:ContractRow { attribute :>> fromNode="collective-release"; attribute :>> toNode="accepted-setup"; attribute :>> custody="Accept only; no partial rollback to old parity"; }
part contract10:ContractRow { attribute :>> fromNode="collective-release"; attribute :>> toNode="failure-delivery"; attribute :>> custody="Reject only; same outcome consumed by every member"; }
part contract11:ContractRow { attribute :>> fromNode="failure-delivery"; attribute :>> toNode="pool-free"; attribute :>> custody="Complete delivery and no native borrowers; single-use receipt"; }
part contract12:ContractRow { attribute :>> fromNode="accepted-setup"; attribute :>> toNode="allocator-epoch"; attribute :>> custody="Guard every fresh fallback and context rebinding entry"; }
part contract13:ContractRow { attribute :>> fromNode="allocator-epoch"; attribute :>> toNode="storage-close"; attribute :>> custody="Drain before resize cleanup or metadata reclamation"; }
part def ObligationRow { attribute key:String; attribute status:String; attribute scope:String; attribute gap:String; }
part obligation0:ObligationRow { attribute :>> key="count"; attribute :>> status="conditional-proved"; attribute :>> scope="Symbolic L bound and two-worker exact section identities"; attribute :>> gap="Arbitrary-worker source-to-token injection remains open"; }
part obligation1:ObligationRow { attribute :>> key="geometry"; attribute :>> status="conditional-proved"; attribute :>> scope="Quarter gap markers and restore/metadata footprints"; attribute :>> gap="R precondition not proved for all legal Scheme states"; }
part obligation2:ObligationRow { attribute :>> key="collective"; attribute :>> status="model-proved"; attribute :>> scope="Accept/reject publication reader retirement and failure delivery"; attribute :>> gap="Native barriers C11 and arbitrary roster proof open"; }
part obligation3:ObligationRow { attribute :>> key="composition"; attribute :>> status="model-proved"; attribute :>> scope="Guarded collective/lease product plus exact prior charge guard bridge"; attribute :>> gap="Not full global multi-context GC/native trace refinement"; }
part obligation4:ObligationRow { attribute :>> key="source"; attribute :>> status="checked-snapshot"; attribute :>> scope="Entry and mutation caller inventory from mem.c/setup.c"; attribute :>> gap="Header/FFI/generated alias closure and effective profile unresolved"; }
part obligation5:ObligationRow { attribute :>> key="net"; attribute :>> status="open"; attribute :>> scope="Operation-count and memory inequalities"; attribute :>> gap="No native timing or real success acceptance"; }
part def BindingRow { attribute actionName:String; attribute lemma:String; attribute scope:String; }
part binding0:BindingRow { attribute :>> actionName="default_section_leases.fresh4worker0"; attribute :>> lemma="SectionLeases.fresh4worker0Preserves"; attribute :>> scope="Actual typed-IR action preservation; no source qualification"; }
part binding1:BindingRow { attribute :>> actionName="default_section_leases.fresh4worker1"; attribute :>> lemma="SectionLeases.fresh4worker1Preserves"; attribute :>> scope="Actual typed-IR action preservation; no source qualification"; }
part binding2:BindingRow { attribute :>> actionName="default_section_leases.fresh5worker0"; attribute :>> lemma="SectionLeases.fresh5worker0Preserves"; attribute :>> scope="Actual typed-IR action preservation; no source qualification"; }
part binding3:BindingRow { attribute :>> actionName="default_section_leases.fresh5worker1"; attribute :>> lemma="SectionLeases.fresh5worker1Preserves"; attribute :>> scope="Actual typed-IR action preservation; no source qualification"; }
part binding4:BindingRow { attribute :>> actionName="default_section_leases.shareWorker0"; attribute :>> lemma="SectionLeases.shareWorker0Preserves"; attribute :>> scope="Actual typed-IR action preservation; no source qualification"; }
part binding5:BindingRow { attribute :>> actionName="default_section_leases.shareWorker1"; attribute :>> lemma="SectionLeases.shareWorker1Preserves"; attribute :>> scope="Actual typed-IR action preservation; no source qualification"; }
part binding6:BindingRow { attribute :>> actionName="default_section_leases.denyStackRebind"; attribute :>> lemma="SectionLeases.denyStackRebindPreserves"; attribute :>> scope="Actual typed-IR action preservation; no source qualification"; }
part binding7:BindingRow { attribute :>> actionName="default_section_leases.denyGrow"; attribute :>> lemma="SectionLeases.denyGrowPreserves"; attribute :>> scope="Actual typed-IR action preservation; no source qualification"; }
part binding8:BindingRow { attribute :>> actionName="default_section_leases.denyReentry"; attribute :>> lemma="SectionLeases.denyReentryPreserves"; attribute :>> scope="Actual typed-IR action preservation; no source qualification"; }
part binding9:BindingRow { attribute :>> actionName="default_section_leases.unknownWriter"; attribute :>> lemma="SectionLeases.unknownWriterPreserves"; attribute :>> scope="Actual typed-IR action preservation; no source qualification"; }
part binding10:BindingRow { attribute :>> actionName="default_section_leases.exhaustedShared0"; attribute :>> lemma="SectionLeases.exhaustedShared0Preserves"; attribute :>> scope="Actual typed-IR action preservation; no source qualification"; }
part binding11:BindingRow { attribute :>> actionName="default_section_leases.closeAllocators"; attribute :>> lemma="SectionLeases.closeAllocatorsPreserves"; attribute :>> scope="Actual typed-IR action preservation; no source qualification"; }
part binding12:BindingRow { attribute :>> actionName="capacity_collective.publishReady"; attribute :>> lemma="CapacityCollective.publishReadyPreserves"; attribute :>> scope="Actual typed-IR action preservation; no source qualification"; }
part binding13:BindingRow { attribute :>> actionName="capacity_collective.publishFailure"; attribute :>> lemma="CapacityCollective.publishFailurePreserves"; attribute :>> scope="Actual typed-IR action preservation; no source qualification"; }
part binding14:BindingRow { attribute :>> actionName="capacity_collective.accept0"; attribute :>> lemma="CapacityCollective.accept0Preserves"; attribute :>> scope="Actual typed-IR action preservation; no source qualification"; }
part binding15:BindingRow { attribute :>> actionName="capacity_collective.accept1"; attribute :>> lemma="CapacityCollective.accept1Preserves"; attribute :>> scope="Actual typed-IR action preservation; no source qualification"; }
part binding16:BindingRow { attribute :>> actionName="capacity_collective.reject0"; attribute :>> lemma="CapacityCollective.reject0Preserves"; attribute :>> scope="Actual typed-IR action preservation; no source qualification"; }
part binding17:BindingRow { attribute :>> actionName="capacity_collective.reject1"; attribute :>> lemma="CapacityCollective.reject1Preserves"; attribute :>> scope="Actual typed-IR action preservation; no source qualification"; }
part binding18:BindingRow { attribute :>> actionName="capacity_collective.decideAccept"; attribute :>> lemma="CapacityCollective.decideAcceptPreserves"; attribute :>> scope="Actual typed-IR action preservation; no source qualification"; }
part binding19:BindingRow { attribute :>> actionName="capacity_collective.decideReject"; attribute :>> lemma="CapacityCollective.decideRejectPreserves"; attribute :>> scope="Actual typed-IR action preservation; no source qualification"; }
part binding20:BindingRow { attribute :>> actionName="capacity_collective.acknowledge0"; attribute :>> lemma="CapacityCollective.acknowledge0Preserves"; attribute :>> scope="Actual typed-IR action preservation; no source qualification"; }
part binding21:BindingRow { attribute :>> actionName="capacity_collective.acknowledge1"; attribute :>> lemma="CapacityCollective.acknowledge1Preserves"; attribute :>> scope="Actual typed-IR action preservation; no source qualification"; }
part binding22:BindingRow { attribute :>> actionName="capacity_collective.release"; attribute :>> lemma="CapacityCollective.releasePreserves"; attribute :>> scope="Actual typed-IR action preservation; no source qualification"; }
part binding23:BindingRow { attribute :>> actionName="capacity_collective.flip0"; attribute :>> lemma="CapacityCollective.flip0Preserves"; attribute :>> scope="Actual typed-IR action preservation; no source qualification"; }
part binding24:BindingRow { attribute :>> actionName="capacity_collective.flip1"; attribute :>> lemma="CapacityCollective.flip1Preserves"; attribute :>> scope="Actual typed-IR action preservation; no source qualification"; }
part binding25:BindingRow { attribute :>> actionName="capacity_collective.deliver0"; attribute :>> lemma="CapacityCollective.deliver0Preserves"; attribute :>> scope="Actual typed-IR action preservation; no source qualification"; }
part binding26:BindingRow { attribute :>> actionName="capacity_collective.deliver1"; attribute :>> lemma="CapacityCollective.deliver1Preserves"; attribute :>> scope="Actual typed-IR action preservation; no source qualification"; }
part binding27:BindingRow { attribute :>> actionName="capacity_collective.retainUnknown"; attribute :>> lemma="CapacityCollective.retainUnknownPreserves"; attribute :>> scope="Actual typed-IR action preservation; no source qualification"; }
part binding28:BindingRow { attribute :>> actionName="capacity_collective.retainSetupUnknown"; attribute :>> lemma="CapacityCollective.retainSetupUnknownPreserves"; attribute :>> scope="Actual typed-IR action preservation; no source qualification"; }
part binding29:BindingRow { attribute :>> actionName="capacity_collective.freeRejected"; attribute :>> lemma="CapacityCollective.freeRejectedPreserves"; attribute :>> scope="Actual typed-IR action preservation; no source qualification"; }
part def ProofRow { attribute key:String; attribute lemma:String; attribute scope:String; }
part proof0:ProofRow { attribute :>> key="general-count"; attribute :>> lemma="DefaultLeaseComposition.leaseCountBound"; attribute :>> scope="General symbolic bound separate from finite slice"; }
part proof1:ProofRow { attribute :>> key="identity"; attribute :>> lemma="SectionLeases.currentHeapsDistinct"; attribute :>> scope="Finite slice current heaps and retained fresh owners"; }
part proof2:ProofRow { attribute :>> key="gap"; attribute :>> lemma="DefaultLeaseComposition.sharedPartition"; attribute :>> scope="Abstract half-open interval offsets"; }
part proof3:ProofRow { attribute :>> key="markers"; attribute :>> lemma="DefaultLeaseComposition.markersStayBelowStack"; attribute :>> scope="Both reserved terminal words included"; }
part proof4:ProofRow { attribute :>> key="restore"; attribute :>> lemma="DefaultLeaseComposition.restoredStackSeparate"; attribute :>> scope="Requires independent R bound"; }
part proof5:ProofRow { attribute :>> key="metadata"; attribute :>> lemma="DefaultLeaseComposition.restoreMetadataInBounds"; attribute :>> scope="First-break field stays in restored interval"; }
part proof6:ProofRow { attribute :>> key="restore-control"; attribute :>> lemma="DefaultLeaseComposition.uncheckedRestoreCanOverlap"; attribute :>> scope="Numerical counterexample; legal Scheme reachability open"; }
part proof7:ProofRow { attribute :>> key="prior-ceiling"; attribute :>> lemma="DefaultLeaseComposition.priorChargeCeiling"; attribute :>> scope="Exact preceding CapacityCharge AST"; }
part proof8:ProofRow { attribute :>> key="prior-advance"; attribute :>> lemma="DefaultLeaseComposition.priorAdvanceGuard"; attribute :>> scope="New unique lease event authorizes old visit guard"; }
part proof9:ProofRow { attribute :>> key="successful-prefix"; attribute :>> lemma="DefaultLeaseComposition.admittedCollectiveReachable"; attribute :>> scope="Actual collective typed action prefix"; }
part proof10:ProofRow { attribute :>> key="product"; attribute :>> lemma="DefaultLeaseComposition.reachableGood"; attribute :>> scope="Guarded new models product"; }
part proof11:ProofRow { attribute :>> key="independent-control"; attribute :>> lemma="DefaultLeaseComposition.falseIndependentAdmission"; attribute :>> scope="Two safe components alone do not authorize collection"; }
part proof12:ProofRow { attribute :>> key="all-acks"; attribute :>> lemma="CapacityCollective.flipRequiresAllAcknowledged"; attribute :>> scope="No setup slot write before both last-reader acks"; }
part proof13:ProofRow { attribute :>> key="reject-no-flip"; attribute :>> lemma="CapacityCollective.rejectCannotFlip"; attribute :>> scope="No rejected generation toggles parity"; }
part proof14:ProofRow { attribute :>> key="free-results"; attribute :>> lemma="CapacityCollective.freeRequiresBothResults"; attribute :>> scope="No free while failure delivery incomplete"; }
part proof15:ProofRow { attribute :>> key="once"; attribute :>> lemma="CapacityCollective.noRepeatedFree"; attribute :>> scope="Abstract once-only free action guard"; }
part def BridgeRow { attribute key:String; attribute targetStep:String; attribute lemma:String; attribute scope:String; }
part bridge0:BridgeRow { attribute :>> key="prior-charge-advance"; attribute :>> targetStep="chunk_capacity_charge.advanceVisit"; attribute :>> lemma="DefaultLeaseComposition.priorAdvanceGuard"; attribute :>> scope="Unique new visit plus old-context coverage implies actual preceding guard; not full multi-context trace refinement"; }
part leasesHistory:GambitAssuranceRouting::ModelNeed { ref part :>> owner=GambitAssuranceRelations::modelUse3; attribute :>> obligationId="DL-leasesHistory"; attribute :>> kind="interleaving"; attribute :>> subjectPath="dev/refactoring/modern-c/models/quint/default_section_leases.qnt"; attribute :>> subjectScope="Two-worker default allocator identity and excluded mutation histories"; attribute :>> premise="Research only; source and native admission remain separate"; }
part collectiveHistory:GambitAssuranceRouting::ModelNeed { ref part :>> owner=GambitAssuranceRelations::modelUse3; attribute :>> obligationId="DL-collectiveHistory"; attribute :>> kind="interleaving"; attribute :>> subjectPath="dev/refactoring/modern-c/models/quint/capacity_collective.qnt"; attribute :>> subjectScope="Two-member accept reject unknown and partial setup histories"; attribute :>> premise="Research only; source and native admission remain separate"; }
part leasesInduction:GambitAssuranceRouting::ModelNeed { ref part :>> owner=GambitAssuranceRelations::modelUse3; attribute :>> obligationId="DL-leasesInduction"; attribute :>> kind="induction"; attribute :>> subjectPath="dev/refactoring/modern-c/models/lean/SectionLeases.lean"; attribute :>> subjectScope="Actual typed lease AST safety and finite identity properties"; attribute :>> premise="Research only; source and native admission remain separate"; }
part collectiveInduction:GambitAssuranceRouting::ModelNeed { ref part :>> owner=GambitAssuranceRelations::modelUse3; attribute :>> obligationId="DL-collectiveInduction"; attribute :>> kind="induction"; attribute :>> subjectPath="dev/refactoring/modern-c/models/lean/CapacityCollective.lean"; attribute :>> subjectScope="Actual typed collective AST safety and failure delivery"; attribute :>> premise="Research only; source and native admission remain separate"; }
part composition:GambitAssuranceRouting::ModelNeed { ref part :>> owner=GambitAssuranceRelations::modelUse3; attribute :>> obligationId="DL-composition"; attribute :>> kind="induction"; attribute :>> subjectPath="dev/refactoring/modern-c/models/lean/DefaultLeaseComposition.lean"; attribute :>> subjectScope="Symbolic geometry guarded product and exact prior charge bridge"; attribute :>> premise="Research only; source and native admission remain separate"; }
part projection:GambitAssuranceRouting::ModelNeed { ref part :>> owner=GambitAssuranceRelations::modelUse3; attribute :>> obligationId="DL-projection"; attribute :>> kind="restricted-projection"; attribute :>> subjectPath="dev/refactoring/modern-c/models/lean/SectionLeasesAst.lean"; attribute :>> subjectScope="Both typed ASTs from pinned restricted emitter"; attribute :>> premise="Research only; source and native admission remain separate"; }
part source:GambitAssuranceRouting::ModelNeed { ref part :>> owner=GambitAssuranceRelations::modelUse3; attribute :>> obligationId="DL-source"; attribute :>> kind="source-refinement"; attribute :>> subjectPath="dev/refactoring/modern-c/default-lease-admission-design.org"; attribute :>> subjectScope="Actual mutation exclusion restore fit and all ingress remain open"; attribute :>> premise="Research only; source and native admission remain separate"; }
part platform:GambitAssuranceRouting::ModelNeed { ref part :>> owner=GambitAssuranceRelations::modelUse3; attribute :>> obligationId="DL-platform"; attribute :>> kind="native-memory-order"; attribute :>> subjectPath="dev/refactoring/modern-c/default-lease-admission-design.org"; attribute :>> subjectScope="C11 generation publication native barriers and lifetimes open"; attribute :>> premise="Research only; source and native admission remain separate"; }
part def Seam { ref part producer:GambitRuntimeComposition::BlueprintModule; ref part consumer:GambitRuntimeComposition::BlueprintModule; attribute contract:String; attribute modelNeed:String; }
part seam0:Seam { ref part :>> producer=GambitRuntimeComposition::blueprintModule4; ref part :>> consumer=GambitRuntimeComposition::blueprintModule4; attribute :>> contract="Disjoint lease and prior chunk charge"; attribute :>> modelNeed="DL-composition"; }
part seam1:Seam { ref part :>> producer=GambitRuntimeComposition::blueprintModule4; ref part :>> consumer=GambitRuntimeComposition::blueprintModule5; attribute :>> contract="Cohort writer closure and failure delivery"; attribute :>> modelNeed="DL-source"; }
part seam2:Seam { ref part :>> producer=GambitRuntimeComposition::blueprintModule4; ref part :>> consumer=GambitRuntimeComposition::blueprintModule1; attribute :>> contract="Native release/acquire and allocation provenance"; attribute :>> modelNeed="DL-platform"; }
part seam3:Seam { ref part :>> producer=GambitRuntimeComposition::blueprintModule3; ref part :>> consumer=GambitRuntimeComposition::blueprintModule4; attribute :>> contract="FFI/reentry authorization before context mutation"; attribute :>> modelNeed="DL-source"; }
}
