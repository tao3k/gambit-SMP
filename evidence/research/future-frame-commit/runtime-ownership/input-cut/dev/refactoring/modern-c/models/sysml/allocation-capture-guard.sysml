package GambitAllocationCaptureGuard { private import ScalarValues::*;
part def Owner { attribute componentId:String; }
part captureOwner:Owner { attribute :>> componentId="capture"; }
part ffiOwner:Owner { attribute :>> componentId="ffi"; }
part loggerOwner:Owner { attribute :>> componentId="logger"; }
part def SourceRow { attribute key:String; attribute path:String; attribute needle:String; attribute obligation:String; }
part source0:SourceRow { attribute :>> key="allocate"; attribute :>> path="vendor/gambit/lib/_mem/rc-allocation.inc"; attribute :>> needle="___ALLOC_MEM(bytes + sizeof (___rc_header))"; attribute :>> obligation="Checked extent and stable allocation attempt must precede this effect"; }
part source1:SourceRow { attribute :>> key="initialize"; attribute :>> path="vendor/gambit/lib/_mem/rc-allocation.inc"; attribute :>> needle="h->data = ___FAL;"; attribute :>> obligation="Private storage has false Scheme payload; input Scheme roots are separate"; }
part source2:SourceRow { attribute :>> key="register"; attribute :>> path="vendor/gambit/lib/_mem/rc-allocation.inc"; attribute :>> needle="tail->next = h;"; attribute :>> obligation="Current append has no result ledger or admission transaction"; }
part source3:SourceRow { attribute :>> key="null"; attribute :>> path="vendor/gambit/lib/_mem/rc-allocation.inc"; attribute :>> needle="if (ptr != 0) ___register_rc (___PSP ptr);"; attribute :>> obligation="Definite NULL already avoids registration"; }
part source4:SourceRow { attribute :>> key="release"; attribute :>> path="vendor/gambit/lib/_mem/rc-allocation.inc"; attribute :>> needle="next->prev = prev;"; attribute :>> obligation="Never-linked candidate needs dedicated private free rather than linked release"; }
part source5:SourceRow { attribute :>> key="cleanup"; attribute :>> path="vendor/gambit/lib/_mem/rc-allocation.inc"; attribute :>> needle="___HIDDEN void cleanup_rc"; attribute :>> obligation="Current bulk free has no stable attempt or outstanding ticket census"; }
part source6:SourceRow { attribute :>> key="malloc"; attribute :>> path="vendor/gambit/lib/os_base.c"; attribute :>> needle="ptr = malloc (bytes);"; attribute :>> obligation="Native allocator is real issuer of pointer or NULL; not ticket signer"; }
part source7:SourceRow { attribute :>> key="free"; attribute :>> path="vendor/gambit/lib/os_base.c"; attribute :>> needle="free (ptr);"; attribute :>> obligation="Synchronous physical release separated from uncertain delivery"; }
part source8:SourceRow { attribute :>> key="root-scan"; attribute :>> path="vendor/gambit/lib/_mem/rc-roots.inc"; attribute :>> needle="mark_array (work, &h->data, 1);"; attribute :>> obligation="New ticket root carrier not automatically covered by old RC chain"; }
part source9:SourceRow { attribute :>> key="tcl"; attribute :>> path="vendor/gambit/examples/tcltk/tcltk.scm"; attribute :>> needle="void *cd = ___EXT(___alloc_rc) (0);"; attribute :>> obligation="Real zero payload caller still owns header and later allocates Scheme vector"; }
part source10:SourceRow { attribute :>> key="closure"; attribute :>> path="vendor/gambit/lib/os_dyn.c"; attribute :>> needle="___set_data_rc (c_closure, proc);"; attribute :>> obligation="Architecture conditional closure caller requires source Scheme root protection"; }
part source11:SourceRow { attribute :>> key="throw"; attribute :>> path="vendor/gambit/include/_gambit/foreign_conversion.h.in"; attribute :>> needle="#define ___THROW(e)do { ___ps->longjmp_err = e;"; attribute :>> obligation="C nonlocal exit has no automatic ticket cleanup; reject unmediated crossing"; }
part source12:SourceRow { attribute :>> key="call"; attribute :>> path="vendor/gambit/lib/setup.c"; attribute :>> needle="___EXP_FUNC(___SCMOBJ,___call)"; attribute :>> obligation="Existing catcher and marker paths do not create stable allocation attempt records"; }
part source13:SourceRow { attribute :>> key="export"; attribute :>> path="vendor/gambit/lib/setup.c"; attribute :>> needle="= ___alloc_rc_no_register;"; attribute :>> obligation="Public indirect allocation callers not closed by literal inventory"; }
part source14:SourceRow { attribute :>> key="layout"; attribute :>> path="vendor/gambit/include/_gambit/memory_state.h.in"; attribute :>> needle="typedef struct ___rc_header_struct"; attribute :>> obligation="No stable ticket identity or operation result in legacy header"; }
part source15:SourceRow { attribute :>> key="teardown"; attribute :>> path="vendor/gambit/lib/_mem/memory-lifecycle.inc"; attribute :>> needle="free_still_objs (___ps);"; attribute :>> obligation="Source Scheme roots must survive cleanup ordering before RC bulk free"; }
part source16:SourceRow { attribute :>> key="logger-format"; attribute :>> path="vendor/gambit/lib/os_base.c"; attribute :>> needle="result = vfprintf (stream, format, ap);"; attribute :>> obligation="Real stdio call before native allocation wrapper returns; no direct Scheme call"; }
part source17:SourceRow { attribute :>> key="logger-flush"; attribute :>> path="vendor/gambit/lib/os_base.c"; attribute :>> needle="___fflush (stream);"; attribute :>> obligation="Logger ignores flush result; allocation ignores logger result"; }
part source18:SourceRow { attribute :>> key="stdio-flush"; attribute :>> path="vendor/gambit/lib/os_base.c"; attribute :>> needle="return fflush (stream);"; attribute :>> obligation="Native FILE wrapper; not a Scheme output port"; }
part source19:SourceRow { attribute :>> key="logger-open"; attribute :>> path="vendor/gambit/lib/os_base.c"; attribute :>> needle="___base_mod.debug = ___fopen (\"gambit.log\", \"w\");"; attribute :>> obligation="Actual setup producer; fallback stderr; not arbitrary registered Scheme sink"; }
part source20:SourceRow { attribute :>> key="logger-close"; attribute :>> path="vendor/gambit/lib/os_base.c"; attribute :>> needle="___fclose (___base_mod.debug);"; attribute :>> obligation="Base module shutdown needs a distinct stream lease if logging can overlap teardown"; }
part source21:SourceRow { attribute :>> key="logger-debug-branch"; attribute :>> path="vendor/gambit/lib/os_base.c"; attribute :>> needle="___printf (\"%p (%lu bytes) ALLOCATED"; attribute :>> obligation="Conditional logger lies after malloc; caller-side capture cannot precede it"; }
part source22:SourceRow { attribute :>> key="stdio-native"; attribute :>> path="vendor/gambit/lib/os_base.h"; attribute :>> needle="typedef FILE ___FILE;"; attribute :>> obligation="Native stdio identity; Scheme-port callback claims need separate evidence"; }
part source23:SourceRow { attribute :>> key="default-debug"; attribute :>> path="vendor/gambit/lib/os.h"; attribute :>> needle="#define ___DEBUG_LOG_not"; attribute :>> obligation="This spelling does not itself define DEBUG_LOG; command-line configuration remains open"; }
part source24:SourceRow { attribute :>> key="mask-resize"; attribute :>> path="vendor/gambit/lib/setup.c"; attribute :>> needle="cancel_disabled = pthread_setcancelstate(PTHREAD_CANCEL_DISABLE,"; attribute :>> obligation="Real resize-only cancellation masking; not allocation guard issuer"; }
part source25:SourceRow { attribute :>> key="mask-root-request"; attribute :>> path="vendor/gambit/lib/setup.c"; attribute :>> needle="if (pthread_setcancelstate(PTHREAD_CANCEL_DISABLE, &cancel_state) != 0)"; attribute :>> obligation="Root request caller checks mask result before control transfer"; }
part source26:SourceRow { attribute :>> key="restore-root-request"; attribute :>> path="vendor/gambit/lib/setup.c"; attribute :>> needle="pthread_setcancelstate(cancel_state, NULL);"; attribute :>> obligation="Restore is a separate edge; successful earlier disable is not permanent authority"; }
part source27:SourceRow { attribute :>> key="plain-cleanup"; attribute :>> path="vendor/gambit/include/_gambit/foreign_conversion.h.in"; attribute :>> needle="cleanup; }"; attribute :>> obligation="C cleanup text is sequential; raw longjmp can bypass it"; }
part source28:SourceRow { attribute :>> key="propagate"; attribute :>> path="vendor/gambit/lib/setup.c"; attribute :>> needle="___EXP_FUNC(void,___propagate_error)"; attribute :>> obligation="Nonzero error reaches throw_error; no allocation ownership record"; }
part source29:SourceRow { attribute :>> key="sfun-marker"; attribute :>> path="vendor/gambit/include/_gambit/foreign_conversion.h.in"; attribute :>> needle="#define ___BEGIN_SFUN(proc,decl)"; attribute :>> obligation="Generated entry allocates marker before Scheme call; not stable allocation guard"; }
part source30:SourceRow { attribute :>> key="marker-new"; attribute :>> path="vendor/gambit/lib/c_intf.c"; attribute :>> needle="stack_marker = ___make_vector (___ps, 2, ___FAL);"; attribute :>> obligation="Marker may allocate Scheme storage; disallow in unrecorded native-return segment"; }
part source31:SourceRow { attribute :>> key="marker-root"; attribute :>> path="vendor/gambit/lib/c_intf.c"; attribute :>> needle="proc_or_false = *proc_root; /* reload after allocating the marker */"; attribute :>> obligation="Root slot must actually remain registered; local raw wrapper alone is not registration"; }
part source32:SourceRow { attribute :>> key="marker-kill"; attribute :>> path="vendor/gambit/lib/c_intf.c"; attribute :>> needle="___VECTORELEM(marker, 0) = ___FAL; /* invalidate the C stack frame */"; attribute :>> obligation="Invalidation protects C return extent; cannot settle an allocation ticket"; }
part source33:SourceRow { attribute :>> key="sfun-emitter"; attribute :>> path="vendor/gambit/gsc/_ptree2.scm"; attribute :>> needle="(define (c-function param-typs result-typ proc-name c-defined? scope)"; attribute :>> obligation="Real Scheme generator for SFUN_CALL and marker macros"; }
part source34:SourceRow { attribute :>> key="tcl-apply"; attribute :>> path="vendor/gambit/examples/tcltk/tcltk.scm"; attribute :>> needle="(let ((result (##apply proc args)))"; attribute :>> obligation="Arbitrary exported Scheme procedure can nest Tcl evaluation and allocation"; }
part source35:SourceRow { attribute :>> key="tcl-eval"; attribute :>> path="vendor/gambit/examples/tcltk/tcltk.scm"; attribute :>> needle="Tcl_Eval (tcl_interp, cmd)"; attribute :>> obligation="Real native evaluation invokes registered command callbacks"; }
part source36:SourceRow { attribute :>> key="c-profile"; attribute :>> path="vendor/gambit/include/_gambit/language.h.in"; attribute :>> needle="#define ___LONGJMP1(jmpbuf)longjmp (jmpbuf,1)"; attribute :>> obligation="C nonlocal exit branch; actual compiler/configuration must qualify effective path"; }
part def IssuerRow { attribute key:String; attribute proposedIssuer:String; attribute actualSource:String; attribute status:String; attribute responsibility:String; }
part issuer0:IssuerRow { attribute :>> key="ticket"; attribute :>> proposedIssuer="VM stable AttemptRegistry"; attribute :>> actualSource="alloc_rc local ptr and context RC head"; attribute :>> status="proposed absent"; attribute :>> responsibility="Reserve guard root and outcome capacity outside restored Scheme frames"; }
part issuer1:IssuerRow { attribute :>> key="mask"; attribute :>> proposedIssuer="qualified native thread adapter"; attribute :>> actualSource="resize and resize-root-request pthread_setcancelstate"; attribute :>> status="real resize callers; allocation adapter absent"; attribute :>> responsibility="Confirm disable before invocation; retain saved state and restore responsibility"; }
part issuer2:IssuerRow { attribute :>> key="capture"; attribute :>> proposedIssuer="managed native allocator successor"; attribute :>> actualSource="alloc_mem malloc then optional logger"; attribute :>> status="proposed absent"; attribute :>> responsibility="Store original base and publish capture before logger header callbacks or restored cancellation"; }
part issuer3:IssuerRow { attribute :>> key="exit"; attribute :>> proposedIssuer="VM stable completion owner"; attribute :>> actualSource="BEGIN_TRY END_TRY and propagate_error"; attribute :>> status="catchers exist; stable allocation owner absent"; attribute :>> responsibility="Own captured candidate before restore; survive nested FFI and uncaught nonlocal exit"; }
part issuer4:IssuerRow { attribute :>> key="logger"; attribute :>> proposedIssuer="process base stream owner"; attribute :>> actualSource="setup_base_module and cleanup_base_module"; attribute :>> status="file lifecycle exists; active log lease absent"; attribute :>> responsibility="Hold stream through vfprintf fflush and teardown; preserve ordinary I/O result semantics"; }
part issuer5:IssuerRow { attribute :>> key="ffi"; attribute :>> proposedIssuer="generated entry and restored-execution issuer"; attribute :>> actualSource="_ptree2 c-function and SFUN macros"; attribute :>> status="marker issuer exists; ticket issuer absent"; attribute :>> responsibility="New semantic entry gets new ticket; delivery retry retains identity; GC roots before marker allocation"; }
part issuer6:IssuerRow { attribute :>> key="unknown"; attribute :>> proposedIssuer="VM quarantine and teardown owner"; attribute :>> actualSource="cleanup_rc bulk list walk"; attribute :>> status="proposed absent"; attribute :>> responsibility="Retain known captured backing or unknown allocator identity; never infer NULL or retry free"; }
part def NeedRow { attribute key:String; attribute kind:String; attribute path:String; attribute scope:String; ref owner:Owner; }
part need0:NeedRow { attribute :>> key="Guard-formal"; attribute :>> kind="formal"; attribute :>> path="dev/refactoring/modern-c/models/quint/allocation_capture_guard.qnt"; attribute :>> scope="one outer attempt one abstract nested activation finite safety only"; ref :>> owner=captureOwner; }
part need1:NeedRow { attribute :>> key="Guard-bridge"; attribute :>> kind="bridge"; attribute :>> path="dev/refactoring/modern-c/models/lean/AllocationCapture.lean"; attribute :>> scope="restricted typed IR all-step induction; NormalStep exclusion is admission premise"; ref :>> owner=captureOwner; }
part need2:NeedRow { attribute :>> key="Guard-pool"; attribute :>> kind="native"; attribute :>> path="vendor/gambit/lib/_mem/rc-allocation.inc"; attribute :>> scope="stable nonallocating guard and source-ticket issuance not implemented"; ref :>> owner=captureOwner; }
part need3:NeedRow { attribute :>> key="Guard-capture"; attribute :>> kind="native"; attribute :>> path="vendor/gambit/lib/os_base.c"; attribute :>> scope="raw allocator to capture nonescaping profile and cancellation adapter unqualified"; ref :>> owner=captureOwner; }
part need4:NeedRow { attribute :>> key="Guard-ffi"; attribute :>> kind="native"; attribute :>> path="vendor/gambit/include/_gambit/foreign_conversion.h.in"; attribute :>> scope="all nonlocal exits and nested callback issuers must join stable guard"; ref :>> owner=ffiOwner; }
part need5:NeedRow { attribute :>> key="Guard-logger"; attribute :>> kind="native"; attribute :>> path="vendor/gambit/lib/os_base.c"; attribute :>> scope="effective debug flags libc hooks and stream lifetime not host-qualified"; ref :>> owner=loggerOwner; }
part need6:NeedRow { attribute :>> key="Guard-roots"; attribute :>> kind="native"; attribute :>> path="vendor/gambit/lib/_mem/rc-roots.inc"; attribute :>> scope="carrier round coverage before marker and cleanup open"; ref :>> owner=captureOwner; }
part need7:NeedRow { attribute :>> key="Guard-retirement"; attribute :>> kind="native"; attribute :>> path="vendor/gambit/lib/_mem/memory-lifecycle.inc"; attribute :>> scope="unknown outcome drain observer grace descriptor and pool retirement open"; ref :>> owner=captureOwner; }
part def BindingRow { attribute actionName:String; attribute lemma:String; }
part binding0:BindingRow { attribute :>> actionName="allocation_capture_guard.issue"; attribute :>> lemma="AllocationCapture.issuePreserves"; }
part binding1:BindingRow { attribute :>> actionName="allocation_capture_guard.metadataReject"; attribute :>> lemma="AllocationCapture.metadataRejectPreserves"; }
part binding2:BindingRow { attribute :>> actionName="allocation_capture_guard.maskReject"; attribute :>> lemma="AllocationCapture.maskRejectPreserves"; }
part binding3:BindingRow { attribute :>> actionName="allocation_capture_guard.cancelBeforeMask"; attribute :>> lemma="AllocationCapture.cancelBeforeMaskPreserves"; }
part binding4:BindingRow { attribute :>> actionName="allocation_capture_guard.maskConfirmed"; attribute :>> lemma="AllocationCapture.maskConfirmedPreserves"; }
part binding5:BindingRow { attribute :>> actionName="allocation_capture_guard.invoke"; attribute :>> lemma="AllocationCapture.invokePreserves"; }
part binding6:BindingRow { attribute :>> actionName="allocation_capture_guard.nativeReturn"; attribute :>> lemma="AllocationCapture.nativeReturnPreserves"; }
part binding7:BindingRow { attribute :>> actionName="allocation_capture_guard.capture"; attribute :>> lemma="AllocationCapture.capturePreserves"; }
part binding8:BindingRow { attribute :>> actionName="allocation_capture_guard.armExitOwner"; attribute :>> lemma="AllocationCapture.armExitOwnerPreserves"; }
part binding9:BindingRow { attribute :>> actionName="allocation_capture_guard.restoreReturns"; attribute :>> lemma="AllocationCapture.restoreReturnsPreserves"; }
part binding10:BindingRow { attribute :>> actionName="allocation_capture_guard.restoreAbandons"; attribute :>> lemma="AllocationCapture.restoreAbandonsPreserves"; }
part binding11:BindingRow { attribute :>> actionName="allocation_capture_guard.restoreUnknown"; attribute :>> lemma="AllocationCapture.restoreUnknownPreserves"; }
part binding12:BindingRow { attribute :>> actionName="allocation_capture_guard.nativeNull"; attribute :>> lemma="AllocationCapture.nativeNullPreserves"; }
part binding13:BindingRow { attribute :>> actionName="allocation_capture_guard.finishNull"; attribute :>> lemma="AllocationCapture.finishNullPreserves"; }
part binding14:BindingRow { attribute :>> actionName="allocation_capture_guard.restoreNullAbandons"; attribute :>> lemma="AllocationCapture.restoreNullAbandonsPreserves"; }
part binding15:BindingRow { attribute :>> actionName="allocation_capture_guard.startLogger"; attribute :>> lemma="AllocationCapture.startLoggerPreserves"; }
part binding16:BindingRow { attribute :>> actionName="allocation_capture_guard.skipLogger"; attribute :>> lemma="AllocationCapture.skipLoggerPreserves"; }
part binding17:BindingRow { attribute :>> actionName="allocation_capture_guard.loggerReturns"; attribute :>> lemma="AllocationCapture.loggerReturnsPreserves"; }
part binding18:BindingRow { attribute :>> actionName="allocation_capture_guard.loggerError"; attribute :>> lemma="AllocationCapture.loggerErrorPreserves"; }
part binding19:BindingRow { attribute :>> actionName="allocation_capture_guard.nestedEnter"; attribute :>> lemma="AllocationCapture.nestedEnterPreserves"; }
part binding20:BindingRow { attribute :>> actionName="allocation_capture_guard.nestedKnownExit"; attribute :>> lemma="AllocationCapture.nestedKnownExitPreserves"; }
part binding21:BindingRow { attribute :>> actionName="allocation_capture_guard.nestedUnknownExit"; attribute :>> lemma="AllocationCapture.nestedUnknownExitPreserves"; }
part binding22:BindingRow { attribute :>> actionName="allocation_capture_guard.capturedThrow"; attribute :>> lemma="AllocationCapture.capturedThrowPreserves"; }
part binding23:BindingRow { attribute :>> actionName="allocation_capture_guard.handoff"; attribute :>> lemma="AllocationCapture.handoffPreserves"; }
part binding24:BindingRow { attribute :>> actionName="allocation_capture_guard.unrecordedEscape"; attribute :>> lemma="AllocationCapture.unrecordedEscapePreserves"; }
part binding25:BindingRow { attribute :>> actionName="allocation_capture_guard.inflightEscape"; attribute :>> lemma="AllocationCapture.inflightEscapePreserves"; }
part def RouteRow { attribute component:String; attribute actionName:String; attribute lemma:String; attribute producerAnchor:String; attribute obligationId:String; }
part route0:RouteRow { attribute :>> component="capture"; attribute :>> actionName="allocation_capture_guard.issue"; attribute :>> lemma="AllocationCapture.issuePreserves"; attribute :>> producerAnchor="allocate"; attribute :>> obligationId="Guard-pool"; }
part route1:RouteRow { attribute :>> component="capture"; attribute :>> actionName="allocation_capture_guard.metadataReject"; attribute :>> lemma="AllocationCapture.metadataRejectPreserves"; attribute :>> producerAnchor="allocate"; attribute :>> obligationId="Guard-pool"; }
part route2:RouteRow { attribute :>> component="capture"; attribute :>> actionName="allocation_capture_guard.maskReject"; attribute :>> lemma="AllocationCapture.maskRejectPreserves"; attribute :>> producerAnchor="mask-root-request"; attribute :>> obligationId="Guard-capture"; }
part route3:RouteRow { attribute :>> component="capture"; attribute :>> actionName="allocation_capture_guard.cancelBeforeMask"; attribute :>> lemma="AllocationCapture.cancelBeforeMaskPreserves"; attribute :>> producerAnchor="malloc"; attribute :>> obligationId="Guard-capture"; }
part route4:RouteRow { attribute :>> component="capture"; attribute :>> actionName="allocation_capture_guard.maskConfirmed"; attribute :>> lemma="AllocationCapture.maskConfirmedPreserves"; attribute :>> producerAnchor="mask-root-request"; attribute :>> obligationId="Guard-capture"; }
part route5:RouteRow { attribute :>> component="capture"; attribute :>> actionName="allocation_capture_guard.invoke"; attribute :>> lemma="AllocationCapture.invokePreserves"; attribute :>> producerAnchor="malloc"; attribute :>> obligationId="Guard-capture"; }
part route6:RouteRow { attribute :>> component="capture"; attribute :>> actionName="allocation_capture_guard.nativeReturn"; attribute :>> lemma="AllocationCapture.nativeReturnPreserves"; attribute :>> producerAnchor="malloc"; attribute :>> obligationId="Guard-capture"; }
part route7:RouteRow { attribute :>> component="capture"; attribute :>> actionName="allocation_capture_guard.capture"; attribute :>> lemma="AllocationCapture.capturePreserves"; attribute :>> producerAnchor="malloc"; attribute :>> obligationId="Guard-capture"; }
part route8:RouteRow { attribute :>> component="capture"; attribute :>> actionName="allocation_capture_guard.armExitOwner"; attribute :>> lemma="AllocationCapture.armExitOwnerPreserves"; attribute :>> producerAnchor="malloc"; attribute :>> obligationId="Guard-capture"; }
part route9:RouteRow { attribute :>> component="capture"; attribute :>> actionName="allocation_capture_guard.restoreReturns"; attribute :>> lemma="AllocationCapture.restoreReturnsPreserves"; attribute :>> producerAnchor="mask-root-request"; attribute :>> obligationId="Guard-capture"; }
part route10:RouteRow { attribute :>> component="capture"; attribute :>> actionName="allocation_capture_guard.restoreAbandons"; attribute :>> lemma="AllocationCapture.restoreAbandonsPreserves"; attribute :>> producerAnchor="mask-root-request"; attribute :>> obligationId="Guard-capture"; }
part route11:RouteRow { attribute :>> component="capture"; attribute :>> actionName="allocation_capture_guard.restoreUnknown"; attribute :>> lemma="AllocationCapture.restoreUnknownPreserves"; attribute :>> producerAnchor="mask-root-request"; attribute :>> obligationId="Guard-capture"; }
part route12:RouteRow { attribute :>> component="capture"; attribute :>> actionName="allocation_capture_guard.nativeNull"; attribute :>> lemma="AllocationCapture.nativeNullPreserves"; attribute :>> producerAnchor="malloc"; attribute :>> obligationId="Guard-capture"; }
part route13:RouteRow { attribute :>> component="capture"; attribute :>> actionName="allocation_capture_guard.finishNull"; attribute :>> lemma="AllocationCapture.finishNullPreserves"; attribute :>> producerAnchor="malloc"; attribute :>> obligationId="Guard-capture"; }
part route14:RouteRow { attribute :>> component="capture"; attribute :>> actionName="allocation_capture_guard.restoreNullAbandons"; attribute :>> lemma="AllocationCapture.restoreNullAbandonsPreserves"; attribute :>> producerAnchor="mask-root-request"; attribute :>> obligationId="Guard-capture"; }
part route15:RouteRow { attribute :>> component="logger"; attribute :>> actionName="allocation_capture_guard.startLogger"; attribute :>> lemma="AllocationCapture.startLoggerPreserves"; attribute :>> producerAnchor="logger-format"; attribute :>> obligationId="Guard-logger"; }
part route16:RouteRow { attribute :>> component="logger"; attribute :>> actionName="allocation_capture_guard.skipLogger"; attribute :>> lemma="AllocationCapture.skipLoggerPreserves"; attribute :>> producerAnchor="logger-format"; attribute :>> obligationId="Guard-logger"; }
part route17:RouteRow { attribute :>> component="logger"; attribute :>> actionName="allocation_capture_guard.loggerReturns"; attribute :>> lemma="AllocationCapture.loggerReturnsPreserves"; attribute :>> producerAnchor="logger-format"; attribute :>> obligationId="Guard-logger"; }
part route18:RouteRow { attribute :>> component="logger"; attribute :>> actionName="allocation_capture_guard.loggerError"; attribute :>> lemma="AllocationCapture.loggerErrorPreserves"; attribute :>> producerAnchor="logger-format"; attribute :>> obligationId="Guard-logger"; }
part route19:RouteRow { attribute :>> component="ffi"; attribute :>> actionName="allocation_capture_guard.nestedEnter"; attribute :>> lemma="AllocationCapture.nestedEnterPreserves"; attribute :>> producerAnchor="sfun-emitter"; attribute :>> obligationId="Guard-ffi"; }
part route20:RouteRow { attribute :>> component="ffi"; attribute :>> actionName="allocation_capture_guard.nestedKnownExit"; attribute :>> lemma="AllocationCapture.nestedKnownExitPreserves"; attribute :>> producerAnchor="sfun-emitter"; attribute :>> obligationId="Guard-ffi"; }
part route21:RouteRow { attribute :>> component="ffi"; attribute :>> actionName="allocation_capture_guard.nestedUnknownExit"; attribute :>> lemma="AllocationCapture.nestedUnknownExitPreserves"; attribute :>> producerAnchor="sfun-emitter"; attribute :>> obligationId="Guard-ffi"; }
part route22:RouteRow { attribute :>> component="ffi"; attribute :>> actionName="allocation_capture_guard.capturedThrow"; attribute :>> lemma="AllocationCapture.capturedThrowPreserves"; attribute :>> producerAnchor="sfun-emitter"; attribute :>> obligationId="Guard-ffi"; }
part route23:RouteRow { attribute :>> component="capture"; attribute :>> actionName="allocation_capture_guard.handoff"; attribute :>> lemma="AllocationCapture.handoffPreserves"; attribute :>> producerAnchor="root-scan"; attribute :>> obligationId="Guard-roots"; }
part route24:RouteRow { attribute :>> component="ffi"; attribute :>> actionName="allocation_capture_guard.unrecordedEscape"; attribute :>> lemma="AllocationCapture.unrecordedEscapePreserves"; attribute :>> producerAnchor="sfun-emitter"; attribute :>> obligationId="Guard-ffi"; }
part route25:RouteRow { attribute :>> component="ffi"; attribute :>> actionName="allocation_capture_guard.inflightEscape"; attribute :>> lemma="AllocationCapture.inflightEscapePreserves"; attribute :>> producerAnchor="sfun-emitter"; attribute :>> obligationId="Guard-ffi"; }
part def ProofRow { attribute key:String; attribute lemma:String; }
part proof0:ProofRow { attribute :>> key="all-step"; attribute :>> lemma="AllocationCapture.stepPreserves"; }
part proof1:ProofRow { attribute :>> key="reachable"; attribute :>> lemma="AllocationCapture.reachableSafe"; }
part proof2:ProofRow { attribute :>> key="logger-captured"; attribute :>> lemma="AllocationCapture.loggerAfterCapture"; }
part proof3:ProofRow { attribute :>> key="nested-parent"; attribute :>> lemma="AllocationCapture.nestedRetainsParent"; }
part proof4:ProofRow { attribute :>> key="unknown-custody"; attribute :>> lemma="AllocationCapture.unknownRetainsGuard"; }
part proof5:ProofRow { attribute :>> key="mask-before-capture"; attribute :>> lemma="AllocationCapture.unrecordedIsMasked"; }
part proof6:ProofRow { attribute :>> key="handoff"; attribute :>> lemma="AllocationCapture.knownHandoff"; }
part proof7:ProofRow { attribute :>> key="invocation-bound"; attribute :>> lemma="AllocationCapture.atMostOneInvocation"; }
part proof8:ProofRow { attribute :>> key="conditional-no-loss"; attribute :>> lemma="AllocationCapture.normalStepDoesNotLosePointer"; }
part def PathRow { attribute key:String; attribute chain:String; attribute classification:String; attribute boundary:String; }
part path0:PathRow { attribute :>> key="plain"; attribute :>> chain="alloc_rc -> alloc_rc_no_register -> alloc_mem -> malloc"; attribute :>> classification="literal default branch has no direct Scheme dispatch"; attribute :>> boundary="effective Darwin allocator hooks external signal and cancellation closure unqualified"; }
part path1:PathRow { attribute :>> key="debug"; attribute :>> chain="alloc_mem -> printf -> vfprintf -> fflush"; attribute :>> classification="real conditional stdio chain after native effect"; attribute :>> boundary="no direct Scheme call in Gambit logger; selected debug profile not proven"; }
part path2:PathRow { attribute :>> key="nested"; attribute :>> chain="Tcl_Eval -> scheme_call_cmd -> generated tcltk_call -> apply proc -> tcltk-export-procedure -> alloc_rc"; attribute :>> classification="source-composable legal nested allocation chain"; attribute :>> boundary="generator and macros identified; no matched native generated artifact qualification"; }
part path3:PathRow { attribute :>> key="logger-Scheme"; attribute :>> chain="vfprintf or FILE writer -> Scheme callback"; attribute :>> classification="not established for inspected fopen/stderr producer"; attribute :>> boundary="custom stream interposer or hook requires new caller evidence; not current bug witness"; }
part path4:PathRow { attribute :>> key="throw"; attribute :>> chain="SFUN_ERROR -> call conversion handler -> END_SFUN propagate_error -> throw_error -> THROW"; attribute :>> classification="real generated-capable nonlocal transfer"; attribute :>> boundary="logger to this chain is not established; C sequential cleanup not automatic unwinding"; }
part path5:PathRow { attribute :>> key="mask"; attribute :>> chain="resize source publication -> disable -> sync -> restore"; attribute :>> classification="real limited cancellation discipline"; attribute :>> boundary="not authority for RC allocation; no current stable allocation guard signer"; }
part def GainRow { attribute key:String; attribute avoided:String; attribute added:String; attribute condition:String; }
part gain0:GainRow { attribute :>> key="critical stdio"; attribute :>> avoided="2 explicit stdio operations moved outside return-to-capture window when debug logger enabled"; attribute :>> added="same vfprintf plus fflush still run after stable capture"; attribute :>> condition="capture moved inside allocator boundary before logging; no claim for opaque libc internal calls"; }
part gain1:GainRow { attribute :>> key="critical callbacks"; attribute :>> avoided="0 admitted Scheme calls inside unrecorded segment by contract"; attribute :>> added="source root stable guard and noescape profile qualification"; attribute :>> condition="reject allocator hooks or jumps that can abandon raw result"; }
part gain2:GainRow { attribute :>> key="cancellation"; attribute :>> avoided="known candidate owned before restoration can abandon execution"; attribute :>> added="disable and restore pair plus completion-owner transfer per outer attempt"; attribute :>> condition="effective native thread API and handler closure qualified; C23 alone insufficient"; }
part gain3:GainRow { attribute :>> key="nesting"; attribute :>> avoided="outer ticket cannot be overwritten or settled by one nested activation in finite model"; attribute :>> added="distinct child authority and retained parent record"; attribute :>> condition="fixed one nested activation only; arbitrary nesting and fresh identities remain open"; }
part gain4:GainRow { attribute :>> key="logger errors"; attribute :>> avoided="negative logger result does not turn successful allocation into NULL"; attribute :>> added="guard must survive blocking I/O and stream teardown"; attribute :>> condition="ordinary result semantics preserved; new asynchronous logger would be separate change"; }
part gain5:GainRow { attribute :>> key="unknown"; attribute :>> avoided="no second allocator effect admitted after unrecorded loss in finite model"; attribute :>> added="quarantine consumes metadata roots and may prevent shutdown"; attribute :>> condition="custody is safety not recovery or liveness"; }
part gain6:GainRow { attribute :>> key="language"; attribute :>> avoided="C23 can express ownership publication and checked boundary schema"; attribute :>> added="modern C and Zig both need mask guards FFI roots and stream lifetime support"; attribute :>> condition="no demonstrated incremental Zig benefit or CPU speedup"; }
part gain7:GainRow { attribute :>> key="retirement"; attribute :>> avoided="0 current native paths retired"; attribute :>> added="new managed allocator and generated guard protocol needed"; attribute :>> condition="close direct indirect FFI and effective ABI/profile paths before removing old managed routes"; }
part def MemoryRow { attribute key:String; attribute publication:String; attribute observation:String; attribute obligation:String; }
part memory0:MemoryRow { attribute :>> key="guard"; attribute :>> publication="publish stable root-linked ticket before invocation"; attribute :>> observation="acquire ticket state with lifetime pin"; attribute :>> obligation="mask success does not register roots or keep VM alive"; }
part memory1:MemoryRow { attribute :>> key="capture"; attribute :>> publication="write original base extent allocator identity then release publish CAPTURED"; attribute :>> observation="acquire CAPTURED before inspecting base"; attribute :>> obligation="no callbacks logger longjmp or cancellation may abandon the prepublication segment"; }
part memory2:MemoryRow { attribute :>> key="restore"; attribute :>> publication="commit stable completion owner before restoring saved cancellation"; attribute :>> observation="supervisor can acquire owner even when restore never returns"; attribute :>> obligation="restoration result must not be needed to reconstruct lost ownership"; }
part memory3:MemoryRow { attribute :>> key="nested"; attribute :>> publication="distinct child identity and parent pin before callback"; attribute :>> observation="child outcome settles only its own record"; attribute :>> obligation="unknown child prevents outer result handoff and pool retirement"; }
part memory4:MemoryRow { attribute :>> key="stream"; attribute :>> publication="hold base stream and code descriptor across logger"; attribute :>> observation="cleanup observes drained active stream users"; attribute :>> obligation="VM ticket pin is not a process-global FILE lifetime lease"; }
part def ContractRow { attribute fromNode:String; attribute toNode:String; attribute custody:String; }
part contract0:ContractRow { attribute :>> fromNode="Caller"; attribute :>> toNode="StableGuard"; attribute :>> custody="reserve stable metadata root and completion identity before native entry"; }
part contract1:ContractRow { attribute :>> fromNode="StableGuard"; attribute :>> toNode="MaskedInvocation"; attribute :>> custody="confirm saved cancellation state and noescape profile; no pool lock across allocator"; }
part contract2:ContractRow { attribute :>> fromNode="MaskedInvocation"; attribute :>> toNode="UnrecordedReturn"; attribute :>> custody="raw native effect; local pointer not reconstructible by an outer catcher"; }
part contract3:ContractRow { attribute :>> fromNode="UnrecordedReturn"; attribute :>> toNode="CapturedRecord"; attribute :>> custody="capture original base before header callbacks debug logger or cancellation restore"; }
part contract4:ContractRow { attribute :>> fromNode="CapturedRecord"; attribute :>> toNode="StableExitOwner"; attribute :>> custody="publish supervisor ownership before restoration can abandon execution"; }
part contract5:ContractRow { attribute :>> fromNode="StableExitOwner"; attribute :>> toNode="Logger"; attribute :>> custody="preserve vfprintf and fflush after capture; hold stream lifetime"; }
part contract6:ContractRow { attribute :>> fromNode="Logger"; attribute :>> toNode="NestedFFI"; attribute :>> custody="Optional admitted hook; current logger has no proven Scheme route"; }
part contract7:ContractRow { attribute :>> fromNode="NestedFFI"; attribute :>> toNode="NestedSettlement"; attribute :>> custody="Separate child ticket; settle only its own identity"; }
part contract8:ContractRow { attribute :>> fromNode="Logger"; attribute :>> toNode="IndexAdmission"; attribute :>> custody="No active child; ordinary I/O error preserves allocation"; }
part contract9:ContractRow { attribute :>> fromNode="UnrecordedReturn"; attribute :>> toNode="Quarantine"; attribute :>> custody="protocol violation loses recoverable pointer; retain identity deny retry and teardown"; }
part contract10:ContractRow { attribute :>> fromNode="StableExitOwner"; attribute :>> toNode="Quarantine"; attribute :>> custody="restore unknown or cancellation abandonment retains captured candidate"; }
part contract11:ContractRow { attribute :>> fromNode="NestedSettlement"; attribute :>> toNode="IndexAdmission"; attribute :>> custody="Known child result and logger completion required"; }
part contract12:ContractRow { attribute :>> fromNode="NestedFFI"; attribute :>> toNode="Quarantine"; attribute :>> custody="Unknown child retains parent; no outer handoff"; }
}
