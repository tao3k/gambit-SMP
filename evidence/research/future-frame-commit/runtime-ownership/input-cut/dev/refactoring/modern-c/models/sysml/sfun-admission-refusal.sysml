package GambitSfunAdmissionRefusal { private import ScalarValues::*;
part def SourceRow { attribute key:String; attribute path:String; attribute needle:String; attribute obligation:String; }
part source0:SourceRow { attribute :>> key="sfun-prolog"; attribute :>> path="vendor/gambit/include/_gambit/foreign_conversion.h.in"; attribute :>> needle="#define ___BEGIN_SFUN_VOID(proc)"; attribute :>> obligation="marker allocated before input conversion; no conversion guard"; }
part source1:SourceRow { attribute :>> key="sfun-input"; attribute :>> path="vendor/gambit/include/_gambit/foreign_conversion.h.in"; attribute :>> needle="#define ___SFUN_ARG(i,arg)___PSSTK"; attribute :>> obligation="stack publication before call; not still-count release"; }
part source2:SourceRow { attribute :>> key="sfun-error"; attribute :>> path="vendor/gambit/include/_gambit/foreign_conversion.h.in"; attribute :>> needle="#define ___SFUN_ERROR_VOID"; attribute :>> obligation="retry calls and error propagation outlive argument scope"; }
part source3:SourceRow { attribute :>> key="sfun-finish"; attribute :>> path="vendor/gambit/include/_gambit/foreign_conversion.h.in"; attribute :>> needle="#define ___END_SFUN_VOID"; attribute :>> obligation="marker invalidation then propagate; not conversion guard"; }
part source4:SourceRow { attribute :>> key="catcher"; attribute :>> path="vendor/gambit/include/_gambit/foreign_conversion.h.in"; attribute :>> needle="___ps->catcher = &___jbuf;"; attribute :>> obligation="catcher is automatic activation, restored at END_TRY"; }
part source5:SourceRow { attribute :>> key="throw"; attribute :>> path="vendor/gambit/include/_gambit/foreign_conversion.h.in"; attribute :>> needle="#define ___THROW(e)do { ___ps->longjmp_err"; attribute :>> obligation="nonlocal jump can bypass nested local ENDs"; }
part source6:SourceRow { attribute :>> key="language-c"; attribute :>> path="vendor/gambit/include/_gambit/language.h.in"; attribute :>> needle="#define ___USE_SETJMP"; attribute :>> obligation="C path uses setjmp; no C++ RAII assumption"; }
part source7:SourceRow { attribute :>> key="call-entry"; attribute :>> path="vendor/gambit/lib/setup.c"; attribute :>> needle="___EXP_FUNC(___SCMOBJ,___call)"; attribute :>> obligation="GC phase rejection before frame writes; catcher created later"; }
part source8:SourceRow { attribute :>> key="call-rethrow"; attribute :>> path="vendor/gambit/lib/setup.c"; attribute :>> needle="stack_marker != ___ps->context->fp[___FRAME_SPACE(2)-2]"; attribute :>> obligation="mismatched marker rethrows across wrapper scope"; }
part source9:SourceRow { attribute :>> key="run-landing"; attribute :>> path="vendor/gambit/lib/setup.c"; attribute :>> needle="___VOLATILE ___SCMOBJ marker = ___FAL;"; attribute :>> obligation="run catches its own marker; no per-conversion record"; }
part source10:SourceRow { attribute :>> key="error-propagation"; attribute :>> path="vendor/gambit/lib/setup.c"; attribute :>> needle="___EXP_FUNC(void,___propagate_error)"; attribute :>> obligation="error triggers throw"; }
part source11:SourceRow { attribute :>> key="marker-rooted"; attribute :>> path="vendor/gambit/lib/c_intf.c"; attribute :>> needle="proc_or_false = *proc_root; /* reload after allocating the marker */"; attribute :>> obligation="rooted startup endpoint reloads; generic wrapper local not registry"; }
part source12:SourceRow { attribute :>> key="marker-raw"; attribute :>> path="vendor/gambit/lib/c_intf.c"; attribute :>> needle="Legacy raw SFUN entry is not made a registered-root interface"; attribute :>> obligation="do not infer generic ingress roots"; }
part source13:SourceRow { attribute :>> key="marker-kill"; attribute :>> path="vendor/gambit/lib/c_intf.c"; attribute :>> needle="___still_obj_refcount_dec (marker);"; attribute :>> obligation="different object and native lifetime"; }
part source14:SourceRow { attribute :>> key="alloc-gc"; attribute :>> path="vendor/gambit/lib/_mem/object-allocation.inc"; attribute :>> needle="if (___garbage_collect (___PSP words))"; attribute :>> obligation="never hold short mutation lease across allocating converter"; }
part source15:SourceRow { attribute :>> key="alloc-count"; attribute :>> path="vendor/gambit/lib/_mem/object-allocation.inc"; attribute :>> needle="base[___STILL_REFCOUNT] = 1;"; attribute :>> obligation="native temporary hold protects fresh still object"; }
part source16:SourceRow { attribute :>> key="scan-context"; attribute :>> path="vendor/gambit/lib/_mem/root-origins.inc"; attribute :>> needle="mark_array (work, context->r, sizeof(context->r)/sizeof(*context->r));"; attribute :>> obligation="includes exact PSR1 slot"; }
part source17:SourceRow { attribute :>> key="scan-startup"; attribute :>> path="vendor/gambit/lib/_mem/root-origins.inc"; attribute :>> needle="mark_array (work, &context->entry_marker, 1);"; attribute :>> obligation="startup has dedicated roots, not generic conversion table"; }
part source18:SourceRow { attribute :>> key="root-barrier"; attribute :>> path="vendor/gambit/lib/_mem/collection-round.inc"; attribute :>> needle="BARRIER(); /* actual W and every grant published after complete R freeze */"; attribute :>> obligation="all participants frozen before worker access"; }
part source19:SourceRow { attribute :>> key="owner-cleanup"; attribute :>> path="vendor/gambit/lib/_mem/collection-round.inc"; attribute :>> needle="vm->gc_participants[id].phase = ___GC_OWNER_CLEANUP;"; attribute :>> obligation="restored stacks do not authorize managed reentry"; }
part source20:SourceRow { attribute :>> key="scan-drain"; attribute :>> path="vendor/gambit/lib/_mem/collection-round.inc"; attribute :>> needle="BARRIER(); /* no worker may retain a stopped root view past this cut */"; attribute :>> obligation="scanner view retirement before reuse"; }
part source21:SourceRow { attribute :>> key="phase-field"; attribute :>> path="vendor/gambit/include/_gambit/runtime_roles.h.in"; attribute :>> needle="___gc_participant_phase phase;"; attribute :>> obligation="ordinary enum, not an atomic admission pin"; }
part source22:SourceRow { attribute :>> key="generator-args"; attribute :>> path="vendor/gambit/gsc/_ptree2.scm"; attribute :>> needle="(define (c-convert-argument sfun? numbered-typ body)"; attribute :>> obligation="SFUN args converted before call"; }
part source23:SourceRow { attribute :>> key="generator-result"; attribute :>> path="vendor/gambit/gsc/_ptree2.scm"; attribute :>> needle="(define (c-set-result sfun? result-typ)"; attribute :>> obligation="CFUN native result converted into PSR1"; }
part source24:SourceRow { attribute :>> key="generator-cleanup"; attribute :>> path="vendor/gambit/gsc/_ptree2.scm"; attribute :>> needle="(define (type-needs-cleanup? typ-source)"; attribute :>> obligation="false parameter flags omit cleanup TRY; not result ownership"; }
part source25:SourceRow { attribute :>> key="generator-plan"; attribute :>> path="vendor/gambit/gsc/_ptree2.scm"; attribute :>> needle="(define (c-make-function sfun? name param-typs result-typ make-body)"; attribute :>> obligation="candidate producer of direction-aware guard plan"; }
part source26:SourceRow { attribute :>> key="type-registry"; attribute :>> path="vendor/gambit/gsc/_parms.scm"; attribute :>> needle="(cons size_t-sym"; attribute :>> obligation="three flags false; unchanged ownership omission"; }
part source27:SourceRow { attribute :>> key="darwin-config"; attribute :>> path="vendor/gambit/config.status"; attribute :>> needle="'--disable-smp'"; attribute :>> obligation="configured arm64 GCC16 subset not SMP native qualification"; }
part source28:SourceRow { attribute :>> key="width-config"; attribute :>> path="vendor/gambit/config.log"; attribute :>> needle="ac_cv_sizeof_long=8"; attribute :>> obligation="historical generated profile"; }
part source29:SourceRow { attribute :>> key="build-command"; attribute :>> path="vendor/gambit/bin/gambuild-C"; attribute :>> needle="/opt/homebrew/Cellar/gcc/16.2.0/bin/gcc-16"; attribute :>> obligation="actual recorded toolchain command"; }
part source30:SourceRow { attribute :>> key="generated-header"; attribute :>> path="vendor/gambit/include/gambit.h"; attribute :>> needle="#define ___CFUN_RESULT ___PSR1"; attribute :>> obligation="same macro subset not same full code cohort"; }
part source31:SourceRow { attribute :>> key="feeley-paper"; attribute :>> path="evidence/research/sfun-converter-use-closure/feeley-sfp-paper.txt"; attribute :>> needle="return to C frames"; attribute :>> obligation="Scheme continuation extent versus C activation extent"; }
part source32:SourceRow { attribute :>> key="real-gc-phase"; attribute :>> path="vendor/gambit/tests/smp/gc/worker-root-domains.scm"; attribute :>> needle="vm->gc_participants[d->owner].phase!=___GC_OWNER_CLEANUP"; attribute :>> obligation="actual native release body checks cleanup phase; source-only test"; }
part source33:SourceRow { attribute :>> key="real-gc-register"; attribute :>> path="vendor/gambit/tests/smp/gc/worker-root-domains.scm"; attribute :>> needle="domain_release,&obj,0);"; attribute :>> obligation="actual pointer constructor stores callback"; }
part source34:SourceRow { attribute :>> key="real-gc-call"; attribute :>> path="vendor/gambit/tests/smp/gc/worker-root-domains.scm"; attribute :>> needle="if (___call(___PSP 0,___FAL,___FAL)==___FIX(___UNKNOWN_ERR))"; attribute :>> obligation="direct low-level call, not generated SFUN"; }
part source35:SourceRow { attribute :>> key="real-gc-run"; attribute :>> path="vendor/gambit/tests/smp/gc/worker-root-domains.scm"; attribute :>> needle="if (___run(___PSP ___FAL)==___FIX(___UNKNOWN_ERR))"; attribute :>> obligation="direct run rejection; avoids SFUN wrapper"; }
part source36:SourceRow { attribute :>> key="real-gc-roster"; attribute :>> path="vendor/gambit/tests/smp/gc/worker-root-domains.scm"; attribute :>> needle="vm->processor_count!=3"; attribute :>> obligation="three-participant source test is not configured disabled-SMP receipt"; }
part source37:SourceRow { attribute :>> key="gc-release-invoke"; attribute :>> path="vendor/gambit/lib/_mem/still-sweep.inc"; attribute :>> needle="___release_foreign(obj);"; attribute :>> obligation="sweep invokes registered native releaser on owner"; }
part source38:SourceRow { attribute :>> key="foreign-release-dispatch"; attribute :>> path="vendor/gambit/lib/c_intf.c"; attribute :>> needle="if ((e = release_fn (ptr)) != ___FIX(___NO_ERR))"; attribute :>> obligation="indirect callback extension point; not every target calls Scheme"; }
part source39:SourceRow { attribute :>> key="pointer-hook"; attribute :>> path="vendor/gambit/lib/c_intf.c"; attribute :>> needle="___FOREIGN_RELEASE_FN_FIELD(r) = ___CAST(___SCMOBJ,release_fn);"; attribute :>> obligation="native callback registration"; }
part source40:SourceRow { attribute :>> key="pointer-default-no-call"; attribute :>> path="vendor/gambit/lib/c_intf.c"; attribute :>> needle="___EXP_FUNC(___SCMOBJ,___release_pointer)"; attribute :>> obligation="default no-op does not call Scheme"; }
part source41:SourceRow { attribute :>> key="function-default-no-call"; attribute :>> path="vendor/gambit/lib/c_intf.c"; attribute :>> needle="___EXP_FUNC(___SCMOBJ,___release_function)"; attribute :>> obligation="releases RC closure storage, does not execute callback"; }
part source42:SourceRow { attribute :>> key="tcl-native-callback"; attribute :>> path="vendor/gambit/examples/tcltk/tcltk.scm"; attribute :>> needle="char *result = tcltk_call (___EXT(___data_rc)"; attribute :>> obligation="real callback loads RC payload before SFUN marker allocation"; }
part source43:SourceRow { attribute :>> key="tcl-register"; attribute :>> path="vendor/gambit/examples/tcltk/tcltk.scm"; attribute :>> needle="___result = ___BOOLEAN (Tcl_CreateCommand"; attribute :>> obligation="native command registration supplies callback and delete hooks"; }
part source44:SourceRow { attribute :>> key="tcl-export"; attribute :>> path="vendor/gambit/examples/tcltk/tcltk.scm"; attribute :>> needle="(c-define (##tcltk-call vect args)"; attribute :>> obligation="typed-result SFUN source producer"; }
part source45:SourceRow { attribute :>> key="tcl-delete"; attribute :>> path="vendor/gambit/examples/tcltk/tcltk.scm"; attribute :>> needle="___HIDDEN void scheme_delete_cmd"; attribute :>> obligation="delete hook releases payload/RC, not a Scheme invocation"; }
part source46:SourceRow { attribute :>> key="tcl-error-callback"; attribute :>> path="vendor/gambit/examples/tcltk/tcltk.scm"; attribute :>> needle="tcltk_eval_error (___CAST(char*,Tcl_GetStringResult(tcl_interp)));"; attribute :>> obligation="native error translator calls a second SFUN endpoint"; }
part source47:SourceRow { attribute :>> key="tcl-error-export"; attribute :>> path="vendor/gambit/examples/tcltk/tcltk.scm"; attribute :>> needle="(c-define (##tcltk-eval-error msg)"; attribute :>> obligation="void error callback also needs refusal policy"; }
part source48:SourceRow { attribute :>> key="tcl-source-publish"; attribute :>> path="vendor/gambit/examples/tcltk/tcltk.scm"; attribute :>> needle="___EXT(___set_data_rc) (cd, vect);"; attribute :>> obligation="STILL vector count protects payload while alive; delete requires borrow closure"; }
part source49:SourceRow { attribute :>> key="rc-source-read"; attribute :>> path="vendor/gambit/lib/_mem/rc-allocation.inc"; attribute :>> needle="___EXP_FUNC(___SCMOBJ,___data_rc)"; attribute :>> obligation="read value is not an atomic borrow or root transfer"; }
part source50:SourceRow { attribute :>> key="rc-source-write"; attribute :>> path="vendor/gambit/lib/_mem/rc-allocation.inc"; attribute :>> needle="h->data = val;"; attribute :>> obligation="public setter must join source-root writer admission"; }
part source51:SourceRow { attribute :>> key="rc-scan"; attribute :>> path="vendor/gambit/lib/_mem/rc-roots.inc"; attribute :>> needle="mark_array (work, &h->data, 1);"; attribute :>> obligation="actual context-owned RC data scanner"; }
part source52:SourceRow { attribute :>> key="mem-native-callback"; attribute :>> path="vendor/gambit/tests/mem.scm"; attribute :>> needle="f (\\\"was called from C\\\");"; attribute :>> obligation="foo calls actual Scheme-exported C function"; }
part source53:SourceRow { attribute :>> key="mem-export"; attribute :>> path="vendor/gambit/tests/mem.scm"; attribute :>> needle="(c-define (hop str)"; attribute :>> obligation="typed result callback producer"; }
part source54:SourceRow { attribute :>> key="mem-function-import"; attribute :>> path="vendor/gambit/tests/mem.scm"; attribute :>> needle="(define foo (c-lambda (real integer (function (char-string) int))"; attribute :>> obligation="actual function-pointer consumer"; }
part source55:SourceRow { attribute :>> key="function-target"; attribute :>> path="vendor/gambit/lib/c_intf.c"; attribute :>> needle="*x = ___CAST(void*,body[-___LABEL_SIZE+___LABEL_HOST])"; attribute :>> obligation="static exported function or dynamic closure converter"; }
part source56:SourceRow { attribute :>> key="pthread-call"; attribute :>> path="vendor/gambit/examples/pthread/pthread.c"; attribute :>> needle="___ON_THROW(increment_counter (counter), got_throw=1);"; attribute :>> obligation="real void SFUN caller and native outer catcher"; }
part source57:SourceRow { attribute :>> key="pthread-mutex"; attribute :>> path="vendor/gambit/examples/pthread/pthread.c"; attribute :>> needle="pthread_mutex_lock (&mut);"; attribute :>> obligation="closed example serializes increments; not a universal GC gate"; }
part source58:SourceRow { attribute :>> key="pthread-join"; attribute :>> path="vendor/gambit/examples/pthread/pthread.c"; attribute :>> needle="pthread_join (tid[i], &results[i]);"; attribute :>> obligation="get/release called after workers joined"; }
part source59:SourceRow { attribute :>> key="pthread-export"; attribute :>> path="vendor/gambit/examples/pthread/mylib.scm"; attribute :>> needle="(c-define (increment-counter c)"; attribute :>> obligation="actual void SFUN producer"; }
part source60:SourceRow { attribute :>> key="pthread-still-root"; attribute :>> path="vendor/gambit/examples/pthread/mylib.scm"; attribute :>> needle="(##still-copy (make-counter 0))"; attribute :>> obligation="counter is explicitly native-held STILL object"; }
part source61:SourceRow { attribute :>> key="error-unknown"; attribute :>> path="vendor/gambit/include/_gambit/foreign_abi.h.in"; attribute :>> needle="#define ___UNKNOWN_ERR                          (___ERR_BASE+3)"; attribute :>> obligation="UNKNOWN differs from NO_ERR and UNWIND in current code"; }
part source62:SourceRow { attribute :>> key="error-unwind"; attribute :>> path="vendor/gambit/include/_gambit/foreign_abi.h.in"; attribute :>> needle="#define ___UNWIND_C_STACK                       (___ERR_BASE+0)"; attribute :>> obligation="legacy loop excludes this sentinel, not UNKNOWN"; }
part source63:SourceRow { attribute :>> key="ctos-stage"; attribute :>> path="vendor/gambit/include/_gambit/foreign_conversion.h.in"; attribute :>> needle="#define ___CTOS3(f,c,s,i)"; attribute :>> obligation="producer operation identifies conversion error provenance"; }
part source64:SourceRow { attribute :>> key="on-throw"; attribute :>> path="vendor/gambit/include/_gambit/foreign_conversion.h.in"; attribute :>> needle="#define ___ON_THROW_AUX(decl,stat1,stat2)"; attribute :>> obligation="outer catcher applies only when actually established"; }
part def ComponentRow { attribute componentId:String; attribute sharedContract:String; attribute role:String; }
part component0:ComponentRow { attribute :>> componentId="entry-admission"; attribute :>> sharedContract="EntryOrigin/SourceBorrow/GuardReceipt"; attribute :>> role="preallocation domain and source admission"; }
part component1:ComponentRow { attribute :>> componentId="native-return"; attribute :>> sharedContract="EntryOrigin/SourceBorrow/GuardReceipt"; attribute :>> role="root/marker/guard cleanup and ABI outcomes"; }
part component2:ComponentRow { attribute :>> componentId="legacy-retry"; attribute :>> sharedContract="EntryOrigin/SourceBorrow/GuardReceipt"; attribute :>> role="audited source recurrence, excluded from managed reachability"; }
part def PathRow { attribute key:String; attribute producer:String; attribute consumer:String; attribute classification:String; attribute phase:String; attribute missing:String; attribute loopStatus:String; }
part path0:PathRow { attribute :>> key="gc-direct"; attribute :>> producer="real-gc-register"; attribute :>> consumer="real-gc-call"; attribute :>> classification="registered-source-chain"; attribute :>> phase="OWNER_CLEANUP"; attribute :>> missing="SFUN wrapper absent"; attribute :>> loopStatus="not-an-SFUN-loop"; }
part path1:PathRow { attribute :>> key="gc-run"; attribute :>> producer="real-gc-register"; attribute :>> consumer="real-gc-run"; attribute :>> classification="registered-source-chain"; attribute :>> phase="OWNER_CLEANUP"; attribute :>> missing="SFUN wrapper absent"; attribute :>> loopStatus="not-an-SFUN-loop"; }
part path2:PathRow { attribute :>> key="tcl-command"; attribute :>> producer="tcl-register"; attribute :>> consumer="tcl-export"; attribute :>> classification="registered-source-endpoint"; attribute :>> phase="ordinary native callback; actual phase unobserved"; attribute :>> missing="GC cleanup to this callback edge"; attribute :>> loopStatus="not-proven"; }
part path3:PathRow { attribute :>> key="tcl-error"; attribute :>> producer="tcl-error-callback"; attribute :>> consumer="tcl-error-export"; attribute :>> classification="direct-source-call"; attribute :>> phase="actual phase unobserved"; attribute :>> missing="GC cleanup to Tcl evaluation edge"; attribute :>> loopStatus="not-proven"; }
part path4:PathRow { attribute :>> key="tcl-delete"; attribute :>> producer="tcl-register"; attribute :>> consumer="tcl-delete"; attribute :>> classification="release-only-source-hook"; attribute :>> phase="native delete callback"; attribute :>> missing="no Scheme call in audited delete body"; attribute :>> loopStatus="excluded-as-SFUN-edge"; }
part path5:PathRow { attribute :>> key="mem-callback"; attribute :>> producer="mem-function-import"; attribute :>> consumer="mem-export"; attribute :>> classification="direct-source-call"; attribute :>> phase="synchronous allocation may collect before f returns into Scheme"; attribute :>> missing="no active-cleanup invocation edge"; attribute :>> loopStatus="not-proven"; }
part path6:PathRow { attribute :>> key="pthread-serialized"; attribute :>> producer="pthread-call"; attribute :>> consumer="pthread-export"; attribute :>> classification="serialized-source-call"; attribute :>> phase="closed example holds mut across entry"; attribute :>> missing="no registered cleanup target; shared mut serializes increments"; attribute :>> loopStatus="excluded-in-closed-example"; }
part path7:PathRow { attribute :>> key="public-release-api"; attribute :>> producer="pointer-hook"; attribute :>> consumer="foreign-release-dispatch"; attribute :>> classification="open-indirect-extension"; attribute :>> phase="can be invoked in cleanup"; attribute :>> missing="identity of arbitrary user callback target"; attribute :>> loopStatus="conditional-schema-only"; }
part def IssuerRow { attribute key:String; attribute source:String; attribute existing:String; attribute candidate:String; attribute gap:String; }
part issuer0:IssuerRow { attribute :>> key="refusal-origin"; attribute :>> source="call-entry"; attribute :>> existing="___call has phase rejection before catcher"; attribute :>> candidate="checked call-site discriminator records operation producer"; attribute :>> gap="current macros fold refusal into one error loop"; }
part issuer1:IssuerRow { attribute :>> key="preallocation-entry"; attribute :>> source="generator-plan"; attribute :>> existing="c-make-function emits common SFUN wrapper"; attribute :>> candidate="reserve/validate source carrier then admission before marker"; attribute :>> gap="legacy raw export cannot return typed refusal by itself"; }
part issuer2:IssuerRow { attribute :>> key="source-pin"; attribute :>> source="rc-source-read"; attribute :>> existing="data_rc returns current payload"; attribute :>> candidate="RC owner grants nonalloc borrow with exact generation and deletion drain"; attribute :>> gap="raw pointer read or refcount++ alone not borrow proof"; }
part issuer3:IssuerRow { attribute :>> key="guard-pool"; attribute :>> source="marker-rooted"; attribute :>> existing="startup helper reloads procedure root after allocation"; attribute :>> candidate="VM/root-domain guard pool with initialized registered slots"; attribute :>> gap="startup-only endpoint not generic ingress issuer"; }
part issuer4:IssuerRow { attribute :>> key="outer-landing"; attribute :>> source="on-throw"; attribute :>> existing="explicit pthread caller installs outer catcher"; attribute :>> candidate="stable NativeReturnDomain completion adopts resources before abandoned C frames disappear"; attribute :>> gap="no catcher may be assumed at arbitrary foreign entry"; }
part issuer5:IssuerRow { attribute :>> key="tcl-boundary"; attribute :>> source="tcl-native-callback"; attribute :>> existing="callback expects char* or Scheme throw; Tcl callback returns int"; attribute :>> candidate="checked adapter maps refusal to Tcl failure without calling Scheme error translator while closed"; attribute :>> gap="native result/error lifetime and deletion borrow remain open"; }
part def RouteRow { attribute component:String; attribute actionName:String; attribute lemma:String; attribute producerAnchor:String; attribute obligationId:String; }
part route0:RouteRow { attribute :>> component="entry-admission"; attribute :>> actionName="sfun_admission_refusal.refuseBeforeEntry"; attribute :>> lemma="SfunAdmission.refuseBeforeEntryPreserves"; attribute :>> producerAnchor="generator-plan"; attribute :>> obligationId="admission-protocol"; }
part route1:RouteRow { attribute :>> component="entry-admission"; attribute :>> actionName="sfun_admission_refusal.exhaustPool"; attribute :>> lemma="SfunAdmission.exhaustPoolPreserves"; attribute :>> producerAnchor="generator-plan"; attribute :>> obligationId="admission-protocol"; }
part route2:RouteRow { attribute :>> component="entry-admission"; attribute :>> actionName="sfun_admission_refusal.refuseNoRecord"; attribute :>> lemma="SfunAdmission.refuseNoRecordPreserves"; attribute :>> producerAnchor="generator-plan"; attribute :>> obligationId="admission-protocol"; }
part route3:RouteRow { attribute :>> component="entry-admission"; attribute :>> actionName="sfun_admission_refusal.reserveGuard"; attribute :>> lemma="SfunAdmission.reserveGuardPreserves"; attribute :>> producerAnchor="generator-plan"; attribute :>> obligationId="admission-protocol"; }
part route4:RouteRow { attribute :>> component="native-return"; attribute :>> actionName="sfun_admission_refusal.ackHandoff"; attribute :>> lemma="SfunAdmission.ackHandoffPreserves"; attribute :>> producerAnchor="rc-source-read"; attribute :>> obligationId="admission-protocol"; }
part route5:RouteRow { attribute :>> component="native-return"; attribute :>> actionName="sfun_admission_refusal.cancelBeforeAck"; attribute :>> lemma="SfunAdmission.cancelBeforeAckPreserves"; attribute :>> producerAnchor="on-throw"; attribute :>> obligationId="admission-protocol"; }
part route6:RouteRow { attribute :>> component="native-return"; attribute :>> actionName="sfun_admission_refusal.allocateMarker"; attribute :>> lemma="SfunAdmission.allocateMarkerPreserves"; attribute :>> producerAnchor="marker-rooted"; attribute :>> obligationId="admission-protocol"; }
part route7:RouteRow { attribute :>> component="native-return"; attribute :>> actionName="sfun_admission_refusal.markerFailure"; attribute :>> lemma="SfunAdmission.markerFailurePreserves"; attribute :>> producerAnchor="marker-rooted"; attribute :>> obligationId="admission-protocol"; }
part route8:RouteRow { attribute :>> component="native-return"; attribute :>> actionName="sfun_admission_refusal.beginBody"; attribute :>> lemma="SfunAdmission.beginBodyPreserves"; attribute :>> producerAnchor="call-entry"; attribute :>> obligationId="admission-protocol"; }
part route9:RouteRow { attribute :>> component="native-return"; attribute :>> actionName="sfun_admission_refusal.conversionFailure"; attribute :>> lemma="SfunAdmission.conversionFailurePreserves"; attribute :>> producerAnchor="generator-plan"; attribute :>> obligationId="admission-protocol"; }
part route10:RouteRow { attribute :>> component="native-return"; attribute :>> actionName="sfun_admission_refusal.opaqueConversionFailure"; attribute :>> lemma="SfunAdmission.opaqueConversionFailurePreserves"; attribute :>> producerAnchor="generator-plan"; attribute :>> obligationId="admission-protocol"; }
part route11:RouteRow { attribute :>> component="native-return"; attribute :>> actionName="sfun_admission_refusal.finishSuccess"; attribute :>> lemma="SfunAdmission.finishSuccessPreserves"; attribute :>> producerAnchor="generator-plan"; attribute :>> obligationId="admission-protocol"; }
part route12:RouteRow { attribute :>> component="native-return"; attribute :>> actionName="sfun_admission_refusal.callRefused"; attribute :>> lemma="SfunAdmission.callRefusedPreserves"; attribute :>> producerAnchor="call-entry"; attribute :>> obligationId="admission-protocol"; }
part route13:RouteRow { attribute :>> component="native-return"; attribute :>> actionName="sfun_admission_refusal.handlerRefused"; attribute :>> lemma="SfunAdmission.handlerRefusedPreserves"; attribute :>> producerAnchor="sfun-error"; attribute :>> obligationId="admission-protocol"; }
part route14:RouteRow { attribute :>> component="native-return"; attribute :>> actionName="sfun_admission_refusal.recoverGood"; attribute :>> lemma="SfunAdmission.recoverGoodPreserves"; attribute :>> producerAnchor="sfun-error"; attribute :>> obligationId="admission-protocol"; }
part route15:RouteRow { attribute :>> component="native-return"; attribute :>> actionName="sfun_admission_refusal.recoverBad"; attribute :>> lemma="SfunAdmission.recoverBadPreserves"; attribute :>> producerAnchor="sfun-error"; attribute :>> obligationId="admission-protocol"; }
part route16:RouteRow { attribute :>> component="native-return"; attribute :>> actionName="sfun_admission_refusal.outerThrow"; attribute :>> lemma="SfunAdmission.outerThrowPreserves"; attribute :>> producerAnchor="on-throw"; attribute :>> obligationId="admission-protocol"; }
part route17:RouteRow { attribute :>> component="native-return"; attribute :>> actionName="sfun_admission_refusal.releaseMarker"; attribute :>> lemma="SfunAdmission.releaseMarkerPreserves"; attribute :>> producerAnchor="generator-plan"; attribute :>> obligationId="admission-protocol"; }
part route18:RouteRow { attribute :>> component="native-return"; attribute :>> actionName="sfun_admission_refusal.closeGuard"; attribute :>> lemma="SfunAdmission.closeGuardPreserves"; attribute :>> producerAnchor="generator-plan"; attribute :>> obligationId="admission-protocol"; }
part route19:RouteRow { attribute :>> component="native-return"; attribute :>> actionName="sfun_admission_refusal.dropRefusedSource"; attribute :>> lemma="SfunAdmission.dropRefusedSourcePreserves"; attribute :>> producerAnchor="rc-source-read"; attribute :>> obligationId="admission-protocol"; }
part route20:RouteRow { attribute :>> component="native-return"; attribute :>> actionName="sfun_admission_refusal.deliver"; attribute :>> lemma="SfunAdmission.deliverPreserves"; attribute :>> producerAnchor="generator-plan"; attribute :>> obligationId="admission-protocol"; }
part route21:RouteRow { attribute :>> component="entry-admission"; attribute :>> actionName="sfun_admission_refusal.closeDomain"; attribute :>> lemma="SfunAdmission.closeDomainPreserves"; attribute :>> producerAnchor="call-entry"; attribute :>> obligationId="admission-protocol"; }
part route22:RouteRow { attribute :>> component="entry-admission"; attribute :>> actionName="sfun_admission_refusal.resumeDomain"; attribute :>> lemma="SfunAdmission.resumeDomainPreserves"; attribute :>> producerAnchor="call-entry"; attribute :>> obligationId="admission-protocol"; }
part route23:RouteRow { attribute :>> component="legacy-retry"; attribute :>> actionName="sfun_admission_refusal.legacyMarkerSuccess"; attribute :>> lemma="SfunAdmission.legacyMarkerSuccessPreserves"; attribute :>> producerAnchor="sfun-error"; attribute :>> obligationId="admission-protocol"; }
part route24:RouteRow { attribute :>> component="legacy-retry"; attribute :>> actionName="sfun_admission_refusal.legacyRejectCall"; attribute :>> lemma="SfunAdmission.legacyRejectCallPreserves"; attribute :>> producerAnchor="sfun-error"; attribute :>> obligationId="admission-protocol"; }
part route25:RouteRow { attribute :>> component="legacy-retry"; attribute :>> actionName="sfun_admission_refusal.legacyErrorRetry"; attribute :>> lemma="SfunAdmission.legacyErrorRetryPreserves"; attribute :>> producerAnchor="sfun-error"; attribute :>> obligationId="admission-protocol"; }
part route26:RouteRow { attribute :>> component="legacy-retry"; attribute :>> actionName="sfun_admission_refusal.legacyMarkerFailure"; attribute :>> lemma="SfunAdmission.legacyMarkerFailurePreserves"; attribute :>> producerAnchor="sfun-error"; attribute :>> obligationId="admission-protocol"; }
part def CompositionRow { attribute key:String; attribute lemma:String; attribute source:String; attribute obligation:String; attribute boundary:String; }
part composition0:CompositionRow { attribute :>> key="closed-parent"; attribute :>> lemma="SfunAdmissionBridge.refusalMatchesClosedParent"; attribute :>> source="call-entry"; attribute :>> obligation="parent-entry-bridge"; attribute :>> boundary="predicate bridge only; no native root/value simulation"; }
part composition1:CompositionRow { attribute :>> key="open-parent"; attribute :>> lemma="SfunAdmissionBridge.admittedMatchesParent"; attribute :>> source="generator-plan"; attribute :>> obligation="parent-entry-bridge"; attribute :>> boundary="entry ticket eligibility, not actual guard issuer"; }
part composition2:CompositionRow { attribute :>> key="same-code"; attribute :>> lemma="SfunAdmissionBridge.originDistinguishesSameCode"; attribute :>> source="ctos-stage"; attribute :>> obligation="stage-discriminator"; attribute :>> boundary="same normalized UNKNOWN value can have different operation provenance"; }
part composition3:CompositionRow { attribute :>> key="legacy-loop"; attribute :>> lemma="SfunAdmission.legacyPersistentLoop"; attribute :>> source="sfun-error"; attribute :>> obligation="legacy-recurrence"; attribute :>> boundary="conditional recurrence; actual GC to SFUN callback edge unproved"; }
part def MemoryRow { attribute key:String; attribute order:String; attribute premise:String; attribute obligation:String; }
part memory0:MemoryRow { attribute :>> key="source-before-record"; attribute :>> order="source owner acquire/borrow before guard publication; receiver acquire/ACK before source release"; attribute :>> premise="metadata/marker allocation cannot substitute for source root"; attribute :>> obligation="ingress-pin-issuer"; }
part memory1:MemoryRow { attribute :>> key="admission"; attribute :>> order="C23 generation gate reserves owner ticket; short mutation lease released before allocation/___call"; attribute :>> premise="ordinary phase load is not concurrent admission reservation"; attribute :>> obligation="C23-domain-admission"; }
part memory2:MemoryRow { attribute :>> key="operation-origin"; attribute :>> order="publish operation stage to stable attempt before converter/call/recovery; preserve across landing"; attribute :>> premise="do not infer all UNKNOWN values mean entry refusal"; attribute :>> obligation="native-outcome-adapter"; }
part memory3:MemoryRow { attribute :>> key="unknown-handoff"; attribute :>> order="lookup same stable attempt; retain source and destination roots until known acknowledgement"; attribute :>> premise="new record is not permission to drop old source on lost reply"; attribute :>> obligation="guard-and-root-registration"; }
part memory4:MemoryRow { attribute :>> key="cleanup"; attribute :>> order="receiver owns escaped resources before source C frame is discarded; exact marker invalidation precedes native return"; attribute :>> premise="GC-closed cleanup retained; no synchronous retry into closed owner"; attribute :>> obligation="landing-and-marker-closure"; }
part def GainRow { attribute key:String; attribute benefit:String; attribute cost:String; attribute condition:String; attribute refutation:String; }
part gain0:GainRow { attribute :>> key="pre-refusal-work"; attribute :>> benefit="R rejected-before-entry calls avoid R marker attempts and all their input conversion work"; attribute :>> cost="R domain/source checks; qualified source-borrow release still required"; attribute :>> condition="rejection happens before wrapper allocation"; attribute :>> refutation="late ___call rejection has already paid marker/conversion costs"; }
part gain1:GainRow { attribute :>> key="retry-work"; attribute :>> benefit="a persistent refusal no longer causes k repeated low-level handler calls for any chosen k"; attribute :>> cost="operation-origin discriminator and native outcome adapter"; attribute :>> condition="caller outcome carries refusal separately"; attribute :>> refutation="blind UNKNOWN blacklist also suppresses legitimate custom-conversion recovery"; }
part gain2:GainRow { attribute :>> key="root-storage"; attribute :>> benefit="share source-carrier/guard/root-domain services with parent conversion protocol"; attribute :>> cost="A simultaneous entries need O(A) records; lost acknowledgements retain both roots temporarily"; attribute :>> condition="exact identity, complete root census and native exclusion qualified"; attribute :>> refutation="extra wrapper with no old-path retirement increases cost"; }
part gain3:GainRow { attribute :>> key="migration"; attribute :>> benefit="three SFUN result shapes share one stage-aware plan"; attribute :>> cost="native ABI adapters plus recompilation and descriptor lifetime accounting"; attribute :>> condition="void/SCMOBJ/typed callbacks all migrated, including Tcl error translator"; attribute :>> refutation="fixing tcltk_call alone leaves tcltk_eval_error and raw callbacks"; }
part gain4:GainRow { attribute :>> key="language"; attribute :>> benefit="C23 preserves C-friendly Gambit frontend/runtime and multi-shot Scheme semantics"; attribute :>> cost="same source roots, GC admission and unwind support remain necessary in Zig"; attribute :>> condition="modern C mainline; no second runtime needed for refusal separation"; attribute :>> refutation="no Zig-specific net benefit established"; }
part def ContractRow { attribute fromNode:String; attribute toNode:String; attribute custody:String; }
part contract0:ContractRow { attribute :>> fromNode="Native callback source"; attribute :>> toNode="Source owner borrow"; attribute :>> custody="pin actual RC/procedure/native argument lifetime without Scheme allocation"; }
part contract1:ContractRow { attribute :>> fromNode="Source owner borrow"; attribute :>> toNode="Entry admission decision"; attribute :>> custody="stage-tagged refusal before marker and converter"; }
part contract2:ContractRow { attribute :>> fromNode="Entry admission decision"; attribute :>> toNode="Native outcome adapter"; attribute :>> custody="refusal is not a conversion handler request"; }
part contract3:ContractRow { attribute :>> fromNode="Entry admission decision"; attribute :>> toNode="Registered guard root"; attribute :>> custody="accepted; initialized source/root slots; exact attempt"; }
part contract4:ContractRow { attribute :>> fromNode="Registered guard root"; attribute :>> toNode="Marker allocation"; attribute :>> custody="source ACK only after scanner-visible destination"; }
part contract5:ContractRow { attribute :>> fromNode="Marker allocation"; attribute :>> toNode="Generated SFUN call"; attribute :>> custody="marker success prerequisite; failure skips inner loop"; }
part contract6:ContractRow { attribute :>> fromNode="Generated SFUN call"; attribute :>> toNode="Conversion recovery"; attribute :>> custody="only converter-origin errors; call rejection bypasses recovery"; }
part contract7:ContractRow { attribute :>> fromNode="Generated SFUN call"; attribute :>> toNode="Stable outer landing"; attribute :>> custody="escaped marker/guard/root custody"; }
part contract8:ContractRow { attribute :>> fromNode="Conversion recovery"; attribute :>> toNode="Stable outer landing"; attribute :>> custody="nested admission refusal is terminal; no closed-domain loop"; }
part contract9:ContractRow { attribute :>> fromNode="Stable outer landing"; attribute :>> toNode="Marker and guard closure"; attribute :>> custody="retain until safe native-use closure and GC authorization"; }
part contract10:ContractRow { attribute :>> fromNode="Marker and guard closure"; attribute :>> toNode="Native outcome adapter"; attribute :>> custody="exactly-once cleanup before final native delivery"; }
part def NeedRow { attribute key:String; attribute status:String; attribute condition:String; }
part need0:NeedRow { attribute :>> key="admission-protocol"; attribute :>> status="formal"; attribute :>> condition="managed recurrence preserves preallocation root coverage and exact cleanup"; }
part need1:NeedRow { attribute :>> key="legacy-recurrence"; attribute :>> status="conditional formal"; attribute :>> condition="successful marker plus persistent non-RUNNING phase; old macro retry never reaches cleanup"; }
part need2:NeedRow { attribute :>> key="stage-discriminator"; attribute :>> status="conditional source"; attribute :>> condition="current ___call normal returns only UNKNOWN refusal or NO_ERR success; converters remain separate"; }
part need3:NeedRow { attribute :>> key="parent-entry-bridge"; attribute :>> status="formal"; attribute :>> condition="closed/open domain decisions check actual imported SizeGuardAst admission predicate"; }
part need4:NeedRow { attribute :>> key="actual-gc-sfun-edge"; attribute :>> status="unresolved"; attribute :>> condition="no audited registered releaser targets generated SFUN; do not splice unrelated examples"; }
part need5:NeedRow { attribute :>> key="ingress-pin-issuer"; attribute :>> status="unresolved"; attribute :>> condition="stable source owner/borrow before guard/marker allocation; deletion/setter/RC scan lifetime joined"; }
part need6:NeedRow { attribute :>> key="guard-and-root-registration"; attribute :>> status="unresolved"; attribute :>> condition="nonalloc stable pool, complete scanner registration and unknown handoff lookup"; }
part need7:NeedRow { attribute :>> key="C23-domain-admission"; attribute :>> status="unresolved"; attribute :>> condition="admission ticket vs short root lease, freeze synchronization and owner generation"; }
part need8:NeedRow { attribute :>> key="native-outcome-adapter"; attribute :>> status="unresolved"; attribute :>> condition="void/typed legacy ABI has no refusal result channel; checked adapter/catcher policy required"; }
part need9:NeedRow { attribute :>> key="landing-and-marker-closure"; attribute :>> status="unresolved"; attribute :>> condition="escaped subtree owns marker and guard; close return permission before native frame exits"; }
part need10:NeedRow { attribute :>> key="native-cohort-and-writers"; attribute :>> status="unresolved"; attribute :>> condition="header/generated module/call implementation and all manual writers qualified"; }
part source65:SourceRow { attribute :>> key="real-gc-drop"; attribute :>> path="vendor/gambit/tests/smp/gc/worker-root-domains.scm"; attribute :>> needle="(drop!)"; attribute :>> obligation="source driver releases the native still holds before explicit GC"; }
part source66:SourceRow { attribute :>> key="real-gc-trigger"; attribute :>> path="vendor/gambit/tests/smp/gc/worker-root-domains.scm"; attribute :>> needle="(workers! count) (##gc)"; attribute :>> obligation="source driver invokes collection; not a native execution receipt"; }
}
