package GambitNodeStorageAuthority { private import ScalarValues::*;
part def SourceRow { attribute key:String; attribute path:String; attribute needle:String; attribute limit:String; }
part source0:SourceRow { attribute :>> key="cache-list"; attribute :>> path="evidence/research/source-references/tcl/cbf86d62348d6b052e1961b4df995960fb21545f/generic/tclThreadAlloc.c"; attribute :>> needle="firstCachePtr = cachePtr;"; attribute :>> limit="visible list insertion precedes owner initialization"; }
part source1:SourceRow { attribute :>> key="cache-owner"; attribute :>> path="evidence/research/source-references/tcl/cbf86d62348d6b052e1961b4df995960fb21545f/generic/tclThreadAlloc.c"; attribute :>> needle="cachePtr->owner = Tcl_GetCurrentThread();"; attribute :>> limit="owner stored after listLockPtr unlock"; }
part source2:SourceRow { attribute :>> key="alloc-distinct"; attribute :>> path="evidence/research/source-references/tcl/cbf86d62348d6b052e1961b4df995960fb21545f/generic/tclThreadAlloc.c"; attribute :>> needle="cachePtr = TclpSysAlloc(sizeof(Cache), 0);"; attribute :>> limit="separate allocation from node chunks; allocator/provenance contract still required"; }
part source3:SourceRow { attribute :>> key="node-chunk"; attribute :>> path="evidence/research/source-references/tcl/cbf86d62348d6b052e1961b4df995960fb21545f/generic/tclThreadAlloc.c"; attribute :>> needle="newObjsPtr = TclpSysAlloc(sizeof(Tcl_Obj) * numMove, 0);"; attribute :>> limit="fresh object batch800; arbitrary later free-list order"; }
part source4:SourceRow { attribute :>> key="zero-all"; attribute :>> path="evidence/research/source-references/tcl/cbf86d62348d6b052e1961b4df995960fb21545f/generic/tclThreadAlloc.c"; attribute :>> needle="memset(cachePtr, 0, sizeof(Cache));"; attribute :>> limit="whole-object initialization writes implicit fields"; }
part source5:SourceRow { attribute :>> key="cache-layout"; attribute :>> path="evidence/research/source-references/tcl/cbf86d62348d6b052e1961b4df995960fb21545f/generic/tclThreadAlloc.c"; attribute :>> needle="typedef struct Cache {"; attribute :>> limit="private full Cache includes lastPtr and buckets"; }
part source6:SourceRow { attribute :>> key="cache-prefix"; attribute :>> path="evidence/research/source-references/tcl/cbf86d62348d6b052e1961b4df995960fb21545f/generic/tclInt.h"; attribute :>> needle="typedef struct AllocCache {"; attribute :>> limit="public prefix excludes lastPtr; common prefix is not a C23 alias proof"; }
part source7:SourceRow { attribute :>> key="object-union"; attribute :>> path="evidence/research/source-references/tcl/cbf86d62348d6b052e1961b4df995960fb21545f/generic/tcl.h"; attribute :>> needle="} internalRep;"; attribute :>> limit="free link shares union storage with alternate Tcl object roles"; }
part source8:SourceRow { attribute :>> key="put-tail"; attribute :>> path="evidence/research/source-references/tcl/cbf86d62348d6b052e1961b4df995960fb21545f/generic/tclThreadAlloc.c"; attribute :>> needle="fromPtr->lastPtr->internalRep.twoPtrValue.ptr1 = sharedPtr->firstObjPtr;"; attribute :>> limit="last target access under shared lock"; }
part source9:SourceRow { attribute :>> key="put-unlock"; attribute :>> path="evidence/research/source-references/tcl/cbf86d62348d6b052e1961b4df995960fb21545f/generic/tclThreadAlloc.c"; attribute :>> needle="Tcl_MutexUnlock(objLockPtr);"; attribute :>> limit="target read capability closed before exposing batch"; }
part source10:SourceRow { attribute :>> key="put-last"; attribute :>> path="evidence/research/source-references/tcl/cbf86d62348d6b052e1961b4df995960fb21545f/generic/tclThreadAlloc.c"; attribute :>> needle="fromPtr->lastPtr = lastPtr;"; attribute :>> limit="write cache field without target dereference"; }
part source11:SourceRow { attribute :>> key="diagnostic"; attribute :>> path="evidence/research/source-references/tcl/cbf86d62348d6b052e1961b4df995960fb21545f/generic/tclThreadAlloc.c"; attribute :>> needle="Tcl_GetMemoryInfo("; attribute :>> limit="directly reads owner, nextPtr and bucket statistics; indirect call closure open"; }
part source12:SourceRow { attribute :>> key="diagnostic-callout"; attribute :>> path="evidence/research/source-references/tcl/cbf86d62348d6b052e1961b4df995960fb21545f/generic/tclThreadAlloc.c"; attribute :>> needle="Tcl_DStringAppendElement(dsPtr, buf);"; attribute :>> limit="formatting/append target effects need separate source closure"; }
part source13:SourceRow { attribute :>> key="callback-overlay"; attribute :>> path="evidence/research/source-references/tcl/cbf86d62348d6b052e1961b4df995960fb21545f/generic/tclInt.h"; attribute :>> needle="_callbackPtr->data[3] = (ClientData)(data3);"; attribute :>> limit="NRE storage overlays Tcl_Obj; temporal role exclusion required"; }
part source14:SourceRow { attribute :>> key="callback-dispatch"; attribute :>> path="evidence/research/source-references/tcl/cbf86d62348d6b052e1961b4df995960fb21545f/generic/tclBasic.c"; attribute :>> needle="result = procPtr(callbackPtr->data, interp, result);"; attribute :>> limit="callback receives interior data-array alias before generic node free"; }
part source15:SourceRow { attribute :>> key="object-callback"; attribute :>> path="evidence/research/source-references/tcl/cbf86d62348d6b052e1961b4df995960fb21545f/generic/tcl.h"; attribute :>> needle="Tcl_FreeInternalRepProc *freeIntRepProc;"; attribute :>> limit="public type hooks can manipulate allocated object representation"; }
part source16:SourceRow { attribute :>> key="trace-hook"; attribute :>> path="evidence/research/source-references/tcl/cbf86d62348d6b052e1961b4df995960fb21545f/generic/tclInt.h"; attribute :>> needle="#define\tTCL_DTRACE_OBJ_CREATE(objPtr)\tTCL_OBJ_CREATE(objPtr)"; attribute :>> limit="enabled instrumentation provider not captured/qualified"; }
part source17:SourceRow { attribute :>> key="new-object"; attribute :>> path="evidence/research/source-references/tcl/cbf86d62348d6b052e1961b4df995960fb21545f/generic/tclInt.h"; attribute :>> needle="(objPtr)->typePtr  = NULL;"; attribute :>> limit="allocation role change is distinct from physical allocation lifetime"; }
part source18:SourceRow { attribute :>> key="cache-free"; attribute :>> path="evidence/research/source-references/tcl/cbf86d62348d6b052e1961b4df995960fb21545f/generic/tclThreadAlloc.c"; attribute :>> needle="TclpSysFree(cachePtr);"; attribute :>> limit="native cache free can enable address reuse"; }
part source19:SourceRow { attribute :>> key="tls-cleanup"; attribute :>> path="evidence/research/source-references/tcl/cbf86d62348d6b052e1961b4df995960fb21545f/generic/tclThreadAlloc.c"; attribute :>> needle="TclpFreeAllocCache(cachePtr);"; attribute :>> limit="platform TLS destructor/free ordering remains unresolved"; }
part source20:SourceRow { attribute :>> key="gambit-callback"; attribute :>> path="vendor/gambit/examples/tcltk/tcltk.scm"; attribute :>> needle="char *result = tcltk_call (___EXT(___data_rc)"; attribute :>> limit="known bridge takes RC payload and string argv, not Cache lastPtr directly"; }
part source21:SourceRow { attribute :>> key="prior"; attribute :>> path="dev/refactoring/modern-c/models/quint/putobjs_move_graph.qnt"; attribute :>> needle="action initializeTailPayload="; attribute :>> limit="actual prior tail role transition and retained source activation"; }
part def ObligationRow { attribute key:String; attribute status:String; attribute condition:String; }
part obligation0:ObligationRow { attribute :>> key="binding-safety"; attribute :>> status="conditional-model"; attribute :>> condition="stable independently lived IDs, admitted registry, closed reader set and external layout/allocator evidence"; }
part obligation1:ObligationRow { attribute :>> key="local-census"; attribute :>> status="source-bound"; attribute :>> condition="all arrow Cache.lastPtr occurrences in captured allocator file classified; whole-cache memset and macro/callback overlays listed"; }
part obligation2:ObligationRow { attribute :>> key="native-provenance"; attribute :>> status="unresolved"; attribute :>> condition="actual live allocation tickets, slot bounds, field spans, effective types and loaded C23 profile"; }
part obligation3:ObligationRow { attribute :>> key="global-readers"; attribute :>> status="unresolved"; attribute :>> condition="DTrace, Tcl object/NR callbacks, diagnostics appenders, raw extensions and platform TLS closure"; }
part obligation4:ObligationRow { attribute :>> key="registration-window"; attribute :>> status="unresolved"; attribute :>> condition="raw GetCache list publication precedes owner initialization; it cannot issue complete binding receipt"; }
part obligation5:ObligationRow { attribute :>> key="retirement"; attribute :>> status="unresolved"; attribute :>> condition="source cache cleanup plus leases/unknown outcomes and independent record lifetime; no generation wrap"; }
part obligation6:ObligationRow { attribute :>> key="full-refinement"; attribute :>> status="unresolved"; attribute :>> condition="external native mapping witness and parent-product/control-flow/mutex refinement; no native execution qualification"; }
part def RouteRow { attribute actionName:String; attribute lemma:String; attribute source:String; attribute obligation:String; }
part route0:RouteRow { attribute :>> actionName="publishRawList"; attribute :>> lemma="NodeStorageAuthority.publishRawListPreserves"; attribute :>> source="cache-list"; attribute :>> obligation="binding-safety"; }
part route1:RouteRow { attribute :>> actionName="initializeOwner"; attribute :>> lemma="NodeStorageAuthority.initializeOwnerPreserves"; attribute :>> source="cache-owner"; attribute :>> obligation="binding-safety"; }
part route2:RouteRow { attribute :>> actionName="attestDisjoint"; attribute :>> lemma="NodeStorageAuthority.attestDisjointPreserves"; attribute :>> source="alloc-distinct"; attribute :>> obligation="binding-safety"; }
part route3:RouteRow { attribute :>> actionName="bindNodeMap"; attribute :>> lemma="NodeStorageAuthority.bindNodeMapPreserves"; attribute :>> source="node-chunk"; attribute :>> obligation="binding-safety"; }
part route4:RouteRow { attribute :>> actionName="sealReaderClosure"; attribute :>> lemma="NodeStorageAuthority.sealReaderClosurePreserves"; attribute :>> source="prior"; attribute :>> obligation="binding-safety"; }
part route5:RouteRow { attribute :>> actionName="exposeAlias"; attribute :>> lemma="NodeStorageAuthority.exposeAliasPreserves"; attribute :>> source="callback-overlay"; attribute :>> obligation="binding-safety"; }
part route6:RouteRow { attribute :>> actionName="revokeSeal"; attribute :>> lemma="NodeStorageAuthority.revokeSealPreserves"; attribute :>> source="trace-hook"; attribute :>> obligation="binding-safety"; }
part route7:RouteRow { attribute :>> actionName="rejectAlias"; attribute :>> lemma="NodeStorageAuthority.rejectAliasPreserves"; attribute :>> source="prior"; attribute :>> obligation="binding-safety"; }
part route8:RouteRow { attribute :>> actionName="acquireMetadata"; attribute :>> lemma="NodeStorageAuthority.acquireMetadataPreserves"; attribute :>> source="diagnostic"; attribute :>> obligation="binding-safety"; }
part route9:RouteRow { attribute :>> actionName="returnMetadata"; attribute :>> lemma="NodeStorageAuthority.returnMetadataPreserves"; attribute :>> source="diagnostic"; attribute :>> obligation="binding-safety"; }
part route10:RouteRow { attribute :>> actionName="acquirePayload"; attribute :>> lemma="NodeStorageAuthority.acquirePayloadPreserves"; attribute :>> source="put-tail"; attribute :>> obligation="binding-safety"; }
part route11:RouteRow { attribute :>> actionName="returnPayload"; attribute :>> lemma="NodeStorageAuthority.returnPayloadPreserves"; attribute :>> source="put-tail"; attribute :>> obligation="binding-safety"; }
part route12:RouteRow { attribute :>> actionName="knownHandoff"; attribute :>> lemma="NodeStorageAuthority.knownHandoffPreserves"; attribute :>> source="put-unlock"; attribute :>> obligation="binding-safety"; }
part route13:RouteRow { attribute :>> actionName="unknownHandoff"; attribute :>> lemma="NodeStorageAuthority.unknownHandoffPreserves"; attribute :>> source="put-unlock"; attribute :>> obligation="binding-safety"; }
part route14:RouteRow { attribute :>> actionName="consumerAllocate"; attribute :>> lemma="NodeStorageAuthority.consumerAllocatePreserves"; attribute :>> source="new-object"; attribute :>> obligation="binding-safety"; }
part route15:RouteRow { attribute :>> actionName="fixSourceLast"; attribute :>> lemma="NodeStorageAuthority.fixSourceLastPreserves"; attribute :>> source="put-last"; attribute :>> obligation="binding-safety"; }
part route16:RouteRow { attribute :>> actionName="publishCompletion"; attribute :>> lemma="NodeStorageAuthority.publishCompletionPreserves"; attribute :>> source="prior"; attribute :>> obligation="binding-safety"; }
part route17:RouteRow { attribute :>> actionName="closeAdmission"; attribute :>> lemma="NodeStorageAuthority.closeAdmissionPreserves"; attribute :>> source="cache-free"; attribute :>> obligation="binding-safety"; }
part route18:RouteRow { attribute :>> actionName="attestCleanup"; attribute :>> lemma="NodeStorageAuthority.attestCleanupPreserves"; attribute :>> source="tls-cleanup"; attribute :>> obligation="binding-safety"; }
part route19:RouteRow { attribute :>> actionName="retireCache"; attribute :>> lemma="NodeStorageAuthority.retireCachePreserves"; attribute :>> source="cache-free"; attribute :>> obligation="binding-safety"; }
part route20:RouteRow { attribute :>> actionName="lookupOpaque"; attribute :>> lemma="NodeStorageAuthority.lookupOpaquePreserves"; attribute :>> source="prior"; attribute :>> obligation="binding-safety"; }
part route21:RouteRow { attribute :>> actionName="probeCurrentCache"; attribute :>> lemma="NodeStorageAuthority.probeCurrentCachePreserves"; attribute :>> source="diagnostic"; attribute :>> obligation="binding-safety"; }
part def GainRow { attribute key:String; attribute saved:String; attribute added:String; attribute condition:String; attribute status:String; }
part gain0:GainRow { attribute :>> key="node-map"; attribute :>> saved="reuse logical NodeId through free-list reordering and role changes; do not treat1201 nodes as one contiguous allocation"; attribute :>> added="allocation ticket/incarnation and slot table; positive metadata bytes depend on actual layout"; attribute :>> condition="valid injective table into live800-slot batches; allocator source contract qualified"; attribute :>> status="conditional"; }
part gain1:GainRow { attribute :>> key="field-footprint"; attribute :>> saved="derive cache-field/node-payload separation from disjoint live allocation regions without hardcoded offsets"; attribute :>> added="field containment, allocator separation and effective-type evidence; union overlay remains intentionally overlapping"; attribute :>> condition="symbolic subfield disjointness proof; native spans unresolved"; attribute :>> status="conditional-model"; }
part gain2:GainRow { attribute :>> key="diagnostic"; attribute :>> saved="known Tcl_GetMemoryInfo has no direct object-tail dereference, so no reason to pin transferred tail for those direct fields"; attribute :>> added="cache metadata lease and owner-ready view; DString/provider callouts remain open"; attribute :>> condition="complete diagnostic caller closure before admission"; attribute :>> status="source-bound/conditional"; }
part gain3:GainRow { attribute :>> key="opaque-query"; attribute :>> saved="stable ID lookup can outlive cache reuse without reading stale pointer target"; attribute :>> added="independent record lifetime, allocation/source generation tracking and lookup service"; attribute :>> condition="process-lived record witness; record compaction/reuse not proved"; attribute :>> status="conditional-model"; }
part gain4:GainRow { attribute :>> key="global-gain"; attribute :>> saved="potentially retire raw address based validation only after complete binding and caller qualification"; attribute :>> added="lease/gate traffic and alias rejection; no reduction of prior2001 link reads; old retired0"; attribute :>> condition="global native evidence incomplete; no measured speedup or Zig-specific gain"; attribute :>> status="unresolved"; }
part def IssuerRow { attribute key:String; attribute source:String; attribute signature:String; attribute gap:String; }
part issuer0:IssuerRow { attribute :>> key="allocation-owner"; attribute :>> source="node-chunk"; attribute :>> signature="allocation success, fresh storage incarnation, live chunk and valid slot before publication"; attribute :>> gap="current Tcl allocator has no installed stable ticket/node table"; }
part issuer1:IssuerRow { attribute :>> key="binding-owner"; attribute :>> source="cache-owner"; attribute :>> signature="owner initialized plus layout/provenance and generation-bound map before native lookup"; attribute :>> gap="raw list insertion occurs earlier; cannot reuse it as this receipt"; }
part issuer2:IssuerRow { attribute :>> key="reader-owner"; attribute :>> source="callback-dispatch"; attribute :>> signature="all reader/writer roles registered and escaping callback aliases refused or independently transferred"; attribute :>> gap="arbitrary native callbacks cannot be certified by a textual grep"; }
part issuer3:IssuerRow { attribute :>> key="retire-owner"; attribute :>> source="tls-cleanup"; attribute :>> signature="known source completion, admission closed, all native metadata/payload leases detached and actual cleanup complete"; attribute :>> gap="TLS/provider and persistent record lifetime remain separate"; }
part def ConsumerRow { attribute key:String; attribute source:String; attribute access:String; attribute lifetime:String; attribute limit:String; }
part consumer0:ConsumerRow { attribute :>> key="cache-last"; attribute :>> source="put-last"; attribute :>> access="store retained pointer into Cache.lastPtr only"; attribute :>> lifetime="source cache allocation and actual struct field"; attribute :>> limit="not a payload release/barrier on prior target"; }
part consumer1:ConsumerRow { attribute :>> key="diagnostics"; attribute :>> source="diagnostic"; attribute :>> access="listLockPtr, Cache.owner/nextPtr and bucket counters plus DString calls"; attribute :>> lifetime="cache metadata and actual callout closure"; attribute :>> limit="no direct tail target read; indirect allocation/instrumentation unresolved"; }
part consumer2:ConsumerRow { attribute :>> key="nr-callback"; attribute :>> source="callback-dispatch"; attribute :>> access="procPtr receives callbackPtr->data interior pointer"; attribute :>> lifetime="borrowed callback node/data during admitted call"; attribute :>> limit="possible raw copy is not permission to use pointer after generic free"; }
part consumer3:ConsumerRow { attribute :>> key="object-hooks"; attribute :>> source="object-callback"; attribute :>> access="allocated Tcl_Obj representation and type callbacks"; attribute :>> lifetime="allocated object role"; attribute :>> limit="union fields overlap; old free-list observer has no lease"; }
part consumer4:ConsumerRow { attribute :>> key="gambit-string-bridge"; attribute :>> source="gambit-callback"; attribute :>> access="RC vector via data_rc, string argv and result handoff"; attribute :>> lifetime="existing RC/string contracts"; attribute :>> limit="no direct Cache pointer supplied here; indirect Scheme/Tcl evaluation remains open"; }
part consumer5:ConsumerRow { attribute :>> key="late-lookup"; attribute :>> source="prior"; attribute :>> access="stable key and slot/incarnation metadata, no old C pointer dereference"; attribute :>> lifetime="independent record service"; attribute :>> limit="raw address equality does not reacquire storage authority"; }
part def EdgeRow { attribute fromNode:String; attribute toNode:String; attribute contract:String; }
part edge0:EdgeRow { attribute :>> fromNode="Native cache /800-object allocation"; attribute :>> toNode="Stable storage keys"; attribute :>> contract="allocation/incarnation plus slot; no NodeId-to-address arithmetic"; }
part edge1:EdgeRow { attribute :>> fromNode="Raw list publication"; attribute :>> toNode="Owner initialization"; attribute :>> contract="actual source order; incomplete publication is not complete binding"; }
part edge2:EdgeRow { attribute :>> fromNode="Stable storage keys"; attribute :>> toNode="Qualified binding view"; attribute :>> contract="owner ready, live spans, injective mapping and field containment"; }
part edge3:EdgeRow { attribute :>> fromNode="Qualified binding view"; attribute :>> toNode="Reader closure seal"; attribute :>> contract="direct census plus callbacks/instrumentation/platform scope"; }
part edge4:EdgeRow { attribute :>> fromNode="Reader closure seal"; attribute :>> toNode="Native target handoff"; attribute :>> contract="payload leases settled; old target read authority closes"; }
part edge5:EdgeRow { attribute :>> fromNode="Native target handoff"; attribute :>> toNode="Allocated object role"; attribute :>> contract="node storage incarnation unchanged; union role changes"; }
part edge6:EdgeRow { attribute :>> fromNode="Unknown handoff"; attribute :>> toNode="Stable source owner"; attribute :>> contract="retain cache and return-domain duty; consumer progress is not source completion"; }
part edge7:EdgeRow { attribute :>> fromNode="Source completion"; attribute :>> toNode="Close metadata admission"; attribute :>> contract="existing leases drain; native cleanup has independent receipt"; }
part edge8:EdgeRow { attribute :>> fromNode="Close metadata admission"; attribute :>> toNode="Fresh cache incarnation"; attribute :>> contract="same address can be reused; old query key rejected"; }
part edge9:EdgeRow { attribute :>> fromNode="Fresh cache incarnation"; attribute :>> toNode="Opaque record lookup"; attribute :>> contract="record service can answer without touching old/new native cache"; }
part def RefinementRow { attribute key:String; attribute lemma:String; attribute source:String; attribute premise:String; }
part refinement0:RefinementRow { attribute :>> key="field-separation"; attribute :>> lemma="NodeStorageAuthority.subfieldsApart"; attribute :>> source="alloc-distinct"; attribute :>> premise="both fields contained in disjoint live allocation regions; no numeric ABI invented"; }
part refinement1:RefinementRow { attribute :>> key="union-overlap"; attribute :>> lemma="NodeStorageAuthority.unionRoleNotApart"; attribute :>> source="object-union"; attribute :>> premise="same nonempty byte span cannot be disjoint; different role names do not change this"; }
part refinement2:RefinementRow { attribute :>> key="allocation-key"; attribute :>> lemma="NodeStorageAuthority.freshIncarnation"; attribute :>> source="cache-free"; attribute :>> premise="stable incarnation differs even when storage address is reused"; }
part refinement3:RefinementRow { attribute :>> key="node-injection"; attribute :>> lemma="NodeStorageAuthority.bindingIdentity"; attribute :>> source="node-chunk"; attribute :>> premise="injective NodeId to allocation-key/slot mapping is external admission evidence"; }
part refinement4:RefinementRow { attribute :>> key="native-edge"; attribute :>> lemma="NodeStorageAuthority.walkToNative"; attribute :>> source="prior"; attribute :>> premise="prior canonical graph and NativeRel injective binding/edge witness, valid cursor"; }
part refinement5:RefinementRow { attribute :>> key="raw-list"; attribute :>> lemma="NodeStorageAuthority.rawListNotBinding"; attribute :>> source="cache-list"; attribute :>> premise="raw list visible while owner still uninitialized; managed lookup gate remains closed"; }
part refinement6:RefinementRow { attribute :>> key="role-authority"; attribute :>> lemma="NodeStorageAuthority.postHandoffNoPayload"; attribute :>> source="put-unlock"; attribute :>> premise="metadata hold is distinct from transferred target read authority"; }
part refinement7:RefinementRow { attribute :>> key="record-lifetime"; attribute :>> lemma="NodeStorageAuthority.opaqueRecordSurvivesCache"; attribute :>> source="prior"; attribute :>> premise="independent never-reused record; opaque lookup does not dereference retired cache"; }
part def WriterRow { attribute key:String; attribute source:String; attribute access:String; attribute closure:String; attribute limit:String; }
part writer0:WriterRow { attribute :>> key="cache-init"; attribute :>> source="zero-all"; attribute :>> access="whole Cache memset then owner/list/TLS writes"; attribute :>> closure="captured function"; attribute :>> limit="publication ordering and platform TLS calls not closed"; }
part writer1:WriterRow { attribute :>> key="object-refill"; attribute :>> source="node-chunk"; attribute :>> access="TclThreadAllocObj writes Cache.lastPtr and object chunk links"; attribute :>> closure="captured function"; attribute :>> limit="allocator and panic/provider effects open"; }
part writer2:WriterRow { attribute :>> key="empty-return"; attribute :>> source="put-tail"; attribute :>> access="TclThreadFreeObj sets lastPtr for previously empty cache"; attribute :>> closure="captured function"; attribute :>> limit="selected allocator profile required"; }
part writer3:WriterRow { attribute :>> key="move"; attribute :>> source="put-last"; attribute :>> access="MoveObjs destination lastPtr plus node tail link; PutObjs old-tail read/final field write"; attribute :>> closure="captured functions"; attribute :>> limit="cross-thread/context and global reader admission not established"; }
part writer4:WriterRow { attribute :>> key="diagnostic"; attribute :>> source="diagnostic"; attribute :>> access="owner/list/bucket reads; no Cache.lastPtr target access in this body"; attribute :>> closure="direct body only"; attribute :>> limit="DString/format/provider indirect closure unresolved"; }
part writer5:WriterRow { attribute :>> key="overlay"; attribute :>> source="callback-overlay"; attribute :>> access="NRE proc/data/next fields reuse Tcl_Obj-sized memory"; attribute :>> closure="macro and dispatch body"; attribute :>> limit="interior callback alias escape and all registered procs unresolved"; }
part writer6:WriterRow { attribute :>> key="object-role"; attribute :>> source="object-callback"; attribute :>> access="TclNewObj field writes and public Tcl_ObjType callbacks"; attribute :>> closure="declarations/macros"; attribute :>> limit="all user-defined type implementations and trace hooks unresolved"; }
part writer7:WriterRow { attribute :>> key="free"; attribute :>> source="cache-free"; attribute :>> access="TclFreeAllocCache flush/unlink/native free"; attribute :>> closure="direct body only"; attribute :>> limit="keep0/bucket/TLS destructor and generation closure unresolved"; }
}
