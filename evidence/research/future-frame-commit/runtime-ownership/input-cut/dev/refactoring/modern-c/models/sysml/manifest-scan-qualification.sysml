package GambitManifestScanQualification { private import ScalarValues::*;
part def Route { attribute key:String; attribute sourcePath:String; attribute needle:String; attribute obligation:String; }
part route0:Route { attribute :>> key="current-request-root"; attribute :>> sourcePath="vendor/gambit/lib/mem.c"; attribute :>> needle="mark_array (work, &___vms->resize.thunk, 1);"; attribute :>> obligation="Existing VM thunk root is scanned by worker zero; preserve constrained baseline"; }
part route1:Route { attribute :>> key="current-startup-root"; attribute :>> sourcePath="vendor/gambit/lib/mem.c"; attribute :>> needle="mark_array (work, &context->startup_thunk, 1);"; attribute :>> obligation="Current context startup slot is already updateable GC input"; }
part route2:Route { attribute :>> key="reload-after-sync"; attribute :>> sourcePath="vendor/gambit/lib/setup.c"; attribute :>> needle="___run_and_throw_error_on_processor_0 (___PSP ___ps->context->startup_thunk);"; attribute :>> obligation="Current child reloads after sync rather than retaining pre-sync raw local"; }
part route3:Route { attribute :>> key="park-before-entry"; attribute :>> sourcePath="vendor/gambit/lib/setup.c"; attribute :>> needle="while (slot->entry == 0)"; attribute :>> obligation="Created child waits on native gate before TLS or Scheme/context use"; }
part route4:Route { attribute :>> key="gc-phase-admission"; attribute :>> sourcePath="vendor/gambit/lib/mem.c"; attribute :>> needle="___vms->resize.phase != ___RESIZE_REQUESTED"; attribute :>> obligation="Current GC rejects most in-progress resize phases; manifest generalization changes admissible schedules"; }
part route5:Route { attribute :>> key="created-members-custody"; attribute :>> sourcePath="vendor/gambit/lib/setup.c"; attribute :>> needle="r->slots[i].phase = ___RESIZE_SLOT_RETAINED;"; attribute :>> obligation="Failed join retains member; do not inherit ignored-join claim"; }
part route6:Route { attribute :>> key="abort-only-isolation"; attribute :>> sourcePath="vendor/gambit/lib/mem.c"; attribute :>> needle="___BOOL ___isolate_aborted_resize"; attribute :>> obligation="Irrevocable abort can exclude future Scheme/context use without proving thread death"; }
part route7:Route { attribute :>> key="retained-request-root"; attribute :>> sourcePath="vendor/gambit/lib/mem.c"; attribute :>> needle="The request thunk remains a VM root scanned by worker 0."; attribute :>> obligation="Abort-isolated GC may proceed while native identity remains quarantined"; }
part route8:Route { attribute :>> key="actual-scanner-closure"; attribute :>> sourcePath="vendor/gambit/lib/mem.c"; attribute :>> needle="mark_reachable_from_marked (work);"; attribute :>> obligation="New root scan work and derived chunks must settle before termination"; }
part route9:Route { attribute :>> key="worker-view-drain"; attribute :>> sourcePath="vendor/gambit/lib/mem.c"; attribute :>> needle="BARRIER(); /* no worker may retain a stopped root view past this cut */"; attribute :>> obligation="Captured directory/slot views survive until complete worker drain"; }
part route10:Route { attribute :>> key="cohort-count-commit"; attribute :>> sourcePath="vendor/gambit/lib/setup.c"; attribute :>> needle="r->phase = ___RESIZE_COMMITTED;"; attribute :>> obligation="Current code commits new count before granting entry permission"; }
part route11:Route { attribute :>> key="parent-adoption-action"; attribute :>> sourcePath="dev/refactoring/modern-c/models/quint/pending_start_composition.qnt"; attribute :>> needle="action adoptA="; attribute :>> obligation="Selected ready-cohort theorem targets actual predecessor adoption expression"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule5; ref part :>> counterpart=GambitRuntimeComposition::blueprintModule3; attribute :>> key="qualified-baseline"; attribute :>> owner="control/roots"; attribute :>> actionName="park create commit reload"; attribute :>> invariant="Reuse existing VM request root context startup root and abort quarantine"; attribute :>> gap="No claim that broad manifest improves current serialized transaction without workload evidence"; }
part contract1:Contract { ref part :>> accountable=GambitRuntimeComposition::blueprintModule4; ref part :>> counterpart=GambitRuntimeComposition::blueprintModule3; attribute :>> key="canonical-partition"; attribute :>> owner="collector/roots"; attribute :>> actionName="freeze scan0 scan1 scan2"; attribute :>> invariant="Every canonical admitted slot has exactly one assigned authorized worker"; attribute :>> gap="Slot identity injectivity and real enumeration are separate premises from modulo arithmetic"; }
part contract2:Contract { ref part :>> accountable=GambitRuntimeComposition::blueprintModule4; ref part :>> counterpart=GambitRuntimeComposition::blueprintModule5; attribute :>> key="producer-closure"; attribute :>> owner="collector/control"; attribute :>> actionName="closeIngress park0 park1 drain"; attribute :>> invariant="Root visits derived debt and producer admission close before worker drain"; attribute :>> gap="Finite one-debt model does not prove real forwarding chunk weak or foreign closure"; }
part contract3:Contract { ref part :>> accountable=GambitRuntimeComposition::blueprintModule7; ref part :>> counterpart=GambitRuntimeComposition::blueprintModule1; attribute :>> key="isolation-not-free"; attribute :>> owner="release/native"; attribute :>> actionName="abortUnknownB retireB"; attribute :>> invariant="Abort-isolated native records may remain live even when Scheme context is detached"; attribute :>> gap="Irrevocable abort is not join and never grants gate/PSTATE/VM physical free"; }
part contract4:Contract { ref part :>> accountable=GambitRuntimeComposition::blueprintModule2; ref part :>> counterpart=GambitRuntimeComposition::blueprintModule3; attribute :>> key="ready-cohort-reuse"; attribute :>> owner="execution/roots"; attribute :>> actionName="adoptA"; attribute :>> invariant="Qualified ready cohort implies predecessor adoption guard and root-preserving step"; attribute :>> gap="Native current entry gate refinement generation and roster agreement remain open"; }
part contract5:Contract { ref part :>> accountable=GambitRuntimeComposition::blueprintModule8; ref part :>> counterpart=GambitRuntimeComposition::blueprintModule0; attribute :>> key="source-identity"; attribute :>> owner="build/semantic"; attribute :>> actionName="scan0 drain retireB adoptA"; attribute :>> invariant="Actual new and predecessor expression certificates with exact source scopes"; attribute :>> gap="Full current source C11 and all-action simulation stay unqualified"; }
part def Obligation { attribute key:String; attribute status:String; attribute scope:String; attribute counterexample:String; }
part obligation0:Obligation { attribute :>> key="finite-manifest"; attribute :>> status="bounded-checked"; attribute :>> scope="Three slots two workers root visit counts debt closure and captured view leases"; attribute :>> counterexample="Missing slot double scan residual work or retiring captured storage violates safety"; }
part obligation1:Obligation { attribute :>> key="partition-algebra"; attribute :>> status="conditional-proved"; attribute :>> scope="For positive W each admitted index has exactly one i mod W owner"; attribute :>> counterexample="Physical RootSlotId injection and exact enumeration remain assumed"; }
part obligation2:Obligation { attribute :>> key="drain-guards"; attribute :>> status="conditional-proved"; attribute :>> scope="Debt and missing slot block drain; captured view blocks physical retirement"; attribute :>> counterexample="Actual debt is not a scalar unless every derived producer is refined"; }
part obligation3:Obligation { attribute :>> key="quarantine-boundary"; attribute :>> status="conditional-proved"; attribute :>> scope="No known join/reject or quarantine permits native retirement"; attribute :>> counterexample="Abort excludes a class of future access but does not prove physical stop"; }
part obligation4:Obligation { attribute :>> key="actual-expressions"; attribute :>> status="conditional-proved"; attribute :>> scope="Actual scan0 drain retireB and predecessor adoptA meanings"; attribute :>> counterexample="Generated code parser remains trusted; fixed assignment is not generic code proof"; }
part obligation5:Obligation { attribute :>> key="runtime-source"; attribute :>> status="open"; attribute :>> scope="Current serialized ledger policy generalized manifests canonical dedup C11 and entry receipts"; attribute :>> counterexample="All old source claims must be checked against current pinned revision"; }
part obligation6:Obligation { attribute :>> key="finite-json"; attribute :>> status="partially-proved"; attribute :>> scope="91-row environment and separate model expression inputs"; attribute :>> counterexample="No verified JSON parser or compiler root extraction"; }
part def Gain { attribute key:String; attribute avoided:String; attribute added:String; attribute condition:String; }
part gain0:Gain { attribute :>> key="reuse-existing-roots"; attribute :>> avoided="Unnecessary generic pending directory for the single serialized resize request"; attribute :>> added="Keep existing one request root and per-context startup slot adapters"; attribute :>> condition="General registry only justified by independently admitted concurrent services"; }
part gain1:Gain { attribute :>> key="partition-balance"; attribute :>> avoided="Mandatory serial N-root enumeration in a generalized design"; attribute :>> added="O(N) snapshot enumeration and W-worker assignment; ideal max ceil(N/W) root visits"; attribute :>> condition="Distinct uniform slots complete assignment; recursive work skew and barriers can dominate"; }
part gain2:Gain { attribute :>> key="closed-producer"; attribute :>> avoided="Repeated rescans caused by premature empty or worker-idle declarations"; attribute :>> added="Root producer cut derived-work debt and termination evidence"; attribute :>> condition="All actual producer sources covered; no measured throughput improvement"; }
part gain3:Gain { attribute :>> key="isolation-memory"; attribute :>> avoided="Some empty execution heap claims can be detached while unknown OS joins remain"; attribute :>> added="Native records descriptors gate and request-root retention remain"; attribute :>> condition="Current abort isolation preconditions qualified; not a physical-capacity refund"; }
part gain4:Gain { attribute :>> key="modern-c-worth"; attribute :>> avoided="Second language not needed for root directory partition or cohort receipts"; attribute :>> added="Modern C atomic protocols generated maps and source qualification"; attribute :>> condition="Zig does not discharge canonical identity or readiness proof obligations"; }
part def Binding { attribute key:String; attribute qntAction:String; attribute leanLemma:String; attribute refinement:String; attribute guardLemma:String; attribute updateLemma:String; }
part binding0:Binding { attribute :>> key="guard"; attribute :>> qntAction="scan0"; attribute :>> leanLemma="noFrozenRejectsScan"; attribute :>> refinement="Selected expression checked; current source relation open"; attribute :>> guardLemma="scan0GuardMeaning"; attribute :>> updateLemma="scan0NextMeaning"; }
part binding1:Binding { attribute :>> key="roots"; attribute :>> qntAction="drain"; attribute :>> leanLemma="debtBlocksDrain"; attribute :>> refinement="Selected expression checked; current source relation open"; attribute :>> guardLemma="drainGuardMeaning"; attribute :>> updateLemma="drainNextMeaning"; }
part binding2:Binding { attribute :>> key="release"; attribute :>> qntAction="retireB"; attribute :>> leanLemma="capturedBlocksRetire"; attribute :>> refinement="Selected expression checked; current source relation open"; attribute :>> guardLemma="retireBGuardMeaning"; attribute :>> updateLemma="retireBNextMeaning"; }
part def Flow { attribute fromNode:String; attribute toNode:String; attribute reason:String; }
part flow0:Flow { attribute :>> fromNode="c0"; attribute :>> toNode="c1"; attribute :>> reason="Generalize only beyond qualified current baseline"; }
part flow1:Flow { attribute :>> fromNode="c1"; attribute :>> toNode="c2"; attribute :>> reason="Root assignment contributes producer work"; }
part flow2:Flow { attribute :>> fromNode="c2"; attribute :>> toNode="c3"; attribute :>> reason="Drain Scheme scans before storage classification"; }
part flow3:Flow { attribute :>> fromNode="c4"; attribute :>> toNode="c5"; attribute :>> reason="Prior adoption expression is checked"; }
part flow4:Flow { attribute :>> fromNode="c1"; attribute :>> toNode="o0"; attribute :>> reason="Finite count coverage"; }
part flow5:Flow { attribute :>> fromNode="c1"; attribute :>> toNode="o1"; attribute :>> reason="Total and unique arithmetic owner"; }
part flow6:Flow { attribute :>> fromNode="c2"; attribute :>> toNode="o2"; attribute :>> reason="Debt and missing slot guards"; }
part flow7:Flow { attribute :>> fromNode="c3"; attribute :>> toNode="o3"; attribute :>> reason="Abort is not physical stop"; }
part flow8:Flow { attribute :>> fromNode="c5"; attribute :>> toNode="o4"; attribute :>> reason="Actual typed IR expressions"; }
part flow9:Flow { attribute :>> fromNode="c5"; attribute :>> toNode="o6"; attribute :>> reason="Finite reference witness"; }
part flow10:Flow { attribute :>> fromNode="c0"; attribute :>> toNode="o5"; attribute :>> reason="Current source differs from predecessor"; }
part flow11:Flow { attribute :>> fromNode="c2"; attribute :>> toNode="o5"; attribute :>> reason="Real copying and chunk closure remains open"; }
part history:GambitAssuranceRouting::ModelNeed { ref part :>> owner=GambitBuildAssurance::planner.component; attribute :>> obligationId="MQ-H"; attribute :>> kind="interleaving"; attribute :>> subjectPath="dev/refactoring/modern-c/models/quint/manifest_scan_cut.qnt"; attribute :>> subjectScope="Three slots two workers captured views root visits and one derived debt"; attribute :>> premise="Bounded models and restricted algebra only; no runtime implementation or native acceptance"; }
part shards:GambitAssuranceRouting::ModelNeed { ref part :>> owner=GambitBuildAssurance::planner.component; attribute :>> obligationId="MQ-B"; attribute :>> kind="interleaving"; attribute :>> subjectPath="dev/refactoring/modern-c/models/quint/pending_start_composition.qnt"; attribute :>> subjectScope="Prior two-member pending/context model with selected actual adoption expression"; attribute :>> premise="Bounded models and restricted algebra only; no runtime implementation or native acceptance"; }
part induction:GambitAssuranceRouting::ModelNeed { ref part :>> owner=GambitBuildAssurance::planner.component; attribute :>> obligationId="MQ-I"; attribute :>> kind="induction"; attribute :>> subjectPath="dev/refactoring/modern-c/models/lean/ManifestScanQualification.lean"; attribute :>> subjectScope="Unbounded index partition algebra guard exclusion ready cohort implication and inherited root preservation"; attribute :>> premise="Bounded models and restricted algebra only; no runtime implementation or native acceptance"; }
part expression:GambitAssuranceRouting::ModelNeed { ref part :>> owner=GambitBuildAssurance::planner.component; attribute :>> obligationId="MQ-X"; attribute :>> kind="induction"; attribute :>> subjectPath="dev/refactoring/modern-c/models/lean/ManifestScanAst.lean"; attribute :>> subjectScope="Actual scan0 drain retireB and finite JSON reference witness"; attribute :>> premise="Bounded models and restricted algebra only; no runtime implementation or native acceptance"; }
part source:GambitAssuranceRouting::ModelNeed { ref part :>> owner=GambitBuildAssurance::planner.component; attribute :>> obligationId="MQ-S"; attribute :>> kind="source-refinement"; attribute :>> subjectPath="dev/refactoring/modern-c/manifest-scan-qualification-design.org"; attribute :>> subjectScope="Current resize roots serialized GC exclusion abort isolation and generic manifest bridge OPEN"; attribute :>> premise="Bounded models and restricted algebra only; no runtime implementation or native acceptance"; }
part platform:GambitAssuranceRouting::ModelNeed { ref part :>> owner=GambitBuildAssurance::planner.component; attribute :>> obligationId="MQ-E"; attribute :>> kind="environment-refinement"; attribute :>> subjectPath="dev/refactoring/modern-c/manifest-scan-qualification-design.org"; attribute :>> subjectScope="C11 root assignment worker debt closure gate generations and physical lifetime OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitPendingStartComposition::source; }
part dependency4:GambitAssuranceRouting::NeedDependency { ref part :>> dependent=source; ref part :>> prerequisite=expression; }
part dependency5:GambitAssuranceRouting::NeedDependency { ref part :>> dependent=source; ref part :>> prerequisite=shards; }
part def Endorsement { attribute roleName:String; attribute scope:String; attribute issuer:String; attribute sourcePath:String; attribute needle:String; }
part endorsement0:Endorsement { attribute :>> roleName="semantic"; attribute :>> scope="Canonical root identity and assigned scan closure are complete"; attribute :>> issuer="Root provider owner"; attribute :>> sourcePath="vendor/gambit/lib/mem.c"; attribute :>> needle="mark_array (work, &context->startup_thunk, 1);"; }
part endorsement1:Endorsement { attribute :>> roleName="foreign"; attribute :>> scope="Known created join or irrevocable abort scopes match native access"; attribute :>> issuer="Resize/thread lifecycle owner"; attribute :>> sourcePath="vendor/gambit/lib/mem.c"; attribute :>> needle="___BOOL ___isolate_aborted_resize"; }
part endorsement2:Endorsement { attribute :>> roleName="resident"; attribute :>> scope="Old immutable manifest views drain before directory or context reclaim"; attribute :>> issuer="VM and GC coordinator"; attribute :>> sourcePath="vendor/gambit/lib/mem.c"; attribute :>> needle="BARRIER(); /* no worker may retain a stopped root view past this cut */"; }
part flow12:Flow { attribute :>> fromNode="c4"; attribute :>> toNode="o5"; attribute :>> reason="Actual readiness generation relation needed"; }
part flow13:Flow { attribute :>> fromNode="c3"; attribute :>> toNode="o5"; attribute :>> reason="Quarantined native gate remains resident"; }
part flow14:Flow { attribute :>> fromNode="c4"; attribute :>> toNode="o1"; attribute :>> reason="Canonical identity is independent of owner"; }
part flow15:Flow { attribute :>> fromNode="o4"; attribute :>> toNode="o5"; attribute :>> reason="Local meaning is not C11 implementation proof"; }
part def Composition { attribute key:String; attribute lemma:String; attribute certificate:String; }
part composition0:Composition { attribute :>> key="ready-square"; attribute :>> lemma="readyAdoptionKeepsRoot"; attribute :>> certificate="adoptANextMeaning"; }
part composition1:Composition { attribute :>> key="partition-total"; attribute :>> lemma="partitionTotal"; attribute :>> certificate="scan0GuardMeaning"; }
part composition2:Composition { attribute :>> key="partition-unique"; attribute :>> lemma="partitionUnique"; attribute :>> certificate="scan0NextMeaning"; }
part startupExpression:GambitAssuranceRouting::ModelNeed { ref part :>> owner=GambitBuildAssurance::planner.component; attribute :>> obligationId="MQ-Y"; attribute :>> kind="induction"; attribute :>> subjectPath="dev/refactoring/modern-c/models/lean/ManifestCohortAst.lean"; attribute :>> subjectScope="Actual predecessor adoptA guard and update certificate"; attribute :>> premise="Restricted JSON parser and emitter remain trusted; no full simulation"; }
part dependency6:GambitAssuranceRouting::NeedDependency { ref part :>> dependent=source; ref part :>> prerequisite=startupExpression; }
}
