package GambitTclSourceBorrow { private import ScalarValues::*;
part def SourceRow { attribute key:String; attribute path:String; attribute needle:String; attribute obligation:String; }
part source0:SourceRow { attribute :>> key="catcher"; attribute :>> path="vendor/gambit/include/_gambit/foreign_conversion.h.in"; attribute :>> needle="___ps->catcher = &___jbuf;"; attribute :>> obligation="catcher is automatic activation, restored at END_TRY"; }
part source1:SourceRow { attribute :>> key="throw"; attribute :>> path="vendor/gambit/include/_gambit/foreign_conversion.h.in"; attribute :>> needle="#define ___THROW(e)do { ___ps->longjmp_err"; attribute :>> obligation="nonlocal jump can bypass nested local ENDs"; }
part source2:SourceRow { attribute :>> key="language-c"; attribute :>> path="vendor/gambit/include/_gambit/language.h.in"; attribute :>> needle="#define ___USE_SETJMP"; attribute :>> obligation="C path uses setjmp; no C++ RAII assumption"; }
part source3:SourceRow { attribute :>> key="call-entry"; attribute :>> path="vendor/gambit/lib/setup.c"; attribute :>> needle="___EXP_FUNC(___SCMOBJ,___call)"; attribute :>> obligation="GC phase rejection before frame writes; catcher created later"; }
part source4:SourceRow { attribute :>> key="marker-rooted"; attribute :>> path="vendor/gambit/lib/c_intf.c"; attribute :>> needle="proc_or_false = *proc_root; /* reload after allocating the marker */"; attribute :>> obligation="rooted startup endpoint reloads; generic wrapper local not registry"; }
part source5:SourceRow { attribute :>> key="marker-raw"; attribute :>> path="vendor/gambit/lib/c_intf.c"; attribute :>> needle="Legacy raw SFUN entry is not made a registered-root interface"; attribute :>> obligation="do not infer generic ingress roots"; }
part source6:SourceRow { attribute :>> key="marker-kill"; attribute :>> path="vendor/gambit/lib/c_intf.c"; attribute :>> needle="___still_obj_refcount_dec (marker);"; attribute :>> obligation="different object and native lifetime"; }
part source7:SourceRow { attribute :>> key="scan-context"; attribute :>> path="vendor/gambit/lib/_mem/root-origins.inc"; attribute :>> needle="mark_array (work, context->r, sizeof(context->r)/sizeof(*context->r));"; attribute :>> obligation="includes exact PSR1 slot"; }
part source8:SourceRow { attribute :>> key="owner-cleanup"; attribute :>> path="vendor/gambit/lib/_mem/collection-round.inc"; attribute :>> needle="vm->gc_participants[id].phase = ___GC_OWNER_CLEANUP;"; attribute :>> obligation="restored stacks do not authorize managed reentry"; }
part source9:SourceRow { attribute :>> key="darwin-config"; attribute :>> path="vendor/gambit/config.status"; attribute :>> needle="'--disable-smp'"; attribute :>> obligation="configured arm64 GCC16 subset not SMP native qualification"; }
part source10:SourceRow { attribute :>> key="width-config"; attribute :>> path="vendor/gambit/config.log"; attribute :>> needle="ac_cv_sizeof_long=8"; attribute :>> obligation="historical generated profile"; }
part source11:SourceRow { attribute :>> key="build-command"; attribute :>> path="vendor/gambit/bin/gambuild-C"; attribute :>> needle="/opt/homebrew/Cellar/gcc/16.2.0/bin/gcc-16"; attribute :>> obligation="actual recorded toolchain command"; }
part source12:SourceRow { attribute :>> key="feeley-paper"; attribute :>> path="evidence/research/sfun-converter-use-closure/feeley-sfp-paper.txt"; attribute :>> needle="return to C frames"; attribute :>> obligation="Scheme continuation extent versus C activation extent"; }
part source13:SourceRow { attribute :>> key="tcl-native-callback"; attribute :>> path="vendor/gambit/examples/tcltk/tcltk.scm"; attribute :>> needle="char *result = tcltk_call (___EXT(___data_rc)"; attribute :>> obligation="real callback loads RC payload before SFUN marker allocation"; }
part source14:SourceRow { attribute :>> key="tcl-register"; attribute :>> path="vendor/gambit/examples/tcltk/tcltk.scm"; attribute :>> needle="___result = ___BOOLEAN (Tcl_CreateCommand"; attribute :>> obligation="native command registration supplies callback and delete hooks"; }
part source15:SourceRow { attribute :>> key="tcl-export"; attribute :>> path="vendor/gambit/examples/tcltk/tcltk.scm"; attribute :>> needle="(c-define (##tcltk-call vect args)"; attribute :>> obligation="typed-result SFUN source producer"; }
part source16:SourceRow { attribute :>> key="tcl-delete"; attribute :>> path="vendor/gambit/examples/tcltk/tcltk.scm"; attribute :>> needle="___HIDDEN void scheme_delete_cmd"; attribute :>> obligation="delete hook releases payload/RC, not a Scheme invocation"; }
part source17:SourceRow { attribute :>> key="tcl-error-callback"; attribute :>> path="vendor/gambit/examples/tcltk/tcltk.scm"; attribute :>> needle="tcltk_eval_error (___CAST(char*,Tcl_GetStringResult(tcl_interp)));"; attribute :>> obligation="native error translator calls a second SFUN endpoint"; }
part source18:SourceRow { attribute :>> key="tcl-error-export"; attribute :>> path="vendor/gambit/examples/tcltk/tcltk.scm"; attribute :>> needle="(c-define (##tcltk-eval-error msg)"; attribute :>> obligation="void error callback also needs refusal policy"; }
part source19:SourceRow { attribute :>> key="tcl-source-publish"; attribute :>> path="vendor/gambit/examples/tcltk/tcltk.scm"; attribute :>> needle="___EXT(___set_data_rc) (cd, vect);"; attribute :>> obligation="STILL vector count protects payload while alive; delete requires borrow closure"; }
part source20:SourceRow { attribute :>> key="rc-source-read"; attribute :>> path="vendor/gambit/lib/_mem/rc-allocation.inc"; attribute :>> needle="___EXP_FUNC(___SCMOBJ,___data_rc)"; attribute :>> obligation="read value is not an atomic borrow or root transfer"; }
part source21:SourceRow { attribute :>> key="rc-source-write"; attribute :>> path="vendor/gambit/lib/_mem/rc-allocation.inc"; attribute :>> needle="h->data = val;"; attribute :>> obligation="public setter must join source-root writer admission"; }
part source22:SourceRow { attribute :>> key="rc-scan"; attribute :>> path="vendor/gambit/lib/_mem/rc-roots.inc"; attribute :>> needle="mark_array (work, &h->data, 1);"; attribute :>> obligation="actual context-owned RC data scanner"; }
part source23:SourceRow { attribute :>> key="rc-addref"; attribute :>> path="vendor/gambit/lib/_mem/rc-allocation.inc"; attribute :>> needle="h->refcount++;"; attribute :>> obligation="plain native RC count is not a versioned payload borrow"; }
part source24:SourceRow { attribute :>> key="rc-release"; attribute :>> path="vendor/gambit/lib/_mem/rc-allocation.inc"; attribute :>> needle="if (--h->refcount == 0)"; attribute :>> obligation="unlinks/free header at zero; separate Scheme hold"; }
part source25:SourceRow { attribute :>> key="rc-forced-cleanup"; attribute :>> path="vendor/gambit/lib/_mem/rc-allocation.inc"; attribute :>> needle="___HIDDEN void cleanup_rc"; attribute :>> obligation="forced list cleanup ignores borrower protocol; shutdown admission open"; }
part source26:SourceRow { attribute :>> key="rc-register"; attribute :>> path="vendor/gambit/lib/_mem/rc-allocation.inc"; attribute :>> needle="h->next = head;"; attribute :>> obligation="source registration mutates collector-scanned list"; }
part source27:SourceRow { attribute :>> key="rc-public-import"; attribute :>> path="vendor/gambit/include/_gambit/runtime_protocols.h.in"; attribute :>> needle="___IMP_FUNC(void,___set_data_rc)"; attribute :>> obligation="public void setter cannot report checked unknown/failure by itself"; }
part source28:SourceRow { attribute :>> key="rc-public-export"; attribute :>> path="vendor/gambit/lib/setup.c"; attribute :>> needle="___GSTATE->___set_data_rc"; attribute :>> obligation="function-table exposure; closed explicit writer census not all clients"; }
part source29:SourceRow { attribute :>> key="closure-setter"; attribute :>> path="vendor/gambit/lib/os_dyn.c"; attribute :>> needle="___set_data_rc (c_closure, proc);"; attribute :>> obligation="other explicit setter is C closure initialization"; }
part source30:SourceRow { attribute :>> key="tcl-result-transfer"; attribute :>> path="vendor/gambit/examples/tcltk/tcltk.scm"; attribute :>> needle="___CAST(Tcl_FreeProc*,___EXT(___release_string))"; attribute :>> obligation="normal result ownership transfer remains required"; }
part source31:SourceRow { attribute :>> key="native-string-free"; attribute :>> path="vendor/gambit/lib/c_intf.c"; attribute :>> needle="___EXP_FUNC(void,___release_string)"; attribute :>> obligation="normal Gambit result free calls RC release, not Scheme directly"; }
part source32:SourceRow { attribute :>> key="tcl-null-result"; attribute :>> path="vendor/gambit/examples/tcltk/tcltk.scm"; attribute :>> needle="if (result == NULL)"; attribute :>> obligation="NULL means valid empty result, not a refusal sentinel"; }
part source33:SourceRow { attribute :>> key="tcl-eval-driver"; attribute :>> path="vendor/gambit/examples/tcltk/tcltk.scm"; attribute :>> needle="else if (Tcl_Eval (tcl_interp, cmd) != TCL_OK)"; attribute :>> obligation="old native error translator invokes Scheme without origin distinction"; }
part source34:SourceRow { attribute :>> key="tcl-event-driver"; attribute :>> path="vendor/gambit/examples/tcltk/tcltk.scm"; attribute :>> needle="Tcl_DoOneEvent (TCL_DONT_WAIT)"; attribute :>> obligation="native scope producer must start before lookup/dispatch, not callback prologue"; }
part source35:SourceRow { attribute :>> key="tcl-interp-delete"; attribute :>> path="vendor/gambit/examples/tcltk/tcltk.scm"; attribute :>> needle="Tcl_DeleteInterp (tcl_interp);"; attribute :>> obligation="logical interpreter deletion and owner scope drain are distinct"; }
part source36:SourceRow { attribute :>> key="root-strong-source"; attribute :>> path="vendor/gambit/lib/_mem/root-origins.inc"; attribute :>> needle="mark_rc (work, context);"; attribute :>> obligation="reuse context-owned RC root enumeration"; }
part source37:SourceRow { attribute :>> key="foreign-release-clear"; attribute :>> path="vendor/gambit/lib/c_intf.c"; attribute :>> needle="___FOREIGN_PTR_FIELD(obj) ="; attribute :>> obligation="callback completion not inferred from clearing fields"; }
part source38:SourceRow { attribute :>> key="root-decrement"; attribute :>> path="vendor/gambit/lib/_mem/still-refcount.inc"; attribute :>> needle="___BODY0(obj)[___STILL_REFCOUNT-___STILL_BODY]--;"; attribute :>> obligation="plain Scheme still counter needs its own owner/effect receipt"; }
part source39:SourceRow { attribute :>> key="tcl-native-dispatch"; attribute :>> path="evidence/research/source-references/tcl/cbf86d62348d6b052e1961b4df995960fb21545f/generic/tclBasic.c"; attribute :>> needle="result = cmdPtr->proc(cmdPtr->clientData, interp, objc, argv);"; attribute :>> obligation="callback uses clientData; argv freed only after callback returns"; }
part source40:SourceRow { attribute :>> key="tcl-argv-release"; attribute :>> path="evidence/research/source-references/tcl/cbf86d62348d6b052e1961b4df995960fb21545f/generic/tclBasic.c"; attribute :>> needle="TclStackFree(interp, (void *) argv);"; attribute :>> obligation="borrowed argv cannot be queued after native scope without copy"; }
part source41:SourceRow { attribute :>> key="tcl-native-delete"; attribute :>> path="evidence/research/source-references/tcl/cbf86d62348d6b052e1961b4df995960fb21545f/generic/tclBasic.c"; attribute :>> needle="cmdPtr->deleteProc(cmdPtr->deleteData);"; attribute :>> obligation="application data deletion precedes final command struct release"; }
part source42:SourceRow { attribute :>> key="tcl-delete-order"; attribute :>> path="evidence/research/source-references/tcl/cbf86d62348d6b052e1961b4df995960fb21545f/generic/tclBasic.c"; attribute :>> needle="TclCleanupCommandMacro(cmdPtr);"; attribute :>> obligation="command refcount is not payload protection"; }
part source43:SourceRow { attribute :>> key="tcl-set-info"; attribute :>> path="evidence/research/source-references/tcl/cbf86d62348d6b052e1961b4df995960fb21545f/generic/tclBasic.c"; attribute :>> needle="cmdPtr->clientData = infoPtr->clientData;"; attribute :>> obligation="native command setter bypasses old logical registration owner unless managed"; }
part source44:SourceRow { attribute :>> key="tcl-set-delete"; attribute :>> path="evidence/research/source-references/tcl/cbf86d62348d6b052e1961b4df995960fb21545f/generic/tclBasic.c"; attribute :>> needle="cmdPtr->deleteData = infoPtr->deleteData;"; attribute :>> obligation="deleteData may differ from current dispatch clientData"; }
part source45:SourceRow { attribute :>> key="tcl-get-info"; attribute :>> path="evidence/research/source-references/tcl/cbf86d62348d6b052e1961b4df995960fb21545f/generic/tclBasic.c"; attribute :>> needle="infoPtr->clientData = cmdPtr->clientData;"; attribute :>> obligation="raw ClientData can escape through command info"; }
part source46:SourceRow { attribute :>> key="tcl-token-epoch"; attribute :>> path="evidence/research/source-references/tcl/cbf86d62348d6b052e1961b4df995960fb21545f/generic/tclBasic.c"; attribute :>> needle="cmdPtr->cmdEpoch++;"; attribute :>> obligation="Tcl command epoch is not VM storage/payload generation"; }
part source47:SourceRow { attribute :>> key="tcl-native-publication"; attribute :>> path="evidence/research/source-references/tcl/cbf86d62348d6b052e1961b4df995960fb21545f/generic/tclBasic.c"; attribute :>> needle="cmdPtr->deleteData = clientData;"; attribute :>> obligation="initial create binds native dispatch and delete data"; }
part source48:SourceRow { attribute :>> key="tcl-result-free-hook"; attribute :>> path="evidence/research/source-references/tcl/cbf86d62348d6b052e1961b4df995960fb21545f/generic/tclResult.c"; attribute :>> needle="oldFreeProc(oldResult);"; attribute :>> obligation="SetResult invokes prior custom free callback; record refusal before publication"; }
part source49:SourceRow { attribute :>> key="tcl-command-type"; attribute :>> path="evidence/research/source-references/tcl/cbf86d62348d6b052e1961b4df995960fb21545f/generic/tclInt.h"; attribute :>> needle="typedef struct Command"; attribute :>> obligation="native Command type distinct from Gambit RC header"; }
part def ComponentRow { attribute componentId:String; attribute sharedContract:String; attribute role:String; }
part component0:ComponentRow { attribute :>> componentId="source-owner"; attribute :>> sharedContract="RegistrationHandle/PayloadVersion/InvocationOutcome"; attribute :>> role="source storage identity, version roots and logical revoke"; }
part component1:ComponentRow { attribute :>> componentId="gc-root-domain"; attribute :>> sharedContract="RegistrationHandle/PayloadVersion/InvocationOutcome"; attribute :>> role="frozen root view and root-write lease"; }
part component2:ComponentRow { attribute :>> componentId="native-outcome"; attribute :>> sharedContract="RegistrationHandle/PayloadVersion/InvocationOutcome"; attribute :>> role="nested native refusal ledger and checked result delivery"; }
part def IssuerRow { attribute key:String; attribute source:String; attribute existing:String; attribute candidate:String; attribute gap:String; }
part issuer0:IssuerRow { attribute :>> key="registration"; attribute :>> source="tcl-register"; attribute :>> existing="Tcl constructor owns cd/vector until create publishes callback"; attribute :>> candidate="CommandOwnerService binds interp/VM/context/storage/registration identity before publish"; attribute :>> gap="no existing source-borrow API"; }
part issuer1:IssuerRow { attribute :>> key="borrow"; attribute :>> source="tcl-native-callback"; attribute :>> existing="ClientData available before raw data_rc read"; attribute :>> candidate="tryBorrow authenticates immutable registration handle and native scope before dereference"; attribute :>> gap="raw header increment or TLS guess is not authority"; }
part issuer2:IssuerRow { attribute :>> key="delete"; attribute :>> source="tcl-delete"; attribute :>> existing="current callback drops vector and RC immediately"; attribute :>> candidate="logical revoke then owner-side version/dispatch drain; return without waiting on itself"; attribute :>> gap="current delete path has no borrow/version accounting"; }
part issuer3:IssuerRow { attribute :>> key="setter"; attribute :>> source="rc-source-write"; attribute :>> existing="public setter overwrites one root slot"; attribute :>> candidate="fixed-slot seal or synchronous versioned commit retains borrowed prior values"; attribute :>> gap="void raw ABI and external setters remain unqualified"; }
part issuer4:IssuerRow { attribute :>> key="scan"; attribute :>> source="rc-scan"; attribute :>> existing="context RC list already scanned and updated"; attribute :>> candidate="enumerate each retained version cell in same root-domain census"; attribute :>> gap="generic version cells and retirement not yet connected"; }
part issuer5:IssuerRow { attribute :>> key="refusal"; attribute :>> source="tcl-eval-driver"; attribute :>> existing="old eval invokes Scheme error callback on Tcl error"; attribute :>> candidate="native eval frame records origin before SetResult and carries descendant refusal out of catch"; attribute :>> gap="TCL_ERROR/NULL alone cannot carry bridge refusal identity"; }
part def ProfileRow { attribute key:String; attribute scope:String; attribute permission:String; attribute boundary:String; }
part profile0:ProfileRow { attribute :>> key="fixed-payload"; attribute :>> scope="Tcl and C-closure constructors in audited source initialize once"; attribute :>> permission="seal managed publication against semantic setter; GC slot relocation still allowed"; attribute :>> boundary="not a deep freeze of the vector/procedure; public bypass not silently accepted"; }
part profile1:ProfileRow { attribute :>> key="mutable-payload"; attribute :>> scope="explicit checked setter compatibility profile"; attribute :>> permission="prepare rooted new value; publish new version synchronously; retain old borrowed version cells"; attribute :>> boundary="do not block a reentrant setter waiting for its own borrower"; }
part profile2:ProfileRow { attribute :>> key="loaded-source"; attribute :>> scope="local Tcl commit cbf86d62348d6b052e1961b4df995960fb21545f"; attribute :>> permission="source-qualified C-call ordering only"; attribute :>> boundary="not installed Tcl identity, Darwin binary ABI or native test evidence"; }
part profile3:ProfileRow { attribute :>> key="nested-native"; attribute :>> scope="native frames may catch errors or invoke old result free callbacks"; attribute :>> permission="preserve causal refusal in native frame ancestry independently of Tcl result"; attribute :>> boundary="normal Gambit free hook is RC release; arbitrary reentry target is an extension hypothesis"; }
part def PathRow { attribute key:String; attribute producer:String; attribute consumer:String; attribute classification:String; attribute missing:String; }
part path0:PathRow { attribute :>> key="registration-read"; attribute :>> producer="tcl-register"; attribute :>> consumer="tcl-native-callback"; attribute :>> classification="actual registered source producer/consumer"; attribute :>> missing="source borrow currently absent"; }
part path1:PathRow { attribute :>> key="delete-payload"; attribute :>> producer="tcl-native-delete"; attribute :>> consumer="tcl-delete"; attribute :>> classification="pinned Tcl delete -> actual Gambit hook"; attribute :>> missing="loaded library correspondence"; }
part path2:PathRow { attribute :>> key="rc-setters"; attribute :>> producer="rc-source-write"; attribute :>> consumer="closure-setter"; attribute :>> classification="plain public store plus explicit constructor callers"; attribute :>> missing="indirect/public postpublication writer closure"; }
part path3:PathRow { attribute :>> key="native-command-setter"; attribute :>> producer="tcl-set-info"; attribute :>> consumer="tcl-get-info"; attribute :>> classification="native bypass/escape capability"; attribute :>> missing="not exercised by audited Gambit adapter"; }
part path4:PathRow { attribute :>> key="result-old-free"; attribute :>> producer="tcl-result-free-hook"; attribute :>> consumer="native-string-free"; attribute :>> classification="old free callback invoked; selected normal free is RC-only"; attribute :>> missing="no observed Scheme reentry from this free hook"; }
part path5:PathRow { attribute :>> key="refusal-error-callback"; attribute :>> producer="tcl-eval-driver"; attribute :>> consumer="tcl-error-export"; attribute :>> classification="real old translator calls Scheme"; attribute :>> missing="checked origin frame/adapter not implemented"; }
part def RouteRow { attribute component:String; attribute actionName:String; attribute lemma:String; attribute producerAnchor:String; attribute obligationId:String; }
part route0:RouteRow { attribute :>> component="source-owner"; attribute :>> actionName="tcl_source_borrow.selectDispatch"; attribute :>> lemma="TclBorrow.selectDispatchPreserves"; attribute :>> producerAnchor="tcl-native-callback"; attribute :>> obligationId="source-safety"; }
part route1:RouteRow { attribute :>> component="source-owner"; attribute :>> actionName="tcl_source_borrow.acquireBorrow"; attribute :>> lemma="TclBorrow.acquireBorrowPreserves"; attribute :>> producerAnchor="tcl-native-callback"; attribute :>> obligationId="source-safety"; }
part route2:RouteRow { attribute :>> component="source-owner"; attribute :>> actionName="tcl_source_borrow.refuseLateDispatch"; attribute :>> lemma="TclBorrow.refuseLateDispatchPreserves"; attribute :>> producerAnchor="tcl-native-callback"; attribute :>> obligationId="source-safety"; }
part route3:RouteRow { attribute :>> component="source-owner"; attribute :>> actionName="tcl_source_borrow.refuseGcClosed"; attribute :>> lemma="TclBorrow.refuseGcClosedPreserves"; attribute :>> producerAnchor="tcl-native-callback"; attribute :>> obligationId="source-safety"; }
part route4:RouteRow { attribute :>> component="source-owner"; attribute :>> actionName="tcl_source_borrow.otherBorrowOld"; attribute :>> lemma="TclBorrow.otherBorrowOldPreserves"; attribute :>> producerAnchor="tcl-native-callback"; attribute :>> obligationId="source-safety"; }
part route5:RouteRow { attribute :>> component="source-owner"; attribute :>> actionName="tcl_source_borrow.otherBorrowNew"; attribute :>> lemma="TclBorrow.otherBorrowNewPreserves"; attribute :>> producerAnchor="tcl-native-callback"; attribute :>> obligationId="source-safety"; }
part route6:RouteRow { attribute :>> component="source-owner"; attribute :>> actionName="tcl_source_borrow.releaseOtherOld"; attribute :>> lemma="TclBorrow.releaseOtherOldPreserves"; attribute :>> producerAnchor="tcl-native-callback"; attribute :>> obligationId="source-safety"; }
part route7:RouteRow { attribute :>> component="source-owner"; attribute :>> actionName="tcl_source_borrow.releaseOtherNew"; attribute :>> lemma="TclBorrow.releaseOtherNewPreserves"; attribute :>> producerAnchor="tcl-native-callback"; attribute :>> obligationId="source-safety"; }
part route8:RouteRow { attribute :>> component="gc-root-domain"; attribute :>> actionName="tcl_source_borrow.acquireWriter"; attribute :>> lemma="TclBorrow.acquireWriterPreserves"; attribute :>> producerAnchor="rc-scan"; attribute :>> obligationId="source-safety"; }
part route9:RouteRow { attribute :>> component="source-owner"; attribute :>> actionName="tcl_source_borrow.prepareSetter"; attribute :>> lemma="TclBorrow.prepareSetterPreserves"; attribute :>> producerAnchor="rc-source-write"; attribute :>> obligationId="source-safety"; }
part route10:RouteRow { attribute :>> component="source-owner"; attribute :>> actionName="tcl_source_borrow.commitSetter"; attribute :>> lemma="TclBorrow.commitSetterPreserves"; attribute :>> producerAnchor="rc-source-write"; attribute :>> obligationId="source-safety"; }
part route11:RouteRow { attribute :>> component="source-owner"; attribute :>> actionName="tcl_source_borrow.abortSetter"; attribute :>> lemma="TclBorrow.abortSetterPreserves"; attribute :>> producerAnchor="rc-source-write"; attribute :>> obligationId="source-safety"; }
part route12:RouteRow { attribute :>> component="gc-root-domain"; attribute :>> actionName="tcl_source_borrow.releaseWriter"; attribute :>> lemma="TclBorrow.releaseWriterPreserves"; attribute :>> producerAnchor="rc-scan"; attribute :>> obligationId="source-safety"; }
part route13:RouteRow { attribute :>> component="source-owner"; attribute :>> actionName="tcl_source_borrow.revoke"; attribute :>> lemma="TclBorrow.revokePreserves"; attribute :>> producerAnchor="tcl-delete"; attribute :>> obligationId="source-safety"; }
part route14:RouteRow { attribute :>> component="source-owner"; attribute :>> actionName="tcl_source_borrow.publishDestination"; attribute :>> lemma="TclBorrow.publishDestinationPreserves"; attribute :>> producerAnchor="tcl-native-callback"; attribute :>> obligationId="source-safety"; }
part route15:RouteRow { attribute :>> component="source-owner"; attribute :>> actionName="tcl_source_borrow.loseReply"; attribute :>> lemma="TclBorrow.loseReplyPreserves"; attribute :>> producerAnchor="tcl-native-callback"; attribute :>> obligationId="source-safety"; }
part route16:RouteRow { attribute :>> component="source-owner"; attribute :>> actionName="tcl_source_borrow.acknowledgeTransfer"; attribute :>> lemma="TclBorrow.acknowledgeTransferPreserves"; attribute :>> producerAnchor="tcl-native-callback"; attribute :>> obligationId="source-safety"; }
part route17:RouteRow { attribute :>> component="source-owner"; attribute :>> actionName="tcl_source_borrow.dropOldVersion"; attribute :>> lemma="TclBorrow.dropOldVersionPreserves"; attribute :>> producerAnchor="tcl-native-callback"; attribute :>> obligationId="source-safety"; }
part route18:RouteRow { attribute :>> component="source-owner"; attribute :>> actionName="tcl_source_borrow.dropRevokedRoots"; attribute :>> lemma="TclBorrow.dropRevokedRootsPreserves"; attribute :>> producerAnchor="tcl-delete"; attribute :>> obligationId="source-safety"; }
part route19:RouteRow { attribute :>> component="source-owner"; attribute :>> actionName="tcl_source_borrow.leaveDispatch"; attribute :>> lemma="TclBorrow.leaveDispatchPreserves"; attribute :>> producerAnchor="tcl-native-callback"; attribute :>> obligationId="source-safety"; }
part route20:RouteRow { attribute :>> component="source-owner"; attribute :>> actionName="tcl_source_borrow.freeSource"; attribute :>> lemma="TclBorrow.freeSourcePreserves"; attribute :>> producerAnchor="tcl-delete"; attribute :>> obligationId="source-safety"; }
part route21:RouteRow { attribute :>> component="source-owner"; attribute :>> actionName="tcl_source_borrow.dropDestination"; attribute :>> lemma="TclBorrow.dropDestinationPreserves"; attribute :>> producerAnchor="tcl-native-callback"; attribute :>> obligationId="source-safety"; }
part route22:RouteRow { attribute :>> component="source-owner"; attribute :>> actionName="tcl_source_borrow.reuseStorage"; attribute :>> lemma="TclBorrow.reuseStoragePreserves"; attribute :>> producerAnchor="tcl-native-callback"; attribute :>> obligationId="source-safety"; }
part route23:RouteRow { attribute :>> component="source-owner"; attribute :>> actionName="tcl_source_borrow.selectNewToken"; attribute :>> lemma="TclBorrow.selectNewTokenPreserves"; attribute :>> producerAnchor="tcl-native-callback"; attribute :>> obligationId="source-safety"; }
part route24:RouteRow { attribute :>> component="gc-root-domain"; attribute :>> actionName="tcl_source_borrow.closeGcGate"; attribute :>> lemma="TclBorrow.closeGcGatePreserves"; attribute :>> producerAnchor="rc-scan"; attribute :>> obligationId="source-safety"; }
part route25:RouteRow { attribute :>> component="gc-root-domain"; attribute :>> actionName="tcl_source_borrow.freezeRoots"; attribute :>> lemma="TclBorrow.freezeRootsPreserves"; attribute :>> producerAnchor="rc-scan"; attribute :>> obligationId="source-safety"; }
part route26:RouteRow { attribute :>> component="gc-root-domain"; attribute :>> actionName="tcl_source_borrow.beginScan"; attribute :>> lemma="TclBorrow.beginScanPreserves"; attribute :>> producerAnchor="rc-scan"; attribute :>> obligationId="source-safety"; }
part route27:RouteRow { attribute :>> component="gc-root-domain"; attribute :>> actionName="tcl_source_borrow.endScan"; attribute :>> lemma="TclBorrow.endScanPreserves"; attribute :>> producerAnchor="rc-scan"; attribute :>> obligationId="source-safety"; }
part route28:RouteRow { attribute :>> component="gc-root-domain"; attribute :>> actionName="tcl_source_borrow.resumeRoots"; attribute :>> lemma="TclBorrow.resumeRootsPreserves"; attribute :>> producerAnchor="rc-scan"; attribute :>> obligationId="source-safety"; }
part route29:RouteRow { attribute :>> component="native-outcome"; attribute :>> actionName="tcl_checked_refusal.beginEval"; attribute :>> lemma="TclRefusal.beginEvalPreserves"; attribute :>> producerAnchor="tcl-eval-driver"; attribute :>> obligationId="outcome-safety"; }
part route30:RouteRow { attribute :>> component="native-outcome"; attribute :>> actionName="tcl_checked_refusal.beginNested"; attribute :>> lemma="TclRefusal.beginNestedPreserves"; attribute :>> producerAnchor="tcl-eval-driver"; attribute :>> obligationId="outcome-safety"; }
part route31:RouteRow { attribute :>> component="native-outcome"; attribute :>> actionName="tcl_checked_refusal.recordOuterRefusal"; attribute :>> lemma="TclRefusal.recordOuterRefusalPreserves"; attribute :>> producerAnchor="tcl-eval-driver"; attribute :>> obligationId="outcome-safety"; }
part route32:RouteRow { attribute :>> component="native-outcome"; attribute :>> actionName="tcl_checked_refusal.recordChildRefusal"; attribute :>> lemma="TclRefusal.recordChildRefusalPreserves"; attribute :>> producerAnchor="tcl-eval-driver"; attribute :>> obligationId="outcome-safety"; }
part route33:RouteRow { attribute :>> component="native-outcome"; attribute :>> actionName="tcl_checked_refusal.publishOuterDiagnostic"; attribute :>> lemma="TclRefusal.publishOuterDiagnosticPreserves"; attribute :>> producerAnchor="tcl-result-free-hook"; attribute :>> obligationId="outcome-safety"; }
part route34:RouteRow { attribute :>> component="native-outcome"; attribute :>> actionName="tcl_checked_refusal.publishChildDiagnostic"; attribute :>> lemma="TclRefusal.publishChildDiagnosticPreserves"; attribute :>> producerAnchor="tcl-result-free-hook"; attribute :>> obligationId="outcome-safety"; }
part route35:RouteRow { attribute :>> component="native-outcome"; attribute :>> actionName="tcl_checked_refusal.catchOrResetResult"; attribute :>> lemma="TclRefusal.catchOrResetResultPreserves"; attribute :>> producerAnchor="tcl-eval-driver"; attribute :>> obligationId="outcome-safety"; }
part route36:RouteRow { attribute :>> component="native-outcome"; attribute :>> actionName="tcl_checked_refusal.ordinaryTclError"; attribute :>> lemma="TclRefusal.ordinaryTclErrorPreserves"; attribute :>> producerAnchor="tcl-eval-driver"; attribute :>> obligationId="outcome-safety"; }
part route37:RouteRow { attribute :>> component="native-outcome"; attribute :>> actionName="tcl_checked_refusal.mergeChildRefusal"; attribute :>> lemma="TclRefusal.mergeChildRefusalPreserves"; attribute :>> producerAnchor="tcl-eval-driver"; attribute :>> obligationId="outcome-safety"; }
part route38:RouteRow { attribute :>> component="native-outcome"; attribute :>> actionName="tcl_checked_refusal.popNested"; attribute :>> lemma="TclRefusal.popNestedPreserves"; attribute :>> producerAnchor="tcl-eval-driver"; attribute :>> obligationId="outcome-safety"; }
part route39:RouteRow { attribute :>> component="native-outcome"; attribute :>> actionName="tcl_checked_refusal.finishEval"; attribute :>> lemma="TclRefusal.finishEvalPreserves"; attribute :>> producerAnchor="tcl-eval-driver"; attribute :>> obligationId="outcome-safety"; }
part route40:RouteRow { attribute :>> component="native-outcome"; attribute :>> actionName="tcl_checked_refusal.deliverRefusal"; attribute :>> lemma="TclRefusal.deliverRefusalPreserves"; attribute :>> producerAnchor="tcl-eval-driver"; attribute :>> obligationId="outcome-safety"; }
part route41:RouteRow { attribute :>> component="native-outcome"; attribute :>> actionName="tcl_checked_refusal.deliverOrdinaryNativeError"; attribute :>> lemma="TclRefusal.deliverOrdinaryNativeErrorPreserves"; attribute :>> producerAnchor="tcl-eval-driver"; attribute :>> obligationId="outcome-safety"; }
part route42:RouteRow { attribute :>> component="native-outcome"; attribute :>> actionName="tcl_checked_refusal.translateOrdinaryError"; attribute :>> lemma="TclRefusal.translateOrdinaryErrorPreserves"; attribute :>> producerAnchor="tcl-eval-driver"; attribute :>> obligationId="outcome-safety"; }
part route43:RouteRow { attribute :>> component="native-outcome"; attribute :>> actionName="tcl_checked_refusal.deliverSuccess"; attribute :>> lemma="TclRefusal.deliverSuccessPreserves"; attribute :>> producerAnchor="tcl-eval-driver"; attribute :>> obligationId="outcome-safety"; }
part route44:RouteRow { attribute :>> component="native-outcome"; attribute :>> actionName="tcl_checked_refusal.closeVm"; attribute :>> lemma="TclRefusal.closeVmPreserves"; attribute :>> producerAnchor="tcl-eval-driver"; attribute :>> obligationId="outcome-safety"; }
part route45:RouteRow { attribute :>> component="native-outcome"; attribute :>> actionName="tcl_checked_refusal.resumeVm"; attribute :>> lemma="TclRefusal.resumeVmPreserves"; attribute :>> producerAnchor="tcl-eval-driver"; attribute :>> obligationId="outcome-safety"; }
part def CompositionRow { attribute key:String; attribute lemma:String; attribute source:String; attribute obligation:String; attribute boundary:String; }
part composition0:CompositionRow { attribute :>> key="entry-pin"; attribute :>> lemma="TclBorrowBridge.activeBorrowProvidesAdmissionRoot"; attribute :>> source="tcl-native-callback"; attribute :>> obligation="entry-pin-bridge"; attribute :>> boundary="abstract live source pin; no VM entry approval inferred from command liveness"; }
part composition1:CompositionRow { attribute :>> key="refusal-event"; attribute :>> lemma="TclBorrowBridge.rejectedSourceCanRecord"; attribute :>> source="tcl-eval-driver"; attribute :>> obligation="outcome-safety"; attribute :>> boundary="one native eval frame with authenticated matching source invocation"; }
part composition2:CompositionRow { attribute :>> key="caught-refusal"; attribute :>> lemma="TclBorrowBridge.recordedSourceRefusalSurvivesCatch"; attribute :>> source="tcl-eval-driver"; attribute :>> obligation="outcome-safety"; attribute :>> boundary="preserve actual Tcl status independently; not uncatchable Tcl control transfer"; }
part def MemoryRow { attribute key:String; attribute order:String; attribute premise:String; attribute obligation:String; }
part memory0:MemoryRow { attribute :>> key="borrow-reserve"; attribute :>> order="same owner/generation admission before payload load; acquire protected root version"; attribute :>> premise="immutable ClientData handle survives dispatch gap; no dereference of freed RC pointer"; attribute :>> obligation="source-issuer"; }
part memory1:MemoryRow { attribute :>> key="setter-publication"; attribute :>> order="new root initialized/registered before current-version release publication; readers acquire selected version"; attribute :>> premise="no allocation or foreign callback under short root-write lease"; attribute :>> obligation="C23-publication"; }
part memory2:MemoryRow { attribute :>> key="delete"; attribute :>> order="close command admission; retain preaccepted borrows; physical free waits version and dispatch/scanner drain"; attribute :>> premise="do not wait in deleteProc for its own in-flight callback"; attribute :>> obligation="dispatch-grace"; }
part memory3:MemoryRow { attribute :>> key="gc-view"; attribute :>> order="root-writer drain precedes frozen manifest; retain all current/borrowed/prepared/destination roots"; attribute :>> premise="GC forwarding updates root contents without changing semantic payload version"; attribute :>> obligation="version-gc-adapter"; }
part memory4:MemoryRow { attribute :>> key="handoff"; attribute :>> order="destination visible then exact ACK; lost ACK keeps source root; release borrow once"; attribute :>> premise="source no longer read after ACK; target completion independently authorizes destination root retirement"; attribute :>> obligation="version-disposition"; }
part memory5:MemoryRow { attribute :>> key="refusal-ledger"; attribute :>> order="publish refusal event before Tcl_SetResult; merge child cause before frame pop; acquire exact invocation outcome"; attribute :>> premise="Tcl catch/reset/result overwrite does not erase native provenance"; attribute :>> obligation="eval-frame-issuer"; }
part def GainRow { attribute key:String; attribute benefit:String; attribute cost:String; attribute condition:String; attribute refutation:String; }
part gain0:GainRow { attribute :>> key="early-handoff"; attribute :>> benefit="A acknowledged callbacks can stop holding source payload versions before full Scheme callback returns"; attribute :>> cost="destination guard/root must remain; source ACK/query metadata required"; attribute :>> condition="no post-ACK source use; current callback already has no post-Scheme cd read"; attribute :>> refutation="new completion/logging code that rereads ClientData extends lifetime again"; }
part gain1:GainRow { attribute :>> key="fixed-specialization"; attribute :>> benefit="known constructors need one root version per command"; attribute :>> cost="identity/borrow/delete/GC contracts still required"; attribute :>> condition="fixed-slot profile actually enforced; GC updates allowed"; attribute :>> refutation="public raw setter bypass invalidates fixed-slot claim"; }
part gain2:GainRow { attribute :>> key="mutable-versions"; attribute :>> benefit="reentrant setter publishes new value without waiting for old borrowers"; attribute :>> cost="V simultaneously retained versions require O(V) roots and native hold accounting"; attribute :>> condition="new source value rooted before preparation; retire only unused versions"; attribute :>> refutation="header refcount alone protects no prior payload after h->data overwrite"; }
part gain3:GainRow { attribute :>> key="scanner-reuse"; attribute :>> benefit="reuse current context RC enumeration rather than second unrelated scanner"; attribute :>> cost="more root cells and phase/census/retirement integration"; attribute :>> condition="version cells genuinely registered in same frozen-root contract"; attribute :>> refutation="file association or root flag does not prove actual GC slot coverage"; }
part gain4:GainRow { attribute :>> key="refusal-routing"; attribute :>> benefit="R refused callbacks avoid R Scheme error-translator invocations at this adapter boundary"; attribute :>> cost="per-native-scope/parent causal ledger and typed outcome channel"; attribute :>> condition="all callback/error translator paths honor checked origin"; attribute :>> refutation="TCL_ERROR can be caught; SetResult may invoke a different old free hook"; }
part gain5:GainRow { attribute :>> key="retained-cost"; attribute :>> benefit="logical revoke can return without self-wait"; attribute :>> cost="D pre-frontier dispatch scopes and retained receipts delay native metadata reclamation"; attribute :>> condition="scope census/epoch exhaustion and shutdown drain qualified"; attribute :>> refutation="a non-returning native scope can retain storage indefinitely"; }
part def ContractRow { attribute fromNode:String; attribute toNode:String; attribute custody:String; }
part contract0:ContractRow { attribute :>> fromNode="Tcl command registration"; attribute :>> toNode="Immutable ClientData handle"; attribute :>> custody="interp/VM/context/storage incarnation; no recycled raw RC identity"; }
part contract1:ContractRow { attribute :>> fromNode="Immutable ClientData handle"; attribute :>> toNode="Command owner source borrow"; attribute :>> custody="validate live native scope and generation before data_rc load"; }
part contract2:ContractRow { attribute :>> fromNode="Command owner source borrow"; attribute :>> toNode="Payload version root"; attribute :>> custody="pin selected semantic version; collector may update slot contents"; }
part contract3:ContractRow { attribute :>> fromNode="Checked setter"; attribute :>> toNode="Payload version root"; attribute :>> custody="publish rooted new value; retain borrowed old cell"; }
part contract4:ContractRow { attribute :>> fromNode="Delete callback"; attribute :>> toNode="Command owner source borrow"; attribute :>> custody="revoke new admission; do not wait on in-flight borrower"; }
part contract5:ContractRow { attribute :>> fromNode="Payload version root"; attribute :>> toNode="Frozen RC root census"; attribute :>> custody="current, old, prepared and destination slots"; }
part contract6:ContractRow { attribute :>> fromNode="Payload version root"; attribute :>> toNode="Checked entry carrier"; attribute :>> custody="source/root identity survives marker/guard allocation"; }
part contract7:ContractRow { attribute :>> fromNode="Checked entry carrier"; attribute :>> toNode="Native outcome frame"; attribute :>> custody="exact ACK or origin-qualified refusal"; }
part contract8:ContractRow { attribute :>> fromNode="Native outcome frame"; attribute :>> toNode="Tcl result/catch/nested eval"; attribute :>> custody="record before result hooks; causal cause survives native result changes"; }
part contract9:ContractRow { attribute :>> fromNode="Tcl result/catch/nested eval"; attribute :>> toNode="Typed native delivery"; attribute :>> custody="merge child refusal; preserve Tcl code; skip Scheme error callback"; }
part contract10:ContractRow { attribute :>> fromNode="Command owner source borrow"; attribute :>> toNode="Retirement coordinator"; attribute :>> custody="borrow/version/dispatch/scanner drain; native holds and RC freed separately"; }
part def NeedRow { attribute key:String; attribute status:String; attribute condition:String; }
part need0:NeedRow { attribute :>> key="source-safety"; attribute :>> status="formal"; attribute :>> condition="borrowed version rooted; delayed free; frozen slots unchanged"; }
part need1:NeedRow { attribute :>> key="outcome-safety"; attribute :>> status="formal"; attribute :>> condition="catch/reset cannot erase refusal; nested merge precedes child retirement"; }
part need2:NeedRow { attribute :>> key="entry-pin-bridge"; attribute :>> status="formal"; attribute :>> condition="active abstract source borrow discharges parent admission sourcePin premise"; }
part need3:NeedRow { attribute :>> key="source-issuer"; attribute :>> status="unresolved"; attribute :>> condition="registration owner and VM root-domain authority jointly issue nonallocating source borrow"; }
part need4:NeedRow { attribute :>> key="dispatch-grace"; attribute :>> status="unresolved"; attribute :>> condition="all scopes that could carry old ClientData drained; raw external retainers excluded"; }
part need5:NeedRow { attribute :>> key="all-setters"; attribute :>> status="unresolved"; attribute :>> condition="public RC accessors plus Tcl command-info mutation/aliases fully mediated"; }
part need6:NeedRow { attribute :>> key="version-gc-adapter"; attribute :>> status="unresolved"; attribute :>> condition="current and retained root slots enumerate/update under actual collector freeze"; }
part need7:NeedRow { attribute :>> key="version-disposition"; attribute :>> status="unresolved"; attribute :>> condition="native still-hold ownership and RC frees settled exactly once, separate from root flags"; }
part need8:NeedRow { attribute :>> key="C23-publication"; attribute :>> status="unresolved"; attribute :>> condition="control/count/slot publication and generation exhaustion refine weak memory"; }
part need9:NeedRow { attribute :>> key="eval-frame-issuer"; attribute :>> status="unresolved"; attribute :>> condition="stable per-invocation/eval generation and parent chain established before Tcl entry"; }
part need10:NeedRow { attribute :>> key="native-outcome-adapter"; attribute :>> status="unresolved"; attribute :>> condition="preserve actual Tcl code/result ownership; no Scheme translator for refused origin"; }
part need11:NeedRow { attribute :>> key="loaded-tcl-cohort"; attribute :>> status="unresolved"; attribute :>> condition="local pinned source and installed example library/build correspondence unproved"; }
}
