package GambitChunkTransportLedger { private import ScalarValues::*;
part def Source { attribute key:String; attribute path:String; attribute needle:String; attribute obligation:String; }
part source0:Source { attribute :>> key="close-marker"; attribute :>> path="vendor/gambit/lib/mem.c"; attribute :>> needle="*work->context->mem.alloc_heap_ptr_++ = NULL_CHUNK_LINK;"; attribute :>> obligation="Writes closing marker and first section prefix; both locations must be qualified"; }
part source1:Source { attribute :>> key="append-link"; attribute :>> path="vendor/gambit/lib/mem.c"; attribute :>> needle="*heap_chunks_to_scan_tail = ___TAG(new_tail, ___FORW);"; attribute :>> obligation="Plain write under FIFO gate; may target prior physical terminator"; }
part source2:Source { attribute :>> key="take-link"; attribute :>> path="vendor/gambit/lib/mem.c"; attribute :>> needle="node = ___UNTAG_AS(*owner->heap_chunks_to_scan_head_, ___FORW);"; attribute :>> obligation="Pointer load under successful gate"; }
part source3:Source { attribute :>> key="scan-classifier"; attribute :>> path="vendor/gambit/lib/mem.c"; attribute :>> needle="while (!___TESTTYPE(head = *ptr, ___FORW))"; attribute :>> obligation="Two raw classifier loads: complete and local frontier"; }
part source4:Source { attribute :>> key="tail-address"; attribute :>> path="vendor/gambit/lib/mem.c"; attribute :>> needle="___WORD *new_tail = alloc_heap_chunk_start-1;"; attribute :>> obligation="Next chunk prefix aliases preceding terminal word"; }
part source5:Source { attribute :>> key="advance-start"; attribute :>> path="vendor/gambit/lib/mem.c"; attribute :>> needle="alloc_heap_chunk_start = work->context->mem.alloc_heap_ptr_;"; attribute :>> obligation="New start follows prior terminal write/increment"; }
part source6:Source { attribute :>> key="dummy-head"; attribute :>> path="vendor/gambit/lib/mem.c"; attribute :>> needle="heap_chunks_to_scan_head = &heap_chunks_to_scan;"; attribute :>> obligation="Empty queue still retains head/tail address"; }
part source7:Source { attribute :>> key="gate-lock"; attribute :>> path="vendor/gambit/lib/mem.c"; attribute :>> needle="while (___COMPARE_AND_SWAP_WORD(&owner->chunk_gate_,0,1) != 0)"; attribute :>> obligation="Protects FIFO accesses; not all scan loads"; }
part source8:Source { attribute :>> key="gate-take"; attribute :>> path="vendor/gambit/lib/mem.c"; attribute :>> needle="if (___COMPARE_AND_SWAP_WORD(&owner->chunk_gate_,0,1) != 0)"; attribute :>> obligation="Failed steal returns without observing queue"; }
part source9:Source { attribute :>> key="gate-release"; attribute :>> path="vendor/gambit/lib/mem.c"; attribute :>> needle="___FETCH_AND_CLEAR_WORD(&owner->chunk_gate_);"; attribute :>> obligation="Legacy native adapter release candidate"; }
part source10:Source { attribute :>> key="steal"; attribute :>> path="vendor/gambit/lib/mem.c"; attribute :>> needle="___WORD *ptr = take_heap_chunk(work,victim);"; attribute :>> obligation="Claim precedes later ungated complete-chunk scanning"; }
part source11:Source { attribute :>> key="scan-done"; attribute :>> path="vendor/gambit/lib/mem.c"; attribute :>> needle="require_chunk_transition(work,start,2,3);"; attribute :>> obligation="Scan completion does not detach FIFO head"; }
part source12:Source { attribute :>> key="frame-pending"; attribute :>> path="vendor/gambit/lib/mem.c"; attribute :>> needle="ptr = &___FP_STK(alloc,link+1);"; attribute :>> obligation="Delayed copied link retains original chunk/epoch responsibility"; }
part source13:Source { attribute :>> key="frame-ready"; attribute :>> path="vendor/gambit/lib/mem.c"; attribute :>> needle="publish_object_scan (work, copy_header);\n          work->copied_words += words+___SUBTYPED_BODY;"; attribute :>> obligation="Current frame READY still precedes later successor fixup"; }
part source14:Source { attribute :>> key="weak-entry"; attribute :>> path="vendor/gambit/lib/mem.c"; attribute :>> needle="traverse_weak_refs = 1;"; attribute :>> obligation="Global cut must precede all weak producers"; }
part source15:Source { attribute :>> key="will-fused"; attribute :>> path="vendor/gambit/lib/mem.c"; attribute :>> needle="determine_will_executability (nonexecutable_wills);"; attribute :>> obligation="Classification and weak retention remain fused"; }
part source16:Source { attribute :>> key="idle"; attribute :>> path="vendor/gambit/lib/mem.c"; attribute :>> needle="if (--(*workers_count) == 0)"; attribute :>> obligation="Active count valid only if every delayed/private/Tail child is covered"; }
part source17:Source { attribute :>> key="gc-reset"; attribute :>> path="vendor/gambit/lib/mem.c"; attribute :>> needle="heap_chunks_to_scan = NULL_CHUNK_LINK;"; attribute :>> obligation="Epoch setup reset; requires all prior observers detached"; }
part source18:Source { attribute :>> key="native-cas"; attribute :>> path="vendor/gambit/include/gambit.h.in"; attribute :>> needle="__sync_val_compare_and_swap(p,oldval,newval)"; attribute :>> obligation="Effective native/C11 adapter mapping remains open"; }
part source19:Source { attribute :>> key="native-fence"; attribute :>> path="vendor/gambit/include/gambit.h.in"; attribute :>> needle="__sync_synchronize()"; attribute :>> obligation="A fence does not order future link stores before prior scan reads"; }
part source20:Source { attribute :>> key="native-word"; attribute :>> path="vendor/gambit/include/gambit.h.in"; attribute :>> needle="___VOLATILE ___WORD chunk_gate_;"; attribute :>> obligation="Current gate storage is a native-layer contract, not new C11 qualification"; }
part def Option { attribute key:String; attribute representation:String; attribute accessRule:String; attribute reuse:String; attribute cost:String; attribute mechanism:String; attribute decision:String; }
part option0:Option { attribute :>> key="unified-atomic"; attribute :>> representation="Preserve shared terminal/link storage"; attribute :>> accessRule="Every conflicting access and every undecided classifier uses compatible atomics"; attribute :>> reuse="No distinct next-link node required in best case"; attribute :>> cost="Storage typing/alignment ABI profiles debugging and generated raw access"; attribute :>> mechanism="Convert K+C classifier loads; no speed estimate"; attribute :>> decision="Control; promote only after full access/storage qualification"; }
part option1:Option { attribute :>> key="split-record"; attribute :>> representation="Immutable in-band terminal plus independently mutable queue record"; attribute :>> accessRule="Reuse central queue gate; scanner reads immutable marker or sealed bound"; attribute :>> reuse="Start/term/next descriptor plus pool and lifetime custody"; attribute :>> cost="Reserve native nodes before close; no recursive Scheme GC; dummy head and late receipts"; attribute :>> mechanism="Selected node has 3 pointer fields; at P=8 at least 24*C bytes before overhead"; attribute :>> decision="Main design candidate; pool/lifetime/ABI refinement still open"; }
part def Trace { attribute key:String; attribute operationText:String; attribute consequence:String; attribute gap:String; }
part trace0:Trace { attribute :>> key="close-C0"; attribute :>> operationText="Writer closes nonlocal C0 at t0"; attribute :>> consequence="C0 becomes eligible for victim queue"; attribute :>> gap="Source assumptions; no legal-input compiled witness"; }
part trace1:Trace { attribute :>> key="start-C1"; attribute :>> operationText="C1.start=t0+1; C1.leading=t0"; attribute :>> consequence="Same address is previous terminator"; attribute :>> gap="Address arithmetic proved by predecessor"; }
part trace2:Trace { attribute :>> key="queue-C1"; attribute :>> operationText="Publishing C1 sets FIFO tail=t0"; attribute :>> consequence="Does not yet require storing next link at t0"; attribute :>> gap="Distinguish selecting a tail from later writing it"; }
part trace3:Trace { attribute :>> key="claim-C0"; attribute :>> operationText="Thief claims C0 under gate then scans outside it"; attribute :>> consequence="Acquire covers earlier stores only"; attribute :>> gap="Later append is not ordered by this earlier acquire"; }
part trace4:Trace { attribute :>> key="queue-C2"; attribute :>> operationText="Publishing C2 writes through tail=t0"; attribute :>> consequence="Queue gate serializes queue users"; attribute :>> gap="No automatically established scanner read happens-before"; }
part trace5:Trace { attribute :>> key="read-t0"; attribute :>> operationText="Thief eventually reads t0 to test FORW"; attribute :>> consequence="Both old/new tags may be FORW"; attribute :>> gap="Tag preservation alone is not a C11 race proof"; }
part trace6:Trace { attribute :>> key="head-retention"; attribute :>> operationText="Consumed node becomes FIFO head even when empty"; attribute :>> consequence="Scan DONE cannot free node or its backing storage"; attribute :>> gap="Retention pin is distinct from work debt"; }
part def Contract { attribute fromNode:String; attribute toNode:String; attribute custody:String; }
part contract0:Contract { attribute :>> fromNode="source-marker"; attribute :>> toNode="unified-atomic"; attribute :>> custody="All classifiers and writers atomically compatible"; }
part contract1:Contract { attribute :>> fromNode="source-marker"; attribute :>> toNode="split-record"; attribute :>> custody="Immutable marker; mutable queue next separate"; }
part contract2:Contract { attribute :>> fromNode="unified-atomic"; attribute :>> toNode="transport-permit"; attribute :>> custody="Qualified storage and lifetime"; }
part contract3:Contract { attribute :>> fromNode="split-record"; attribute :>> toNode="transport-permit"; attribute :>> custody="Reserved node pool and retained dummy head"; }
part contract4:Contract { attribute :>> fromNode="strong-close"; attribute :>> toNode="classify-all"; attribute :>> custody="No hidden strong delayed debt"; }
part contract5:Contract { attribute :>> fromNode="classify-all"; attribute :>> toNode="weak-cut"; attribute :>> custody="Same epoch and all context lists"; }
part contract6:Contract { attribute :>> fromNode="weak-cut"; attribute :>> toNode="accept-delayed"; attribute :>> custody="One task identity and accepted debt"; }
part contract7:Contract { attribute :>> fromNode="accept-delayed"; attribute :>> toNode="seal-delayed"; attribute :>> custody="Keep original chunk/frame/root pin"; }
part contract8:Contract { attribute :>> fromNode="seal-delayed"; attribute :>> toNode="queue-publish"; attribute :>> custody="Transport permit plus whole physical seal"; }
part contract9:Contract { attribute :>> fromNode="transport-permit"; attribute :>> toNode="queue-publish"; attribute :>> custody="Guarded product; real C issuer open"; }
part contract10:Contract { attribute :>> fromNode="queue-publish"; attribute :>> toNode="scan-owner"; attribute :>> custody="Same work debt; unknown ack not another task"; }
part contract11:Contract { attribute :>> fromNode="scan-owner"; attribute :>> toNode="derived-child"; attribute :>> custody="Reserve before releasing parent"; }
part contract12:Contract { attribute :>> fromNode="derived-child"; attribute :>> toNode="weak-complete"; attribute :>> custody="Root admission closed and all work zero"; }
part contract13:Contract { attribute :>> fromNode="weak-complete"; attribute :>> toNode="future-users-closed"; attribute :>> custody="Cleanup and callbacks must not reuse queue"; }
part contract14:Contract { attribute :>> fromNode="future-users-closed"; attribute :>> toNode="head-detached"; attribute :>> custody="Drop lifetime pin; no new work"; }
part contract15:Contract { attribute :>> fromNode="head-detached"; attribute :>> toNode="epoch-retired"; attribute :>> custody="Receipt observers also retired"; }
part contract16:Contract { attribute :>> fromNode="epoch-retired"; attribute :>> toNode="storage-free"; attribute :>> custody="Product permits transport reclamation only now"; }
part def Obligation { attribute key:String; attribute status:String; attribute scope:String; attribute gap:String; }
part obligation0:Obligation { attribute :>> key="source-interleaving"; attribute :>> status="source-enabled-under-premises"; attribute :>> scope="Three adjacent physical chunks and thief"; attribute :>> gap="No exact Scheme/configuration witness or native race claim"; }
part obligation1:Obligation { attribute :>> key="atomic-protocol"; attribute :>> status="proved-in-model"; attribute :>> scope="Managed shared accesses are atomic and lifetime valid"; attribute :>> gap="No C atomic type/profile/weak-memory proof"; }
part obligation2:Obligation { attribute :>> key="split-protocol"; attribute :>> status="proved-in-model"; attribute :>> scope="Plain reader/writer use distinct locations"; attribute :>> gap="Concrete node pool and all scanner callers unmigrated"; }
part obligation3:Obligation { attribute :>> key="ledger"; attribute :>> status="proved-in-model"; attribute :>> scope="debt=accepted-settled; private to queue is transfer"; attribute :>> gap="Real all-producer task mapping open"; }
part obligation4:Obligation { attribute :>> key="pins"; attribute :>> status="proved-in-model"; attribute :>> scope="Weak completion can retain dummy/receipt pins"; attribute :>> gap="Future cleanup user closure is an external premise"; }
part obligation5:Obligation { attribute :>> key="phase-refinement"; attribute :>> status="proved-model-step-simulation"; attribute :>> scope="18 new actions map to old weak actions or stutter"; attribute :>> gap="Subset safety refinement; no fairness/completeness/source simulation"; }
part obligation6:Obligation { attribute :>> key="product"; attribute :>> status="proved-guarded-product"; attribute :>> scope="Transport permission and epoch lifetime gates"; attribute :>> gap="Native implementation of those guards unproved"; }
part obligation7:Obligation { attribute :>> key="spatial-seal"; attribute :>> status="open"; attribute :>> scope="Real mixed-span and late-writer closure receipt"; attribute :>> gap="Ledger sealed flag is not a source extraction proof"; }
part obligation8:Obligation { attribute :>> key="C11"; attribute :>> status="open"; attribute :>> scope="Reads-from HB storage typing mixed metadata and reset"; attribute :>> gap="No SC model can qualify the actual Darwin/GCC program"; }
part obligation9:Obligation { attribute :>> key="retirement"; attribute :>> status="open"; attribute :>> scope="All cleanup and unknown observers detached before pool reuse"; attribute :>> gap="No native shutdown/receipt deduplication evidence"; }
part def Gain { attribute key:String; attribute avoided:String; attribute added:String; attribute condition:String; }
part gain0:Gain { attribute :>> key="C payload preservation"; attribute :>> avoided="Split keeps ordinary object/frame word representation"; attribute :>> added="Extra queue records and native pool"; attribute :>> condition="Main candidate only; node storage remains bounded/admitted"; }
part gain1:Gain { attribute :>> key="atomic alternative"; attribute :>> avoided="Can avoid out-of-band next-link node"; attribute :>> added="K+C classifier loads become atomic plus atomic metadata access"; attribute :>> condition="No plain/atomic concurrent mixture; all storage cases qualified"; }
part gain2:Gain { attribute :>> key="split space"; attribute :>> avoided="Avoid whole heap conversion to atomic word storage"; attribute :>> added="3 pointer fields per selected node plus epoch/pin/pool cost"; attribute :>> condition="At 8-byte pointers lower bound 24*C bytes; no measured peak"; }
part gain3:Gain { attribute :>> key="one work ledger"; attribute :>> avoided="No extra publication debt when same accepted chunk moves"; attribute :>> added="One identity and child reservation/settlement"; attribute :>> condition="Work lifetime spans delayed state through scanning"; }
part gain4:Gain { attribute :>> key="lifetime distinction"; attribute :>> avoided="No false weak-stage stall from persistent dummy head pin"; attribute :>> added="Separate lifetime accounting; cannot free at debt zero"; attribute :>> condition="All future users closed before node/epoch reuse"; }
part gain5:Gain { attribute :>> key="will decision"; attribute :>> avoided="No new strong graph rescan"; attribute :>> added="O(W) classification plus one collective cut or snapshot"; attribute :>> condition="Queue alternative alone does not solve global will semantics"; }
part gain6:Gain { attribute :>> key="net benefit"; attribute :>> avoided="Useful prefix overlap H"; attribute :>> added="Transport cost A plus phase/custody cost B and retention"; attribute :>> condition="Need H>A+B; memory budget separately admits pool"; }
part gain7:Gain { attribute :>> key="old retirement"; attribute :>> avoided="Remove shared plain relink/read overlap and frame early READY"; attribute :>> added="Replace all queue readers/writers and seal-aware local frontier"; attribute :>> condition="Existing CAS queue gate and suffix reuse get no new credit"; }
part def Binding { attribute actionName:String; attribute lemma:String; attribute scope:String; }
part binding0:Binding { attribute :>> actionName="chunk_marker_transport.chooseAtomic"; attribute :>> lemma="MarkerTransport.chooseAtomicPreserves"; attribute :>> scope="Actual restricted typed IR; no C11 qualification"; }
part binding1:Binding { attribute :>> actionName="chunk_marker_transport.chooseSplit"; attribute :>> lemma="MarkerTransport.chooseSplitPreserves"; attribute :>> scope="Actual restricted typed IR; no C11 qualification"; }
part binding2:Binding { attribute :>> actionName="chunk_marker_transport.expose"; attribute :>> lemma="MarkerTransport.exposePreserves"; attribute :>> scope="Actual restricted typed IR; no C11 qualification"; }
part binding3:Binding { attribute :>> actionName="chunk_marker_transport.plainRead"; attribute :>> lemma="MarkerTransport.plainReadPreserves"; attribute :>> scope="Actual restricted typed IR; no C11 qualification"; }
part binding4:Binding { attribute :>> actionName="chunk_marker_transport.atomicRead"; attribute :>> lemma="MarkerTransport.atomicReadPreserves"; attribute :>> scope="Actual restricted typed IR; no C11 qualification"; }
part binding5:Binding { attribute :>> actionName="chunk_marker_transport.acquireGate"; attribute :>> lemma="MarkerTransport.acquireGatePreserves"; attribute :>> scope="Actual restricted typed IR; no C11 qualification"; }
part binding6:Binding { attribute :>> actionName="chunk_marker_transport.plainWrite"; attribute :>> lemma="MarkerTransport.plainWritePreserves"; attribute :>> scope="Actual restricted typed IR; no C11 qualification"; }
part binding7:Binding { attribute :>> actionName="chunk_marker_transport.atomicWrite"; attribute :>> lemma="MarkerTransport.atomicWritePreserves"; attribute :>> scope="Actual restricted typed IR; no C11 qualification"; }
part binding8:Binding { attribute :>> actionName="chunk_marker_transport.finishRead"; attribute :>> lemma="MarkerTransport.finishReadPreserves"; attribute :>> scope="Actual restricted typed IR; no C11 qualification"; }
part binding9:Binding { attribute :>> actionName="chunk_marker_transport.finishWrite"; attribute :>> lemma="MarkerTransport.finishWritePreserves"; attribute :>> scope="Actual restricted typed IR; no C11 qualification"; }
part binding10:Binding { attribute :>> actionName="chunk_marker_transport.releaseGate"; attribute :>> lemma="MarkerTransport.releaseGatePreserves"; attribute :>> scope="Actual restricted typed IR; no C11 qualification"; }
part binding11:Binding { attribute :>> actionName="chunk_marker_transport.retireStorage"; attribute :>> lemma="MarkerTransport.retireStoragePreserves"; attribute :>> scope="Actual restricted typed IR; no C11 qualification"; }
part binding12:Binding { attribute :>> actionName="delayed_chunk_ledger.drainStrong"; attribute :>> lemma="DelayedLedger.drainStrongPreserves"; attribute :>> scope="Actual restricted typed IR; no C11 qualification"; }
part binding13:Binding { attribute :>> actionName="delayed_chunk_ledger.freezeStrong"; attribute :>> lemma="DelayedLedger.freezeStrongPreserves"; attribute :>> scope="Actual restricted typed IR; no C11 qualification"; }
part binding14:Binding { attribute :>> actionName="delayed_chunk_ledger.classifyA"; attribute :>> lemma="DelayedLedger.classifyAPreserves"; attribute :>> scope="Actual restricted typed IR; no C11 qualification"; }
part binding15:Binding { attribute :>> actionName="delayed_chunk_ledger.classifyB"; attribute :>> lemma="DelayedLedger.classifyBPreserves"; attribute :>> scope="Actual restricted typed IR; no C11 qualification"; }
part binding16:Binding { attribute :>> actionName="delayed_chunk_ledger.enterWeak"; attribute :>> lemma="DelayedLedger.enterWeakPreserves"; attribute :>> scope="Actual restricted typed IR; no C11 qualification"; }
part binding17:Binding { attribute :>> actionName="delayed_chunk_ledger.acceptDelayed"; attribute :>> lemma="DelayedLedger.acceptDelayedPreserves"; attribute :>> scope="Actual restricted typed IR; no C11 qualification"; }
part binding18:Binding { attribute :>> actionName="delayed_chunk_ledger.sealDelayed"; attribute :>> lemma="DelayedLedger.sealDelayedPreserves"; attribute :>> scope="Actual restricted typed IR; no C11 qualification"; }
part binding19:Binding { attribute :>> actionName="delayed_chunk_ledger.publishAccepted"; attribute :>> lemma="DelayedLedger.publishAcceptedPreserves"; attribute :>> scope="Actual restricted typed IR; no C11 qualification"; }
part binding20:Binding { attribute :>> actionName="delayed_chunk_ledger.observeReceipt"; attribute :>> lemma="DelayedLedger.observeReceiptPreserves"; attribute :>> scope="Actual restricted typed IR; no C11 qualification"; }
part binding21:Binding { attribute :>> actionName="delayed_chunk_ledger.claim"; attribute :>> lemma="DelayedLedger.claimPreserves"; attribute :>> scope="Actual restricted typed IR; no C11 qualification"; }
part binding22:Binding { attribute :>> actionName="delayed_chunk_ledger.deriveChild"; attribute :>> lemma="DelayedLedger.deriveChildPreserves"; attribute :>> scope="Actual restricted typed IR; no C11 qualification"; }
part binding23:Binding { attribute :>> actionName="delayed_chunk_ledger.settleParent"; attribute :>> lemma="DelayedLedger.settleParentPreserves"; attribute :>> scope="Actual restricted typed IR; no C11 qualification"; }
part binding24:Binding { attribute :>> actionName="delayed_chunk_ledger.settleChild"; attribute :>> lemma="DelayedLedger.settleChildPreserves"; attribute :>> scope="Actual restricted typed IR; no C11 qualification"; }
part binding25:Binding { attribute :>> actionName="delayed_chunk_ledger.closeRoots"; attribute :>> lemma="DelayedLedger.closeRootsPreserves"; attribute :>> scope="Actual restricted typed IR; no C11 qualification"; }
part binding26:Binding { attribute :>> actionName="delayed_chunk_ledger.finishWeak"; attribute :>> lemma="DelayedLedger.finishWeakPreserves"; attribute :>> scope="Actual restricted typed IR; no C11 qualification"; }
part binding27:Binding { attribute :>> actionName="delayed_chunk_ledger.closeFutureUsers"; attribute :>> lemma="DelayedLedger.closeFutureUsersPreserves"; attribute :>> scope="Actual restricted typed IR; no C11 qualification"; }
part binding28:Binding { attribute :>> actionName="delayed_chunk_ledger.releaseHead"; attribute :>> lemma="DelayedLedger.releaseHeadPreserves"; attribute :>> scope="Actual restricted typed IR; no C11 qualification"; }
part binding29:Binding { attribute :>> actionName="delayed_chunk_ledger.retireEpoch"; attribute :>> lemma="DelayedLedger.retireEpochPreserves"; attribute :>> scope="Actual restricted typed IR; no C11 qualification"; }
part def Refinement { attribute actionName:String; attribute targetStep:String; attribute lemma:String; }
part refinement0:Refinement { attribute :>> actionName="delayed_chunk_ledger.drainStrong"; attribute :>> targetStep="weak_producer_admission.drainStrong"; attribute :>> lemma="TransportComposition.drainStrongSimulates"; }
part refinement1:Refinement { attribute :>> actionName="delayed_chunk_ledger.freezeStrong"; attribute :>> targetStep="weak_producer_admission.freezeStrong"; attribute :>> lemma="TransportComposition.freezeStrongSimulates"; }
part refinement2:Refinement { attribute :>> actionName="delayed_chunk_ledger.classifyA"; attribute :>> targetStep="weak_producer_admission.classifyA"; attribute :>> lemma="TransportComposition.classifyASimulates"; }
part refinement3:Refinement { attribute :>> actionName="delayed_chunk_ledger.classifyB"; attribute :>> targetStep="weak_producer_admission.classifyB"; attribute :>> lemma="TransportComposition.classifyBSimulates"; }
part refinement4:Refinement { attribute :>> actionName="delayed_chunk_ledger.enterWeak"; attribute :>> targetStep="weak_producer_admission.openWeak"; attribute :>> lemma="TransportComposition.enterWeakSimulates"; }
part refinement5:Refinement { attribute :>> actionName="delayed_chunk_ledger.acceptDelayed"; attribute :>> targetStep="weak_producer_admission.continuationProducer"; attribute :>> lemma="TransportComposition.acceptDelayedSimulates"; }
part refinement6:Refinement { attribute :>> actionName="delayed_chunk_ledger.sealDelayed"; attribute :>> targetStep="weak_producer_admission.stutter"; attribute :>> lemma="TransportComposition.sealDelayedSimulates"; }
part refinement7:Refinement { attribute :>> actionName="delayed_chunk_ledger.publishAccepted"; attribute :>> targetStep="weak_producer_admission.stutter"; attribute :>> lemma="TransportComposition.publishAcceptedSimulates"; }
part refinement8:Refinement { attribute :>> actionName="delayed_chunk_ledger.observeReceipt"; attribute :>> targetStep="weak_producer_admission.stutter"; attribute :>> lemma="TransportComposition.observeReceiptSimulates"; }
part refinement9:Refinement { attribute :>> actionName="delayed_chunk_ledger.claim"; attribute :>> targetStep="weak_producer_admission.stutter"; attribute :>> lemma="TransportComposition.claimSimulates"; }
part refinement10:Refinement { attribute :>> actionName="delayed_chunk_ledger.deriveChild"; attribute :>> targetStep="weak_producer_admission.deriveChild"; attribute :>> lemma="TransportComposition.deriveChildSimulates"; }
part refinement11:Refinement { attribute :>> actionName="delayed_chunk_ledger.settleParent"; attribute :>> targetStep="weak_producer_admission.settleTask"; attribute :>> lemma="TransportComposition.settleParentSimulates"; }
part refinement12:Refinement { attribute :>> actionName="delayed_chunk_ledger.settleChild"; attribute :>> targetStep="weak_producer_admission.settleTask"; attribute :>> lemma="TransportComposition.settleChildSimulates"; }
part refinement13:Refinement { attribute :>> actionName="delayed_chunk_ledger.closeRoots"; attribute :>> targetStep="weak_producer_admission.closeRoots"; attribute :>> lemma="TransportComposition.closeRootsSimulates"; }
part refinement14:Refinement { attribute :>> actionName="delayed_chunk_ledger.finishWeak"; attribute :>> targetStep="weak_producer_admission.finishWeak"; attribute :>> lemma="TransportComposition.finishWeakSimulates"; }
part refinement15:Refinement { attribute :>> actionName="delayed_chunk_ledger.closeFutureUsers"; attribute :>> targetStep="weak_producer_admission.stutter"; attribute :>> lemma="TransportComposition.closeFutureUsersSimulates"; }
part refinement16:Refinement { attribute :>> actionName="delayed_chunk_ledger.releaseHead"; attribute :>> targetStep="weak_producer_admission.stutter"; attribute :>> lemma="TransportComposition.releaseHeadSimulates"; }
part refinement17:Refinement { attribute :>> actionName="delayed_chunk_ledger.retireEpoch"; attribute :>> targetStep="weak_producer_admission.stutter"; attribute :>> lemma="TransportComposition.retireEpochSimulates"; }
part def Composition { attribute key:String; attribute lemma:String; attribute scope:String; }
part composition0:Composition { attribute :>> key="marker-induction"; attribute :>> lemma="MarkerTransport.reachableSafe"; attribute :>> scope="All access protocol steps"; }
part composition1:Composition { attribute :>> key="mixed-access"; attribute :>> lemma="MarkerTransport.noMixedSharedAccess"; attribute :>> scope="Managed modes only; no weak-memory theorem"; }
part composition2:Composition { attribute :>> key="ledger-induction"; attribute :>> lemma="DelayedLedger.reachableSafe"; attribute :>> scope="All ledger steps"; }
part composition3:Composition { attribute :>> key="balance"; attribute :>> lemma="DelayedLedger.workConservation"; attribute :>> scope="Accepted minus settled work"; }
part composition4:Composition { attribute :>> key="publication"; attribute :>> lemma="DelayedLedger.publicationPreservesDebt"; attribute :>> scope="No new debt at queue visibility"; }
part composition5:Composition { attribute :>> key="pins"; attribute :>> lemma="DelayedLedger.retirementRequiresNoPins"; attribute :>> scope="Epoch retirement excludes work and storage pins"; }
part composition6:Composition { attribute :>> key="step-refinement"; attribute :>> lemma="TransportComposition.stepSimulates"; attribute :>> scope="Exact old weak AST actions plus stutter"; }
part composition7:Composition { attribute :>> key="reachable-refinement"; attribute :>> lemma="TransportComposition.reachableProjects"; attribute :>> scope="New reachability mapped to old reachability"; }
part composition8:Composition { attribute :>> key="old-safety"; attribute :>> lemma="TransportComposition.projectedSafety"; attribute :>> scope="Old weak invariant reused"; }
part composition9:Composition { attribute :>> key="product-step"; attribute :>> lemma="TransportComposition.combinedStepPreserves"; attribute :>> scope="Two added admission guards are necessary premises"; }
part composition10:Composition { attribute :>> key="product-induction"; attribute :>> lemma="TransportComposition.combinedReachableSafe"; attribute :>> scope="Guarded interleaving product"; }
part composition11:Composition { attribute :>> key="publish-gate"; attribute :>> lemma="TransportComposition.publicationUsesManagedTransport"; attribute :>> scope="Transport permit at new queue publication"; }
part composition12:Composition { attribute :>> key="free-counterexample"; attribute :>> lemma="TransportComposition.lifetimeGuardNecessary"; attribute :>> scope="Removing lifetime guard admits invalid storage free"; }
part composition13:Composition { attribute :>> key="publish-counterexample"; attribute :>> lemma="TransportComposition.transportGuardNecessary"; attribute :>> scope="Separate passes alone admit legacy publish"; }
part def Access { attribute key:String; ref part source:Source; attribute callerName:String; attribute accessMode:String; attribute lane:String; attribute lock:String; attribute scope:String; }
part access0:Access { ref part :>> source=source0; attribute :>> key="marker-initialize"; attribute :>> callerName="end_heap_chunk / prepare_heap_msection"; attribute :>> accessMode="plain write"; attribute :>> lane="shared marker"; attribute :>> lock="before publication"; attribute :>> scope="All initialization before consumer reads"; }
part access1:Access { ref part :>> source=source1; attribute :>> key="queue-relink"; attribute :>> callerName="end_heap_chunk"; attribute :>> accessMode="plain write"; attribute :>> lane="shared marker / queue next"; attribute :>> lock="FIFO gate"; attribute :>> scope="Reader outside gate still needs atomic/separate protocol"; }
part access2:Access { ref part :>> source=source2; attribute :>> key="queue-consume"; attribute :>> callerName="take_heap_chunk"; attribute :>> accessMode="plain read"; attribute :>> lane="queue next"; attribute :>> lock="FIFO gate"; attribute :>> scope="Node survives as new dummy head"; }
part access3:Access { ref part :>> source=source3; attribute :>> key="complete-classify"; attribute :>> callerName="scan_complete_heap_chunk"; attribute :>> accessMode="plain read"; attribute :>> lane="object header or terminal"; attribute :>> lock="no FIFO gate"; attribute :>> scope="Victim may publish later chunks concurrently"; }
part access4:Access { ref part :>> source=source3; attribute :>> key="local-classify"; attribute :>> callerName="scan_movable_objs_to_scan"; attribute :>> accessMode="plain read"; attribute :>> lane="object header or terminal"; attribute :>> lock="local work owner"; attribute :>> scope="Same-carrier writes alone do not establish cross-thread witness"; }
part access5:Access { ref part :>> source=source6; attribute :>> key="queue-dummy"; attribute :>> callerName="setup_stack_heap_vmstate"; attribute :>> accessMode="pointer retention"; attribute :>> lane="queue dummy/head"; attribute :>> lock="epoch setup collective"; attribute :>> scope="Work zero does not remove storage reference"; }
part access6:Access { ref part :>> source=source4; attribute :>> key="address-alias"; attribute :>> callerName="end_heap_chunk"; attribute :>> accessMode="address derivation"; attribute :>> lane="previous terminal"; attribute :>> lock="not a memory access"; attribute :>> scope="Needs adjacent physical chunks and later relink"; }
part access7:Access { ref part :>> source=source17; attribute :>> key="epoch-reset"; attribute :>> callerName="setup_stack_heap_vmstate"; attribute :>> accessMode="plain reset"; attribute :>> lane="queue root"; attribute :>> lock="GC setup collective"; attribute :>> scope="All old queue users and receipts retired"; }
part frameHistory:GambitAssuranceRouting::ModelNeed { ref part :>> owner=GambitAssuranceRelations::modelUse3; attribute :>> obligationId="TL-frameHistory"; attribute :>> kind="interleaving"; attribute :>> subjectPath="dev/refactoring/modern-c/models/quint/chunk_marker_transport.qnt"; attribute :>> subjectScope="Legacy overlap atomic and split access intervals"; attribute :>> premise="Design and formal models only; no native qualification"; }
part weakHistory:GambitAssuranceRouting::ModelNeed { ref part :>> owner=GambitAssuranceRelations::modelUse3; attribute :>> obligationId="TL-weakHistory"; attribute :>> kind="interleaving"; attribute :>> subjectPath="dev/refactoring/modern-c/models/quint/delayed_chunk_ledger.qnt"; attribute :>> subjectScope="Private queued child work and retained pins"; attribute :>> premise="Design and formal models only; no native qualification"; }
part frameInduction:GambitAssuranceRouting::ModelNeed { ref part :>> owner=GambitAssuranceRelations::modelUse3; attribute :>> obligationId="TL-frameInduction"; attribute :>> kind="induction"; attribute :>> subjectPath="dev/refactoring/modern-c/models/lean/MarkerTransport.lean"; attribute :>> subjectScope="All access steps"; attribute :>> premise="Design and formal models only; no native qualification"; }
part weakInduction:GambitAssuranceRouting::ModelNeed { ref part :>> owner=GambitAssuranceRelations::modelUse3; attribute :>> obligationId="TL-weakInduction"; attribute :>> kind="induction"; attribute :>> subjectPath="dev/refactoring/modern-c/models/lean/DelayedLedger.lean"; attribute :>> subjectScope="All work and pin steps"; attribute :>> premise="Design and formal models only; no native qualification"; }
part compositionProof:GambitAssuranceRouting::ModelNeed { ref part :>> owner=GambitAssuranceRelations::modelUse3; attribute :>> obligationId="TL-compositionProof"; attribute :>> kind="induction"; attribute :>> subjectPath="dev/refactoring/modern-c/models/lean/TransportComposition.lean"; attribute :>> subjectScope="Old AST step simulation and guarded transport/ledger product"; attribute :>> premise="Design and formal models only; no native qualification"; }
part projection:GambitAssuranceRouting::ModelNeed { ref part :>> owner=GambitAssuranceRelations::modelUse3; attribute :>> obligationId="TL-projection"; attribute :>> kind="restricted-projection"; attribute :>> subjectPath="dev/refactoring/modern-c/models/lean/DelayedLedgerAst.lean"; attribute :>> subjectScope="Both new ASTs and exact pinned old weak AST"; attribute :>> premise="Design and formal models only; no native qualification"; }
part source:GambitAssuranceRouting::ModelNeed { ref part :>> owner=GambitAssuranceRelations::modelUse3; attribute :>> obligationId="TL-source"; attribute :>> kind="source-refinement"; attribute :>> subjectPath="dev/refactoring/modern-c/chunk-transport-ledger-design.org"; attribute :>> subjectScope="Actual sentinel access node layout and same ledger mapping open"; attribute :>> premise="Design and formal models only; no native qualification"; }
part platform:GambitAssuranceRouting::ModelNeed { ref part :>> owner=GambitAssuranceRelations::modelUse3; attribute :>> obligationId="TL-platform"; attribute :>> kind="native-memory-order"; attribute :>> subjectPath="dev/refactoring/modern-c/chunk-transport-ledger-design.org"; attribute :>> subjectScope="Effective storage atomic profile reads-from and epoch reclamation open"; attribute :>> premise="Design and formal models only; no native qualification"; }
part def Seam { ref part producer:GambitRuntimeComposition::BlueprintModule; ref part consumer:GambitRuntimeComposition::BlueprintModule; attribute contract:String; attribute modelNeed:String; }
part seam0:Seam { ref part :>> producer=GambitRuntimeComposition::blueprintModule4; ref part :>> consumer=GambitRuntimeComposition::blueprintModule1; attribute :>> contract="Marker/link storage ABI and accesses"; attribute :>> modelNeed="TL-platform"; }
part seam1:Seam { ref part :>> producer=GambitRuntimeComposition::blueprintModule4; ref part :>> consumer=GambitRuntimeComposition::blueprintModule4; attribute :>> contract="Delayed chunk is one accepted task"; attribute :>> modelNeed="TL-weakInduction"; }
part seam2:Seam { ref part :>> producer=GambitRuntimeComposition::blueprintModule4; ref part :>> consumer=GambitRuntimeComposition::blueprintModule5; attribute :>> contract="Frozen list cut and future-user closure"; attribute :>> modelNeed="TL-compositionProof"; }
part seam3:Seam { ref part :>> producer=GambitRuntimeComposition::blueprintModule3; ref part :>> consumer=GambitRuntimeComposition::blueprintModule4; attribute :>> contract="Physical frame seal and retained stack roots"; attribute :>> modelNeed="TL-source"; }
}
