package GambitSourceOwnerRegistry { private import ScalarValues::*;
part def Owner { attribute componentId:String; }
part registryOwner:Owner { attribute :>> componentId="registry"; }
part writerOwner:Owner { attribute :>> componentId="writer"; }
part guardOwner:Owner { attribute :>> componentId="guard"; }
part rootsOwner:Owner { attribute :>> componentId="roots"; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-init"; attribute :>> path="vendor/gambit/lib/memory/rc-allocation.inc"; attribute :>> needle="h->data = ___FAL;"; attribute :>> obligation="Native allocation initializes data before registration; not a source lease"; }
part source4:SourceRow { attribute :>> key="rc-register"; attribute :>> path="vendor/gambit/lib/memory/rc-allocation.inc"; attribute :>> needle="tail->next = h;"; attribute :>> obligation="Plain list insertion requires owner and collector exclusion"; }
part source5:SourceRow { attribute :>> key="rc-free"; attribute :>> path="vendor/gambit/lib/memory/rc-allocation.inc"; attribute :>> needle="if (--h->refcount == 0)"; attribute :>> obligation="Nonatomic decrement and unlink are not safe arbitrary-thread admission"; }
part source6:SourceRow { attribute :>> key="rc-retain"; attribute :>> path="vendor/gambit/lib/memory/rc-allocation.inc"; attribute :>> needle="h->refcount++;"; attribute :>> obligation="Dereferences existing header; cannot safely retain already-freed raw client_data"; }
part source7:SourceRow { attribute :>> key="rc-read"; attribute :>> path="vendor/gambit/lib/memory/rc-allocation.inc"; attribute :>> needle="return h->data;"; attribute :>> obligation="Raw native copy is not a registered update slot"; }
part source8:SourceRow { attribute :>> key="rc-write"; attribute :>> path="vendor/gambit/lib/memory/rc-allocation.inc"; attribute :>> needle="h->data = val;"; attribute :>> obligation="All semantic writers must join freeze/generation protocol or deny admission"; }
part source9:SourceRow { attribute :>> key="rc-cleanup"; attribute :>> path="vendor/gambit/lib/memory/rc-allocation.inc"; attribute :>> needle="___HIDDEN void cleanup_rc"; attribute :>> obligation="Bulk cleanup frees chain independent of per-entry leases"; }
part source10:SourceRow { attribute :>> key="rc-scan"; attribute :>> path="vendor/gambit/lib/memory/rc-roots.inc"; attribute :>> needle="mark_array (work, &h->data, 1);"; attribute :>> obligation="Actual GC slot update; target private carrier is not implicitly scanned"; }
part source11:SourceRow { attribute :>> key="retire-refuse"; attribute :>> path="vendor/gambit/lib/memory/capacity-resize.inc"; attribute :>> needle="return 0; /* no freeze receipt for external RC/native borrowers */"; attribute :>> obligation="Current processor retirement refuses nonempty RC rather than manufacturing a lease"; }
part source12:SourceRow { attribute :>> key="pstate-cleanup"; attribute :>> path="vendor/gambit/lib/memory/memory-lifecycle.inc"; attribute :>> needle="free_still_objs (___ps);"; attribute :>> obligation="cleanup_mem_pstate frees still storage before cleanup_rc; not an active-lease release helper"; }
part source13:SourceRow { attribute :>> key="vm-cleanup"; attribute :>> path="vendor/gambit/lib/memory/memory-lifecycle.inc"; attribute :>> needle="___cleanup_mem_pstate (___PSTATE_FROM_PROCESSOR_ID(0,___vms));"; attribute :>> obligation="VM cleanup still has other-processors TODO; global retirement qualification cannot be inferred"; }
part source14:SourceRow { attribute :>> key="pstate-wrapper"; attribute :>> path="vendor/gambit/lib/setup.c"; attribute :>> needle="___cleanup_mem_pstate (___ps);"; attribute :>> obligation="PSTATE cleanup wrapper reaches destructive memory cleanup before OS cleanup"; }
part source15:SourceRow { attribute :>> key="setter-export"; attribute :>> path="vendor/gambit/lib/setup.c"; attribute :>> needle="= ___set_data_rc;"; attribute :>> obligation="Public GSTATE function pointer permits indirect/out-of-tree callers; lexical sites do not close writer authority"; }
part source16:SourceRow { attribute :>> key="register-export"; attribute :>> path="vendor/gambit/lib/setup.c"; attribute :>> needle="= ___register_rc;"; attribute :>> obligation="Public registration ABI is not a stable VM SourceOwner registry"; }
part source17:SourceRow { attribute :>> key="context-owner"; attribute :>> path="vendor/gambit/lib/memory/configuration.inc"; attribute :>> needle="#define rc_head                 ___CONTEXT_MEM(rc_head_)"; attribute :>> obligation="RC chain belongs to context; not independent VM owner identity"; }
part source18:SourceRow { attribute :>> key="closure-writer"; attribute :>> path="vendor/gambit/lib/os_dyn.c"; attribute :>> needle="___set_data_rc (c_closure, proc);"; attribute :>> obligation="Concrete semantic payload installer, architecture conditional"; }
part source19:SourceRow { attribute :>> key="closure-release"; attribute :>> path="vendor/gambit/lib/os_dyn.c"; attribute :>> needle="___release_rc (c_closure);"; attribute :>> obligation="Indirect function release reaches native RC retirement"; }
part source20:SourceRow { attribute :>> key="release-function"; attribute :>> path="vendor/gambit/lib/c_intf.c"; attribute :>> needle="if (___is_a_c_closure (x))"; attribute :>> obligation="Function retain/release wrappers reach RC API conditionally"; }
part source21:SourceRow { attribute :>> key="release-string"; attribute :>> path="vendor/gambit/lib/c_intf.c"; attribute :>> needle="___EXP_FUNC(void,___release_string)"; attribute :>> obligation="RC API also owns native buffers; root-bearing sources must be classified separately"; }
part source22:SourceRow { attribute :>> key="tls-release"; attribute :>> path="vendor/gambit/lib/os_io.c"; attribute :>> needle="___SCMOBJ ___release_rc_tls_context"; attribute :>> obligation="Native destructor has SSL/string effects; not all RC users are Scheme root sources"; }
part source23:SourceRow { attribute :>> key="epoch-limit"; attribute :>> path="vendor/gambit/lib/memory/heap-sections.inc"; attribute :>> needle="if (___vms->gc_round.epoch >= ___MAX_FIX)"; attribute :>> obligation="Existing round identity refuses exhaustion; no unchecked wrapping receipt"; }
part source24:SourceRow { attribute :>> key="epoch-new"; attribute :>> path="vendor/gambit/lib/memory/heap-sections.inc"; attribute :>> needle="___vms->gc_round.epoch++;"; attribute :>> obligation="Round number created at setup, distinct from semantic payload generation"; }
part source25:SourceRow { attribute :>> key="origin-publish"; attribute :>> path="vendor/gambit/lib/memory/heap-sections.inc"; attribute :>> needle="!___gc_root_task_publish(&___vms->gc_root_tasks[i],"; attribute :>> obligation="Publish follows frozen origin; not generic new-source enrollment"; }
part source26:SourceRow { attribute :>> key="origin-claim"; attribute :>> path="vendor/gambit/lib/memory/collection-round.inc"; attribute :>> needle="if (___gc_root_task_claim(task,___vms->gc_round.epoch,owner))"; attribute :>> obligation="Actual claim checks current round and worker owner"; }
part source27:SourceRow { attribute :>> key="origin-finish"; attribute :>> path="vendor/gambit/lib/memory/collection-round.inc"; attribute :>> needle="if (!___gc_root_task_finish(task,___vms->gc_round.epoch,owner))"; attribute :>> obligation="Task finish has exact owner and epoch boundary"; }
part source28:SourceRow { attribute :>> key="origin-thaw"; attribute :>> path="vendor/gambit/lib/memory/collection-round.inc"; attribute :>> needle="if (!___gc_origin_thaw(&___vms->gc_root_tasks[id],___vms->gc_round.epoch))"; attribute :>> obligation="Resume requires completed origin; not a payload-version receipt"; }
part source29:SourceRow { attribute :>> key="view-drain"; attribute :>> path="vendor/gambit/lib/memory/collection-round.inc"; attribute :>> needle="BARRIER(); /* no worker may retain a stopped root view past this cut */"; attribute :>> obligation="Root view grace cut precedes ordinary execution"; }
part source30:SourceRow { attribute :>> key="growth-cleanup"; attribute :>> path="vendor/gambit/lib/setup.c"; attribute :>> needle="___cleanup_pstate (___PSTATE_FROM_PROCESSOR_ID(i,vms));"; attribute :>> obligation="Known failed growth joins before destructive cleanup; unknown join retains"; }
part source31:SourceRow { attribute :>> key="shrink-cleanup"; attribute :>> path="vendor/gambit/lib/setup.c"; attribute :>> needle="___transfer_retired_still (ps, ___ps);"; attribute :>> obligation="Shrink known join transfers still before cleanup; does not qualify arbitrary native roots"; }
part source32:SourceRow { attribute :>> key="vm-root-retained"; attribute :>> path="vendor/gambit/lib/setup.c"; attribute :>> needle="return; /* do not erase retained source roots through repeated setup */"; attribute :>> obligation="Whole VM cleanup checks resize source requests; generic SourceRegistry not covered"; }
part source33:SourceRow { attribute :>> key="register-abi"; attribute :>> path="vendor/gambit/include/gambit.h"; attribute :>> needle="void *(*___register_rc)"; attribute :>> obligation="Inspected exported return type differs from void implementation spelling; effective header/profile correspondence open"; }
part def IdentityRow { attribute key:String; attribute structure:String; attribute rule:String; attribute caveat:String; }
part identity0:IdentityRow { attribute :>> key="owner"; attribute :>> structure="VM SourceSlotId + owner generation"; attribute :>> rule="Register complete immutable descriptor and root before exposing source lookup"; attribute :>> caveat="Current context RC list is not such a descriptor"; }
part identity1:IdentityRow { attribute :>> key="writer"; attribute :>> structure="SourceId + WriteOperationId + candidate root"; attribute :>> rule="Accepted writer survives close; keyed completion cannot target next operation"; attribute :>> caveat="Unbounded abstract IDs do not prove finite native overflow"; }
part identity2:IdentityRow { attribute :>> key="payload"; attribute :>> structure="Semantic payload generation"; attribute :>> rule="Frozen for source pins; old target carries independent prior generation"; attribute :>> caveat="GC relocation does not increment this semantic generation"; }
part identity3:IdentityRow { attribute :>> key="round"; attribute :>> structure="CollectorRoundId + root descriptor generation + scan owner"; attribute :>> rule="Refresh round receipt after GC; do not equate with payload generation"; attribute :>> caveat="Task completion is not by itself source admission"; }
part identity4:IdentityRow { attribute :>> key="target"; attribute :>> structure="CarrierId + bound payload generation"; attribute :>> rule="Old carrier remains rooted if new source payload is installed"; attribute :>> caveat="Backing storage and module/context grace still require owners"; }
part def IssuerRow { attribute key:String; attribute proposedIssuer:String; attribute actualSource:String; attribute status:String; attribute responsibility:String; }
part issuer0:IssuerRow { attribute :>> key="registration"; attribute :>> proposedIssuer="VM SourceRegistry owner"; attribute :>> actualSource="setup_rc/register_rc set context list links; exported through GSTATE"; attribute :>> status="No complete stable SourceOwner registration identified"; attribute :>> responsibility="Reserve descriptor, root and generation then publish lookup"; }
part issuer1:IssuerRow { attribute :>> key="writer"; attribute :>> proposedIssuer="Managed payload setter owner"; attribute :>> actualSource="Only direct semantic setter sites found in Tcl and C closure; public setter escapes"; attribute :>> status="All indirect/out-of-tree writers unclosed"; attribute :>> responsibility="Root candidate; serialize source pins; retain accepted/unknown write on close"; }
part issuer2:IssuerRow { attribute :>> key="round"; attribute :>> proposedIssuer="Collector root-origin publisher and final grace owner"; attribute :>> actualSource="epoch increment, origin publish, claim, finish and thaw found"; attribute :>> status="Partial real round signers; carrier/source registration gap remains"; attribute :>> responsibility="Bind descriptor/epoch; renew after round transition"; }
part issuer3:IssuerRow { attribute :>> key="pin"; attribute :>> proposedIssuer="Stable source adapter and per-source admission owner"; attribute :>> actualSource="Current raw data/refcount APIs do not validate stable owner identity"; attribute :>> status="Native pin issuer absent"; attribute :>> responsibility="Check published source, generation and writer state without allocation"; }
part issuer4:IssuerRow { attribute :>> key="reservation"; attribute :>> proposedIssuer="Stable host guard commit owner"; attribute :>> actualSource="Prior rooted helper and guard designs only"; attribute :>> status="Exact native lookup and outcomes unimplemented"; attribute :>> responsibility="Unknown record retains source pin and target"; }
part issuer5:IssuerRow { attribute :>> key="cleanup"; attribute :>> proposedIssuer="Registry close plus storage/scanner owners"; attribute :>> actualSource="Known resize failure/shrink cleanup and retained-source checks found"; attribute :>> status="Whole SourceRegistry closed manifest not implemented"; attribute :>> responsibility="Drain accepted writes/pins, root scans and storage; then bulk cleanup"; }
part def ClaimRow { attribute key:String; attribute mechanism:String; attribute condition:String; attribute result:String; attribute gap:String; }
part claim0:ClaimRow { attribute :>> key="registration"; attribute :>> mechanism="Private descriptor then rooted publication"; attribute :>> condition="Stable lookup storage and no late publish after registry close"; attribute :>> result="No public owner with an uninitialized source root"; attribute :>> gap="Real record allocator and ABI mapping open"; }
part claim1:ClaimRow { attribute :>> key="writers"; attribute :>> mechanism="Close rejects new operations but accepted writer stays rooted"; attribute :>> condition="Managed setter and raw escape closure"; attribute :>> result="Unknown accepted writer prevents cleanup"; attribute :>> gap="Actual mutation/FFI/callback authority census incomplete"; }
part claim2:ClaimRow { attribute :>> key="write-key"; attribute :>> mechanism="WriteId monotone; witness key must match active operation"; attribute :>> condition="Trusted commit witness and rooted candidate"; attribute :>> result="Old completion cannot commit the next write"; attribute :>> gap="Full result cache and native ID reuse open"; }
part claim3:ClaimRow { attribute :>> key="round"; attribute :>> mechanism="Round ack or qualified persistent root-domain coverage"; attribute :>> condition="Actual target remains enrolled/updated"; attribute :>> result="Round-scoped old ack cannot release source pin; persistent coverage is a distinct admitted premise"; attribute :>> gap="Round receipt to native slot/descriptor correspondence open"; }
part claim4:ClaimRow { attribute :>> key="old-view"; attribute :>> mechanism="Target keeps bound prior payload generation"; attribute :>> condition="Independent target GC/storage ownership"; attribute :>> result="New payload install does not rewrite old target binding"; attribute :>> gap="No proof arbitrary managed mutation preserves all Scheme observations"; }
part claim5:ClaimRow { attribute :>> key="cleanup"; attribute :>> mechanism="Closed registry manifest plus per-source drains and storage receipt"; attribute :>> condition="Single modeled source; no raw registration bypass"; attribute :>> result="Accepted/unknown writes, nested pins block cleanup"; attribute :>> gap="Unbounded member roster and native cleanup composition not proved"; }
part claim6:ClaimRow { attribute :>> key="persistent-profile"; attribute :>> mechanism="Separate round completion from persistent root enrollment"; attribute :>> condition="Trusted descriptor lifetime and all-round scan coverage"; attribute :>> result="A prior round ack need not be renewed solely because another GC occurred"; attribute :>> gap="Current source has round tasks, not a complete generic persistent carrier signer"; }
part def MemoryRow { attribute key:String; attribute publication:String; attribute observation:String; attribute obligation:String; attribute overhead:String; }
part memory0:MemoryRow { attribute :>> key="publish"; attribute :>> publication="Fully initialize owner descriptor and root then publish handle"; attribute :>> observation="Acquire lookup pins stable generation"; attribute :>> obligation="GC metadata enrollment precedes handle exposure; no freed-header CAS"; attribute :>> overhead="Reserved registry slot and generation"; }
part memory1:MemoryRow { attribute :>> key="write"; attribute :>> publication="Candidate rooted before accepting operation; commit under root access"; attribute :>> observation="Pins see one semantic payload generation"; attribute :>> obligation="Close cannot cancel accepted write by clearing count; no lock across GC"; attribute :>> overhead="Rooted candidate, operation record and short serial point"; }
part memory2:MemoryRow { attribute :>> key="round"; attribute :>> publication="Bind exact root descriptor and GC round; refresh after thaw"; attribute :>> observation="Pin return sees current round or qualified persistent enrollment, plus committed guard"; attribute :>> obligation="Avoid holding metadata lock while waiting for old collective"; attribute :>> overhead="Epoch query/ack and target scan work"; }
part memory3:MemoryRow { attribute :>> key="snapshot"; attribute :>> publication="Each target binds its payload generation"; attribute :>> observation="Writer can install new generation after source pins return"; attribute :>> obligation="Old target stays scan-visible; not updated to new semantic object"; attribute :>> overhead="Independent target roots and storage retention"; }
part memory4:MemoryRow { attribute :>> key="cleanup"; attribute :>> publication="Close new owner registration and seal complete manifest"; attribute :>> observation="Drained member receipts permit source removal"; attribute :>> obligation="No late members, unknown writes or scanner borrows; storage receipt required"; attribute :>> overhead="Registry census and deferred cleanup coordination"; }
part def GainRow { attribute key:String; attribute avoided:String; attribute added:String; attribute condition:String; }
part gain0:GainRow { attribute :>> key="sparse-roots"; attribute :>> avoided="Potential N_RC minus N_payload root-slot visits per GC"; attribute :>> added="Classified root index, setter updates and close protocol"; attribute :>> condition="All root-bearing sources admitted; raw callers retain conservative scan fallback"; }
part gain1:GainRow { attribute :>> key="root-reuse"; attribute :>> avoided="Extra carrier copies for already qualified RC sources"; attribute :>> added="Pin and root-origin checks"; attribute :>> condition="Reuse existing registered source when independent lifetime not needed"; }
part gain2:GainRow { attribute :>> key="shared-owner"; attribute :>> avoided="Duplicate component-specific registration/close bookkeeping"; attribute :>> added="Shared registry ABI, rooted candidates and exact receipts"; attribute :>> condition="Actually retire old callers rather than keep duplicate protocols"; }
part gain3:GainRow { attribute :>> key="overlap"; attribute :>> avoided="Serializing source replacement until every old execution ends"; attribute :>> added="Independent generation-bound carrier roots"; attribute :>> condition="No live source pin; old target backing storage retained"; }
part gain4:GainRow { attribute :>> key="unknown"; attribute :>> avoided="Blind re-execution and guessed-failure cleanup"; attribute :>> added="Queries and retained candidate/source/target storage"; attribute :>> condition="Exact owner survives; no bounded retention/liveness theorem"; }
part gain5:GainRow { attribute :>> key="persistent-coverage"; attribute :>> avoided="Per-GC acknowledgement renewal for continuously registered carriers"; attribute :>> added="Root-domain lifetime and descriptor-generation proof; close/reclaim checks"; attribute :>> condition="Every round updates the same live slot; no untracked deregistration, reuse or migration"; }
part def ContractRow { attribute fromNode:String; attribute toNode:String; attribute custody:String; }
part contract0:ContractRow { attribute :>> fromNode="Private SourceOwner"; attribute :>> toNode="Root enrollment"; attribute :>> custody="root and descriptor before public lookup"; }
part contract1:ContractRow { attribute :>> fromNode="Root enrollment"; attribute :>> toNode="Published SourceOwner"; attribute :>> custody="VM identity and generation; qualified GC coverage"; }
part contract2:ContractRow { attribute :>> fromNode="Published SourceOwner"; attribute :>> toNode="Accepted writer"; attribute :>> custody="root candidate and issue exact WriteOperationId"; }
part contract3:ContractRow { attribute :>> fromNode="Published SourceOwner"; attribute :>> toNode="Source pins"; attribute :>> custody="no unclassified writer overlap"; }
part contract4:ContractRow { attribute :>> fromNode="Accepted writer"; attribute :>> toNode="Closing SourceOwner"; attribute :>> custody="accepted work survives admission close"; }
part contract5:ContractRow { attribute :>> fromNode="Closing SourceOwner"; attribute :>> toNode="Writer outcome"; attribute :>> custody="same keyed owner resolves unknown operation"; }
part contract6:ContractRow { attribute :>> fromNode="Source pins"; attribute :>> toNode="Generation-bound carrier"; attribute :>> custody="independent old payload snapshot"; }
part contract7:ContractRow { attribute :>> fromNode="Generation-bound carrier"; attribute :>> toNode="Coverage receipt"; attribute :>> custody="current round or qualified persistent root-domain enrollment"; }
part contract8:ContractRow { attribute :>> fromNode="Coverage receipt"; attribute :>> toNode="Exact pin return"; attribute :>> custody="known guard outcome and valid coverage before source lease drops"; }
part contract9:ContractRow { attribute :>> fromNode="Closing SourceOwner"; attribute :>> toNode="Closed registry manifest"; attribute :>> custody="exclude late source registration"; }
part contract10:ContractRow { attribute :>> fromNode="Closed registry manifest"; attribute :>> toNode="Cleanup permit"; attribute :>> custody="writes pins scans and storage settled"; }
part contract11:ContractRow { attribute :>> fromNode="Cleanup permit"; attribute :>> toNode="cleanup_rc replacement boundary"; attribute :>> custody="no raw bulk bypass while roots retained"; }
part contract12:ContractRow { attribute :>> fromNode="Writer outcome"; attribute :>> toNode="Cleanup permit"; attribute :>> custody="known terminal writer outcome; candidate root custody settled"; }
part contract13:ContractRow { attribute :>> fromNode="Exact pin return"; attribute :>> toNode="Cleanup permit"; attribute :>> custody="all accepted source pins settled; target roots independent"; }
part contract14:ContractRow { attribute :>> fromNode="Closing SourceOwner"; attribute :>> toNode="Source scan grace"; attribute :>> custody="close source root view after handoff"; }
part contract15:ContractRow { attribute :>> fromNode="Source scan grace"; attribute :>> toNode="Cleanup permit"; attribute :>> custody="no admitted reader retains source descriptor"; }
part def BindingRow { attribute actionName:String; attribute lemma:String; attribute scope:String; }
part binding0:BindingRow { attribute :>> actionName="source_owner_registry.reserveOwner"; attribute :>> lemma="SourceOwner.reserveOwnerPreserves"; attribute :>> scope="one owner, two pins, current write identity; native refinement open"; }
part binding1:BindingRow { attribute :>> actionName="source_owner_registry.prepareRoot"; attribute :>> lemma="SourceOwner.prepareRootPreserves"; attribute :>> scope="one owner, two pins, current write identity; native refinement open"; }
part binding2:BindingRow { attribute :>> actionName="source_owner_registry.publishOwner"; attribute :>> lemma="SourceOwner.publishOwnerPreserves"; attribute :>> scope="one owner, two pins, current write identity; native refinement open"; }
part binding3:BindingRow { attribute :>> actionName="source_owner_registry.abortPrivate"; attribute :>> lemma="SourceOwner.abortPrivatePreserves"; attribute :>> scope="one owner, two pins, current write identity; native refinement open"; }
part binding4:BindingRow { attribute :>> actionName="source_owner_registry.closeRegistry"; attribute :>> lemma="SourceOwner.closeRegistryPreserves"; attribute :>> scope="one owner, two pins, current write identity; native refinement open"; }
part binding5:BindingRow { attribute :>> actionName="source_owner_registry.closeOwner"; attribute :>> lemma="SourceOwner.closeOwnerPreserves"; attribute :>> scope="one owner, two pins, current write identity; native refinement open"; }
part binding6:BindingRow { attribute :>> actionName="source_owner_registry.sealRoster"; attribute :>> lemma="SourceOwner.sealRosterPreserves"; attribute :>> scope="one owner, two pins, current write identity; native refinement open"; }
part binding7:BindingRow { attribute :>> actionName="source_owner_registry.rejectLate"; attribute :>> lemma="SourceOwner.rejectLatePreserves"; attribute :>> scope="one owner, two pins, current write identity; native refinement open"; }
part binding8:BindingRow { attribute :>> actionName="source_owner_registry.beginWrite"; attribute :>> lemma="SourceOwner.beginWritePreserves"; attribute :>> scope="one owner, two pins, current write identity; native refinement open"; }
part binding9:BindingRow { attribute :>> actionName="source_owner_registry.unknownWrite"; attribute :>> lemma="SourceOwner.unknownWritePreserves"; attribute :>> scope="one owner, two pins, current write identity; native refinement open"; }
part binding10:BindingRow { attribute :>> actionName="source_owner_registry.presentCurrentWrite"; attribute :>> lemma="SourceOwner.presentCurrentWritePreserves"; attribute :>> scope="one owner, two pins, current write identity; native refinement open"; }
part binding11:BindingRow { attribute :>> actionName="source_owner_registry.presentOldWrite"; attribute :>> lemma="SourceOwner.presentOldWritePreserves"; attribute :>> scope="one owner, two pins, current write identity; native refinement open"; }
part binding12:BindingRow { attribute :>> actionName="source_owner_registry.commitWrite"; attribute :>> lemma="SourceOwner.commitWritePreserves"; attribute :>> scope="one owner, two pins, current write identity; native refinement open"; }
part binding13:BindingRow { attribute :>> actionName="source_owner_registry.abortWrite"; attribute :>> lemma="SourceOwner.abortWritePreserves"; attribute :>> scope="one owner, two pins, current write identity; native refinement open"; }
part binding14:BindingRow { attribute :>> actionName="source_owner_registry.queryWrite"; attribute :>> lemma="SourceOwner.queryWritePreserves"; attribute :>> scope="one owner, two pins, current write identity; native refinement open"; }
part binding15:BindingRow { attribute :>> actionName="source_owner_registry.pin0"; attribute :>> lemma="SourceOwner.pin0Preserves"; attribute :>> scope="one owner, two pins, current write identity; native refinement open"; }
part binding16:BindingRow { attribute :>> actionName="source_owner_registry.enrollTarget0"; attribute :>> lemma="SourceOwner.enrollTarget0Preserves"; attribute :>> scope="one owner, two pins, current write identity; native refinement open"; }
part binding17:BindingRow { attribute :>> actionName="source_owner_registry.ackRound0"; attribute :>> lemma="SourceOwner.ackRound0Preserves"; attribute :>> scope="one owner, two pins, current write identity; native refinement open"; }
part binding18:BindingRow { attribute :>> actionName="source_owner_registry.reserveGuard0"; attribute :>> lemma="SourceOwner.reserveGuard0Preserves"; attribute :>> scope="one owner, two pins, current write identity; native refinement open"; }
part binding19:BindingRow { attribute :>> actionName="source_owner_registry.commitGuard0"; attribute :>> lemma="SourceOwner.commitGuard0Preserves"; attribute :>> scope="one owner, two pins, current write identity; native refinement open"; }
part binding20:BindingRow { attribute :>> actionName="source_owner_registry.unknownGuard0"; attribute :>> lemma="SourceOwner.unknownGuard0Preserves"; attribute :>> scope="one owner, two pins, current write identity; native refinement open"; }
part binding21:BindingRow { attribute :>> actionName="source_owner_registry.resolveGuard0"; attribute :>> lemma="SourceOwner.resolveGuard0Preserves"; attribute :>> scope="one owner, two pins, current write identity; native refinement open"; }
part binding22:BindingRow { attribute :>> actionName="source_owner_registry.returnPin0"; attribute :>> lemma="SourceOwner.returnPin0Preserves"; attribute :>> scope="one owner, two pins, current write identity; native refinement open"; }
part binding23:BindingRow { attribute :>> actionName="source_owner_registry.finishGuard0"; attribute :>> lemma="SourceOwner.finishGuard0Preserves"; attribute :>> scope="one owner, two pins, current write identity; native refinement open"; }
part binding24:BindingRow { attribute :>> actionName="source_owner_registry.retireTarget0"; attribute :>> lemma="SourceOwner.retireTarget0Preserves"; attribute :>> scope="one owner, two pins, current write identity; native refinement open"; }
part binding25:BindingRow { attribute :>> actionName="source_owner_registry.pin1"; attribute :>> lemma="SourceOwner.pin1Preserves"; attribute :>> scope="one owner, two pins, current write identity; native refinement open"; }
part binding26:BindingRow { attribute :>> actionName="source_owner_registry.enrollTarget1"; attribute :>> lemma="SourceOwner.enrollTarget1Preserves"; attribute :>> scope="one owner, two pins, current write identity; native refinement open"; }
part binding27:BindingRow { attribute :>> actionName="source_owner_registry.ackRound1"; attribute :>> lemma="SourceOwner.ackRound1Preserves"; attribute :>> scope="one owner, two pins, current write identity; native refinement open"; }
part binding28:BindingRow { attribute :>> actionName="source_owner_registry.reserveGuard1"; attribute :>> lemma="SourceOwner.reserveGuard1Preserves"; attribute :>> scope="one owner, two pins, current write identity; native refinement open"; }
part binding29:BindingRow { attribute :>> actionName="source_owner_registry.commitGuard1"; attribute :>> lemma="SourceOwner.commitGuard1Preserves"; attribute :>> scope="one owner, two pins, current write identity; native refinement open"; }
part binding30:BindingRow { attribute :>> actionName="source_owner_registry.unknownGuard1"; attribute :>> lemma="SourceOwner.unknownGuard1Preserves"; attribute :>> scope="one owner, two pins, current write identity; native refinement open"; }
part binding31:BindingRow { attribute :>> actionName="source_owner_registry.resolveGuard1"; attribute :>> lemma="SourceOwner.resolveGuard1Preserves"; attribute :>> scope="one owner, two pins, current write identity; native refinement open"; }
part binding32:BindingRow { attribute :>> actionName="source_owner_registry.returnPin1"; attribute :>> lemma="SourceOwner.returnPin1Preserves"; attribute :>> scope="one owner, two pins, current write identity; native refinement open"; }
part binding33:BindingRow { attribute :>> actionName="source_owner_registry.finishGuard1"; attribute :>> lemma="SourceOwner.finishGuard1Preserves"; attribute :>> scope="one owner, two pins, current write identity; native refinement open"; }
part binding34:BindingRow { attribute :>> actionName="source_owner_registry.retireTarget1"; attribute :>> lemma="SourceOwner.retireTarget1Preserves"; attribute :>> scope="one owner, two pins, current write identity; native refinement open"; }
part binding35:BindingRow { attribute :>> actionName="source_owner_registry.freezeGc"; attribute :>> lemma="SourceOwner.freezeGcPreserves"; attribute :>> scope="one owner, two pins, current write identity; native refinement open"; }
part binding36:BindingRow { attribute :>> actionName="source_owner_registry.finishGc"; attribute :>> lemma="SourceOwner.finishGcPreserves"; attribute :>> scope="one owner, two pins, current write identity; native refinement open"; }
part binding37:BindingRow { attribute :>> actionName="source_owner_registry.storageReceipt"; attribute :>> lemma="SourceOwner.storageReceiptPreserves"; attribute :>> scope="one owner, two pins, current write identity; native refinement open"; }
part binding38:BindingRow { attribute :>> actionName="source_owner_registry.bulkCleanup"; attribute :>> lemma="SourceOwner.bulkCleanupPreserves"; attribute :>> scope="one owner, two pins, current write identity; native refinement open"; }
part binding39:BindingRow { attribute :>> actionName="source_owner_registry.qualifyPersistentCoverage"; attribute :>> lemma="SourceOwner.qualifyPersistentCoveragePreserves"; attribute :>> scope="trusted persistent root-domain premise; native issuer open"; }
part def ProofRow { attribute key:String; attribute lemma:String; }
part proof0:ProofRow { attribute :>> key="stepPreserves"; attribute :>> lemma="SourceOwner.stepPreserves"; }
part proof1:ProofRow { attribute :>> key="reachableSafe"; attribute :>> lemma="SourceOwner.reachableSafe"; }
part proof2:ProofRow { attribute :>> key="staleRoundCannotReturn"; attribute :>> lemma="SourceOwner.staleRoundCannotReturn"; }
part proof3:ProofRow { attribute :>> key="unknownWriterBlocksCleanup"; attribute :>> lemma="SourceOwner.unknownWriterBlocksCleanup"; }
part proof4:ProofRow { attribute :>> key="oldWriteCannotCommit"; attribute :>> lemma="SourceOwner.oldWriteCannotCommit"; }
part proof5:ProofRow { attribute :>> key="closeRetainsAcceptedWriter"; attribute :>> lemma="SourceOwner.closeRetainsAcceptedWriter"; }
part proof6:ProofRow { attribute :>> key="sourceReplacementKeepsOldTarget"; attribute :>> lemma="SourceOwner.sourceReplacementKeepsOldTarget"; }
part proof7:ProofRow { attribute :>> key="nestedPinBlocksCleanup"; attribute :>> lemma="SourceOwner.nestedPinBlocksCleanup"; }
part proof8:ProofRow { attribute :>> key="unknownGuardRetainsPin"; attribute :>> lemma="SourceOwner.unknownGuardRetainsPin"; }
part proof9:ProofRow { attribute :>> key="sourcePinAgreement"; attribute :>> lemma="SourceOwnerBridge.sourcePinAgreement"; }
part proof10:ProofRow { attribute :>> key="carrierReservationAgreement"; attribute :>> lemma="SourceOwnerBridge.carrierReservationAgreement"; }
part proof11:ProofRow { attribute :>> key="carrierReservationSafe"; attribute :>> lemma="SourceOwnerBridge.carrierReservationSafe"; }
part proof12:ProofRow { attribute :>> key="cleanupAgreement"; attribute :>> lemma="SourceOwnerBridge.cleanupAgreement"; }
part proof13:ProofRow { attribute :>> key="persistent-carrier"; attribute :>> lemma="SourceOwnerBridge.persistentCarrierReservation"; }
part def RouteRow { attribute component:String; attribute actionName:String; attribute lemma:String; attribute producerAnchor:String; attribute obligationId:String; }
part route0:RouteRow { attribute :>> component="registry"; attribute :>> actionName="source_owner_registry.publishOwner"; attribute :>> lemma="SourceOwner.publishOwnerPreserves"; attribute :>> producerAnchor="rc-register"; attribute :>> obligationId="SO-source"; }
part route1:RouteRow { attribute :>> component="registry"; attribute :>> actionName="source_owner_registry.closeRegistry"; attribute :>> lemma="SourceOwner.closeRegistryPreserves"; attribute :>> producerAnchor="register-export"; attribute :>> obligationId="SO-source"; }
part route2:RouteRow { attribute :>> component="writer"; attribute :>> actionName="source_owner_registry.beginWrite"; attribute :>> lemma="SourceOwner.beginWritePreserves"; attribute :>> producerAnchor="rc-write"; attribute :>> obligationId="SO-writers"; }
part route3:RouteRow { attribute :>> component="writer"; attribute :>> actionName="source_owner_registry.commitWrite"; attribute :>> lemma="SourceOwner.commitWritePreserves"; attribute :>> producerAnchor="setter-export"; attribute :>> obligationId="SO-writers"; }
part route4:RouteRow { attribute :>> component="writer"; attribute :>> actionName="source_owner_registry.unknownWrite"; attribute :>> lemma="SourceOwner.unknownWritePreserves"; attribute :>> producerAnchor="closure-writer"; attribute :>> obligationId="SO-writers"; }
part route5:RouteRow { attribute :>> component="roots"; attribute :>> actionName="source_owner_registry.ackRound0"; attribute :>> lemma="SourceOwner.ackRound0Preserves"; attribute :>> producerAnchor="origin-finish"; attribute :>> obligationId="SO-roots"; }
part route6:RouteRow { attribute :>> component="roots"; attribute :>> actionName="source_owner_registry.freezeGc"; attribute :>> lemma="SourceOwner.freezeGcPreserves"; attribute :>> producerAnchor="epoch-new"; attribute :>> obligationId="SO-roots"; }
part route7:RouteRow { attribute :>> component="guard"; attribute :>> actionName="source_owner_registry.returnPin1"; attribute :>> lemma="SourceOwner.returnPin1Preserves"; attribute :>> producerAnchor="tcl-call"; attribute :>> obligationId="SO-execution"; }
part route8:RouteRow { attribute :>> component="guard"; attribute :>> actionName="source_owner_registry.unknownGuard0"; attribute :>> lemma="SourceOwner.unknownGuard0Preserves"; attribute :>> producerAnchor="tcl-call"; attribute :>> obligationId="SO-execution"; }
part route9:RouteRow { attribute :>> component="storage"; attribute :>> actionName="source_owner_registry.bulkCleanup"; attribute :>> lemma="SourceOwner.bulkCleanupPreserves"; attribute :>> producerAnchor="rc-cleanup"; attribute :>> obligationId="SO-storage"; }
part route10:RouteRow { attribute :>> component="storage"; attribute :>> actionName="source_owner_registry.storageReceipt"; attribute :>> lemma="SourceOwner.storageReceiptPreserves"; attribute :>> producerAnchor="shrink-cleanup"; attribute :>> obligationId="SO-storage"; }
part route11:RouteRow { attribute :>> component="registry"; attribute :>> actionName="source_owner_registry.sealRoster"; attribute :>> lemma="SourceOwner.sealRosterPreserves"; attribute :>> producerAnchor="vm-root-retained"; attribute :>> obligationId="SO-source"; }
part def Need { attribute obligationId:String; attribute kind:String; attribute subjectPath:String; attribute subjectScope:String; ref owner:Owner; }
part formalNeed:Need { attribute :>> obligationId="SO-formal"; attribute :>> kind="induction"; attribute :>> subjectPath="dev/refactoring/modern-c/models/lean/SourceOwner.lean"; attribute :>> subjectScope="single owner, two pin slots, accepted writer and GC round safety"; ref :>> owner=guardOwner; }
part bridgeNeed:Need { attribute :>> obligationId="SO-bridge"; attribute :>> kind="composition"; attribute :>> subjectPath="dev/refactoring/modern-c/models/lean/SourceOwnerBridge.lean"; attribute :>> subjectScope="explicit relations to prior source pin/carrier/cleanup model"; ref :>> owner=guardOwner; }
part sourceNeed:Need { attribute :>> obligationId="SO-source"; attribute :>> kind="source"; attribute :>> subjectPath="vendor/gambit/lib/memory/rc-allocation.inc"; attribute :>> subjectScope="stable owner registration, close and complete member manifest"; ref :>> owner=registryOwner; }
part executionNeed:Need { attribute :>> obligationId="SO-execution"; attribute :>> kind="source"; attribute :>> subjectPath="vendor/gambit/lib/c_intf.c"; attribute :>> subjectScope="real pin/guard commit witnesses and unknown outcome lookup"; ref :>> owner=guardOwner; }
part rootsNeed:Need { attribute :>> obligationId="SO-roots"; attribute :>> kind="source"; attribute :>> subjectPath="vendor/gambit/lib/memory/collection-round.inc"; attribute :>> subjectScope="real current-round carrier and descriptor/scan grace receipts"; ref :>> owner=rootsOwner; }
part writersNeed:Need { attribute :>> obligationId="SO-writers"; attribute :>> kind="source"; attribute :>> subjectPath="vendor/gambit/lib/setup.c"; attribute :>> subjectScope="all exported setters, direct header writes and native extension aliases"; ref :>> owner=writerOwner; }
part platformNeed:Need { attribute :>> obligationId="SO-platform"; attribute :>> kind="platform"; attribute :>> subjectPath="dev/refactoring/modern-c/language-baseline-design.org"; attribute :>> subjectScope="C23 ordering, finite IDs, ABI and effective Darwin header provenance"; ref :>> owner=guardOwner; }
part storageNeed:Need { attribute :>> obligationId="SO-storage"; attribute :>> kind="source"; attribute :>> subjectPath="vendor/gambit/lib/setup.c"; attribute :>> subjectScope="all processor/VM cleanup callers and retained backing storage authority"; ref :>> owner=storageOwner; }
}
