package GambitChainSealWillCut { private import ScalarValues::*;
part def Source { attribute key:String; attribute path:String; attribute needle:String; attribute obligation:String; }
part source0:Source { attribute :>> key="capacity-before-fixup"; attribute :>> path="vendor/gambit/lib/mem.c"; attribute :>> needle="while (alloc + words + ___SUBTYPED_BODY > limit)"; attribute :>> obligation="Next fresh frame can publish previous chunk before writing previous ptr"; }
part source1:Source { attribute :>> key="frame-ready"; attribute :>> path="vendor/gambit/lib/mem.c"; attribute :>> needle="publish_object_scan (work, copy_header);"; attribute :>> obligation="All publisher call sites inventoried; frame publisher follows initial copied payload"; }
part source2:Source { attribute :>> key="pending-link"; attribute :>> path="vendor/gambit/lib/mem.c"; attribute :>> needle="ptr = &___FP_STK(alloc,link+1);"; attribute :>> obligation="Cursor retains preceding copied-frame link address"; }
part source3:Source { attribute :>> key="already-forwarded-fixup"; attribute :>> path="vendor/gambit/lib/mem.c"; attribute :>> needle="*ptr = ra2; /* already copied, replace by forwarding pointer */"; attribute :>> obligation="Separate fixup branch exists; capacity witness uses the fresh-frame branch"; }
part source4:Source { attribute :>> key="copy-lock"; attribute :>> path="vendor/gambit/lib/mem.c"; attribute :>> needle="MISC_MEM_LOCK();\n\n      next_frame:"; attribute :>> obligation="Copier holds global memory lock; this alone does not exclude frame scanner"; }
part source5:Source { attribute :>> key="strong-weak-barrier"; attribute :>> path="vendor/gambit/lib/mem.c"; attribute :>> needle="garbage_collect_mark_strong_phase (work);\n\n  BARRIER();"; attribute :>> obligation="Strong closure precedes weak phase but does not serialize weak classification against weak marking"; }
part source6:Source { attribute :>> key="will-repair"; attribute :>> path="vendor/gambit/lib/mem.c"; attribute :>> needle="mark_array (work, tail_exec+___WILL_TESTATOR, 1);"; attribute :>> obligation="Executable and moved-to-executable paths directly repair testator"; }
part source7:Source { attribute :>> key="chunk-authority"; attribute :>> path="vendor/gambit/lib/mem.c"; attribute :>> needle="if (alloc_heap_chunk_start != work->local_scan_chunk_)"; attribute :>> obligation="Current source uses explicit local chunk identity; parent range guard is historical"; }
part source8:Source { attribute :>> key="terminal"; attribute :>> path="vendor/gambit/lib/mem.c"; attribute :>> needle="if (___FIXNUMP(cf) && cf != ___END_OF_CONT_MARKER)"; attribute :>> obligation="Seal last link without successor"; }
part source9:Source { attribute :>> key="retag"; attribute :>> path="vendor/gambit/lib/mem.c"; attribute :>> needle="*orig_ptr = ___TAG(___UNTAG_AS(*orig_ptr, ___tFIXNUM), ___tSUBTYPED);"; attribute :>> obligation="Retag follows all link resolution"; }
part source10:Source { attribute :>> key="custom"; attribute :>> path="vendor/gambit/lib/mem.c"; attribute :>> needle="return custom_msection_alloc ();"; attribute :>> obligation="Custom grant unknown"; }
part source11:Source { attribute :>> key="grant"; attribute :>> path="vendor/gambit/lib/mem.c"; attribute :>> needle="alloc_heap_limit = alloc_heap_start + (___MSECTION_SIZE>>1);"; attribute :>> obligation="Standard half section"; }
part source12:Source { attribute :>> key="shared"; attribute :>> path="vendor/gambit/lib/mem.c"; attribute :>> needle="space = (space - 2*___MSECTION_FUDGE) >> 2;"; attribute :>> obligation="Shared stack remaining grant"; }
part source13:Source { attribute :>> key="markers"; attribute :>> path="vendor/gambit/lib/mem.c"; attribute :>> needle="alloc_heap_limit_ -= 2;"; attribute :>> obligation="Two end markers plus first link word"; }
part source14:Source { attribute :>> key="frame-max"; attribute :>> path="vendor/gambit/lib/mem.h"; attribute :>> needle="#define ___MAX_NB_FRAME_SLOTS   8192"; attribute :>> obligation="Static slot limit"; }
part source15:Source { attribute :>> key="threshold"; attribute :>> path="vendor/gambit/lib/mem.h"; attribute :>> needle="#define ___MSECTION_BIGGEST     255"; attribute :>> obligation="Threshold not maximum chunk size"; }
part source16:Source { attribute :>> key="end-value"; attribute :>> path="vendor/gambit/include/gambit.h.in"; attribute :>> needle="#define ___END_OF_CONT_MARKER ___VOID"; attribute :>> obligation="Nonfixnum terminal"; }
part source17:Source { attribute :>> key="callcc"; attribute :>> path="vendor/gambit/lib/_thread.scm"; attribute :>> needle="(receiver (reify-continuation cont))"; attribute :>> obligation="Captured continuation retained by closure"; }
part source18:Source { attribute :>> key="capture"; attribute :>> path="vendor/gambit/gsc/_t-c-2.scm"; attribute :>> needle="(targ-emit-jump-inline \"CONTINUATION_CAPTURE\" safe? nb-args)"; attribute :>> obligation="Actual capture emitter"; }
part source19:Source { attribute :>> key="public-will"; attribute :>> path="vendor/gambit/lib/_nonstd.scm"; attribute :>> needle="(define-prim (make-will testator action)"; attribute :>> obligation="Distinct wills may share testator"; }
part source20:Source { attribute :>> key="will-list"; attribute :>> path="vendor/gambit/include/gambit.h.in"; attribute :>> needle="___ADD_SUBTYPED_ELEM(___WILL_NEXT,___ps->context->mem.nonexecutable_wills_)"; attribute :>> obligation="Per-context registration"; }
part source21:Source { attribute :>> key="will-decision"; attribute :>> path="vendor/gambit/lib/mem.c"; attribute :>> needle="UNMARKED(testator)) /* testator was not marked? */"; attribute :>> obligation="Mutable mark observation"; }
part source22:Source { attribute :>> key="will-local"; attribute :>> path="vendor/gambit/lib/mem.c"; attribute :>> needle="determine_will_executability (nonexecutable_wills);"; attribute :>> obligation="Local decide immediately followed by retention"; }
part def Footprint { attribute key:String; attribute required:String; attribute reuse:String; attribute premise:String; }
part footprint0:Footprint { attribute :>> key="steady debt"; attribute :>> required="<=1 pending link"; attribute :>> reuse="ptr cursor"; attribute :>> premise="Sequential loop boundary"; }
part footprint1:Footprint { attribute :>> key="transient debt"; attribute :>> required="<=2 unsealed copied frames"; attribute :>> reuse="Existing destination storage"; attribute :>> premise="Initialize successor before predecessor fixup"; }
part footprint2:Footprint { attribute :>> key="deferred chunk"; attribute :>> required="<=1 per admitted sequential copier"; attribute :>> reuse="Retain allocated chunk"; attribute :>> premise="Drain before next close; next frame fits grant"; }
part footprint3:Footprint { attribute :>> key="frame cap"; attribute :>> required="fs+2 <=8194 words"; attribute :>> reuse="Existing guarded copy layout"; attribute :>> premise="SUBTYPED_BODY=1 EXTRA=1 and valid descriptor"; }
part footprint4:Footprint { attribute :>> key="section grant"; attribute :>> required="65536 minus 3 marker words"; attribute :>> reuse="Existing standard tospace"; attribute :>> premise="Unshared standard allocation only"; }
part footprint5:Footprint { attribute :>> key="chunk bound"; attribute :>> required="threshold+maxFrame+terminator conditional"; attribute :>> reuse="No O(N) whole-chain buffer"; attribute :>> premise="Regular threshold checks; current stale local-alloc check unresolved"; }
part def Contract { attribute fromNode:String; attribute toNode:String; attribute custody:String; }
part contract0:Contract { attribute :>> fromNode="reserve"; attribute :>> toNode="initialize"; attribute :>> custody="Fit grant; retain owner"; }
part contract1:Contract { attribute :>> fromNode="initialize"; attribute :>> toNode="fix-previous"; attribute :>> custody="At most two copied obligations"; }
part contract2:Contract { attribute :>> fromNode="fix-previous"; attribute :>> toNode="install"; attribute :>> custody="Seal predecessor; current pending"; }
part contract3:Contract { attribute :>> fromNode="install"; attribute :>> toNode="reserve"; attribute :>> custody="Advance chain"; }
part contract4:Contract { attribute :>> fromNode="install"; attribute :>> toNode="defer-chunk"; attribute :>> custody="Retain last unresolved chunk"; }
part contract5:Contract { attribute :>> fromNode="defer-chunk"; attribute :>> toNode="publish"; attribute :>> custody="Whole physical coverage sealed"; }
part contract6:Contract { attribute :>> fromNode="install"; attribute :>> toNode="terminal"; attribute :>> custody="Seal END without successor"; }
part contract7:Contract { attribute :>> fromNode="install"; attribute :>> toNode="forwarded"; attribute :>> custody="Same-epoch sealed suffix"; }
part contract8:Contract { attribute :>> fromNode="terminal"; attribute :>> toNode="retag"; attribute :>> custody="No pending copied link"; }
part contract9:Contract { attribute :>> fromNode="forwarded"; attribute :>> toNode="retag"; attribute :>> custody="Stop; do not recopy suffix"; }
part contract10:Contract { attribute :>> fromNode="reserve"; attribute :>> toNode="failure"; attribute :>> custody="Owner retains unresolved debt"; }
part contract11:Contract { attribute :>> fromNode="strong-closure"; attribute :>> toNode="classify-all"; attribute :>> custody="Freeze roster and lists"; }
part contract12:Contract { attribute :>> fromNode="classify-all"; attribute :>> toNode="decision-cut"; attribute :>> custody="Every owner acknowledges"; }
part contract13:Contract { attribute :>> fromNode="decision-cut"; attribute :>> toNode="weak-retain"; attribute :>> custody="Then repair and derived work"; }
part def Obligation { attribute key:String; attribute status:String; attribute scope:String; attribute gap:String; }
part obligation0:Obligation { attribute :>> key="chain"; attribute :>> status="proved-in-model"; attribute :>> scope="All lengths scalar accounting"; attribute :>> gap="Object identity and physical chunk mapping open"; }
part obligation1:Obligation { attribute :>> key="terminal"; attribute :>> status="proved-in-model"; attribute :>> scope="Empty and final-frame exits"; attribute :>> gap="Actual retag and descriptor mapping open"; }
part obligation2:Obligation { attribute :>> key="forwarded"; attribute :>> status="conditional"; attribute :>> scope="Same-epoch sealed suffix"; attribute :>> gap="Receipt issuer not implemented"; }
part obligation3:Obligation { attribute :>> key="capacity"; attribute :>> status="conditional"; attribute :>> scope="Bounded debt and failure custody"; attribute :>> gap="Custom/shared grant and byte bounds open"; }
part obligation4:Obligation { attribute :>> key="Scheme reachability"; attribute :>> status="source-family"; attribute :>> scope="Public callcc and make-will callers"; attribute :>> gap="Exact emitted frames and processor schedule unqualified"; }
part obligation5:Obligation { attribute :>> key="shared will"; attribute :>> status="proved-in-model"; attribute :>> scope="Two lists same testator"; attribute :>> gap="Native schedule unqualified"; }
part obligation6:Obligation { attribute :>> key="global cut"; attribute :>> status="proved-in-model"; attribute :>> scope="All classification precedes retention"; attribute :>> gap="Full weak producer roster open"; }
part obligation7:Obligation { attribute :>> key="C11"; attribute :>> status="open"; attribute :>> scope="READY queue and phase publication"; attribute :>> gap="Source/configuration refinement absent"; }
part obligation8:Obligation { attribute :>> key="native"; attribute :>> status="open"; attribute :>> scope="No implementation or native tests"; attribute :>> gap="No performance qualification"; }
part def Gain { attribute key:String; attribute avoided:String; attribute added:String; attribute condition:String; }
part gain0:Gain { attribute :>> key="rolling seal"; attribute :>> avoided="Avoid O(N) full-chain staging"; attribute :>> added="One link record; transient second frame"; attribute :>> condition="One deferred chunk with fit/drain rule"; }
part gain1:Gain { attribute :>> key="suffix reuse"; attribute :>> avoided="0 new copies for S sealed suffix frames"; attribute :>> added="One suffix lifetime check"; attribute :>> condition="Already a C advantage; no added speed credit"; }
part gain2:Gain { attribute :>> key="will consistency"; attribute :>> avoided="W decisions before weak retention"; attribute :>> added="Existing O(W) work plus one collective cut"; attribute :>> condition="Frozen lists and all weak producers gated"; }
part gain3:Gain { attribute :>> key="snapshot option"; attribute :>> avoided="May avoid new rendezvous"; attribute :>> added="Immutable strong epoch metadata"; attribute :>> condition="All decisions read stable snapshot; not free"; }
part gain4:Gain { attribute :>> key="C retirement"; attribute :>> avoided="Remove immediate READY and fused classify-retain entry"; attribute :>> added="Seal API and split phase entry"; attribute :>> condition="All callers migrated; no Zig requirement"; }
part gain5:Gain { attribute :>> key="parallel overlap"; attribute :>> avoided="Other workers scan sealed prefixes"; attribute :>> added="Delay P bytes per copier plus phase handoff"; attribute :>> condition="Useful overlap exceeds handoff cost; no timing evidence"; }
part def Binding { attribute actionName:String; attribute lemma:String; attribute scope:String; }
part binding0:Binding { attribute :>> actionName="captured_chain_seal.reserve"; attribute :>> lemma="ChainSeal.reservePreserves"; attribute :>> scope="Actual typed IR update; source mapping open"; }
part binding1:Binding { attribute :>> actionName="captured_chain_seal.initializeCopy"; attribute :>> lemma="ChainSeal.initializeCopyPreserves"; attribute :>> scope="Actual typed IR update; source mapping open"; }
part binding2:Binding { attribute :>> actionName="captured_chain_seal.resolvePrevious"; attribute :>> lemma="ChainSeal.resolvePreviousPreserves"; attribute :>> scope="Actual typed IR update; source mapping open"; }
part binding3:Binding { attribute :>> actionName="captured_chain_seal.finishInstall"; attribute :>> lemma="ChainSeal.finishInstallPreserves"; attribute :>> scope="Actual typed IR update; source mapping open"; }
part binding4:Binding { attribute :>> actionName="captured_chain_seal.deferChunk"; attribute :>> lemma="ChainSeal.deferChunkPreserves"; attribute :>> scope="Actual typed IR update; source mapping open"; }
part binding5:Binding { attribute :>> actionName="captured_chain_seal.publishDeferred"; attribute :>> lemma="ChainSeal.publishDeferredPreserves"; attribute :>> scope="Actual typed IR update; source mapping open"; }
part binding6:Binding { attribute :>> actionName="captured_chain_seal.publishPrefix"; attribute :>> lemma="ChainSeal.publishPrefixPreserves"; attribute :>> scope="Actual typed IR update; source mapping open"; }
part binding7:Binding { attribute :>> actionName="captured_chain_seal.certifySuffix"; attribute :>> lemma="ChainSeal.certifySuffixPreserves"; attribute :>> scope="Actual typed IR update; source mapping open"; }
part binding8:Binding { attribute :>> actionName="captured_chain_seal.terminal"; attribute :>> lemma="ChainSeal.terminalPreserves"; attribute :>> scope="Actual typed IR update; source mapping open"; }
part binding9:Binding { attribute :>> actionName="captured_chain_seal.forwarded"; attribute :>> lemma="ChainSeal.forwardedPreserves"; attribute :>> scope="Actual typed IR update; source mapping open"; }
part binding10:Binding { attribute :>> actionName="captured_chain_seal.capacityFailure"; attribute :>> lemma="ChainSeal.capacityFailurePreserves"; attribute :>> scope="Actual typed IR update; source mapping open"; }
part binding11:Binding { attribute :>> actionName="captured_chain_seal.retagRoot"; attribute :>> lemma="ChainSeal.retagRootPreserves"; attribute :>> scope="Actual typed IR update; source mapping open"; }
part binding12:Binding { attribute :>> actionName="captured_chain_seal.release"; attribute :>> lemma="ChainSeal.releasePreserves"; attribute :>> scope="Actual typed IR update; source mapping open"; }
part binding13:Binding { attribute :>> actionName="will_classification_cut.strongReachable"; attribute :>> lemma="WillCut.strongReachablePreserves"; attribute :>> scope="Actual typed IR update; source mapping open"; }
part binding14:Binding { attribute :>> actionName="will_classification_cut.decideA"; attribute :>> lemma="WillCut.decideAPreserves"; attribute :>> scope="Actual typed IR update; source mapping open"; }
part binding15:Binding { attribute :>> actionName="will_classification_cut.decideB"; attribute :>> lemma="WillCut.decideBPreserves"; attribute :>> scope="Actual typed IR update; source mapping open"; }
part binding16:Binding { attribute :>> actionName="will_classification_cut.legacyDecideA"; attribute :>> lemma="WillCut.legacyDecideAPreserves"; attribute :>> scope="Actual typed IR update; source mapping open"; }
part binding17:Binding { attribute :>> actionName="will_classification_cut.legacyDecideB"; attribute :>> lemma="WillCut.legacyDecideBPreserves"; attribute :>> scope="Actual typed IR update; source mapping open"; }
part binding18:Binding { attribute :>> actionName="will_classification_cut.classifyCut"; attribute :>> lemma="WillCut.classifyCutPreserves"; attribute :>> scope="Actual typed IR update; source mapping open"; }
part binding19:Binding { attribute :>> actionName="will_classification_cut.weakMark"; attribute :>> lemma="WillCut.weakMarkPreserves"; attribute :>> scope="Actual typed IR update; source mapping open"; }
part binding20:Binding { attribute :>> actionName="will_classification_cut.finish"; attribute :>> lemma="WillCut.finishPreserves"; attribute :>> scope="Actual typed IR update; source mapping open"; }
part def Composition { attribute key:String; attribute lemma:String; attribute scope:String; }
part composition0:Composition { attribute :>> key="chain"; attribute :>> lemma="ChainSeal.arbitraryLengthSafe"; attribute :>> scope="Any length accounting"; }
part composition1:Composition { attribute :>> key="debt"; attribute :>> lemma="ChainSeal.unresolvedBound"; attribute :>> scope="At most two transient obligations"; }
part composition2:Composition { attribute :>> key="steady"; attribute :>> lemma="ChainSeal.quiescentLinkBound"; attribute :>> scope="One at loop boundary"; }
part composition3:Composition { attribute :>> key="fit"; attribute :>> lemma="ChainSeal.grantIncludesFrame"; attribute :>> scope="Given fit"; }
part composition4:Composition { attribute :>> key="chunk"; attribute :>> lemma="ChainSeal.closedChunkBound"; attribute :>> scope="Given threshold and maxFrame"; }
part composition5:Composition { attribute :>> key="will"; attribute :>> lemma="WillCut.reachableSafe"; attribute :>> scope="All modeled steps"; }
part composition6:Composition { attribute :>> key="decision"; attribute :>> lemma="WillCut.sharedDecision"; attribute :>> scope="Same strong observation"; }
part composition7:Composition { attribute :>> key="legacy"; attribute :>> lemma="WillCut.legacyDisagreement"; attribute :>> scope="Updates with Quint guard-admitted trace"; }
part frameHistory:GambitAssuranceRouting::ModelNeed { ref part :>> owner=GambitAssuranceRelations::modelUse3; attribute :>> obligationId="CS-frameHistory"; attribute :>> kind="interleaving"; attribute :>> subjectPath="dev/refactoring/modern-c/models/quint/captured_chain_seal.qnt"; attribute :>> subjectScope="Three frames and both exits"; attribute :>> premise="Design and formal models only; no native qualification"; }
part weakHistory:GambitAssuranceRouting::ModelNeed { ref part :>> owner=GambitAssuranceRelations::modelUse3; attribute :>> obligationId="CS-weakHistory"; attribute :>> kind="interleaving"; attribute :>> subjectPath="dev/refactoring/modern-c/models/quint/will_classification_cut.qnt"; attribute :>> subjectScope="Two owners shared testator"; attribute :>> premise="Design and formal models only; no native qualification"; }
part frameInduction:GambitAssuranceRouting::ModelNeed { ref part :>> owner=GambitAssuranceRelations::modelUse3; attribute :>> obligationId="CS-frameInduction"; attribute :>> kind="induction"; attribute :>> subjectPath="dev/refactoring/modern-c/models/lean/ChainSeal.lean"; attribute :>> subjectScope="All steps arbitrary length accounting"; attribute :>> premise="Design and formal models only; no native qualification"; }
part weakInduction:GambitAssuranceRouting::ModelNeed { ref part :>> owner=GambitAssuranceRelations::modelUse3; attribute :>> obligationId="CS-weakInduction"; attribute :>> kind="induction"; attribute :>> subjectPath="dev/refactoring/modern-c/models/lean/WillCut.lean"; attribute :>> subjectScope="All steps consistent decisions"; attribute :>> premise="Design and formal models only; no native qualification"; }
part projection:GambitAssuranceRouting::ModelNeed { ref part :>> owner=GambitAssuranceRelations::modelUse3; attribute :>> obligationId="CS-projection"; attribute :>> kind="restricted-projection"; attribute :>> subjectPath="dev/refactoring/modern-c/models/lean/ChainSealAst.lean"; attribute :>> subjectScope="Both typed IR exact rosters trusted emitter"; attribute :>> premise="Design and formal models only; no native qualification"; }
part source:GambitAssuranceRouting::ModelNeed { ref part :>> owner=GambitAssuranceRelations::modelUse3; attribute :>> obligationId="CS-source"; attribute :>> kind="source-refinement"; attribute :>> subjectPath="dev/refactoring/modern-c/chain-seal-will-cut-design.org"; attribute :>> subjectScope="Physical mapping and producer closure open"; attribute :>> premise="Design and formal models only; no native qualification"; }
part platform:GambitAssuranceRouting::ModelNeed { ref part :>> owner=GambitAssuranceRelations::modelUse3; attribute :>> obligationId="CS-platform"; attribute :>> kind="native-memory-order"; attribute :>> subjectPath="dev/refactoring/modern-c/chain-seal-will-cut-design.org"; attribute :>> subjectScope="Actual C11 and config refinement open"; attribute :>> premise="Design and formal models only; no native qualification"; }
part def Seam { ref part producer:GambitRuntimeComposition::BlueprintModule; ref part consumer:GambitRuntimeComposition::BlueprintModule; attribute contract:String; attribute modelNeed:String; }
part seam0:Seam { ref part :>> producer=GambitRuntimeComposition::blueprintModule3; ref part :>> consumer=GambitRuntimeComposition::blueprintModule4; attribute :>> contract="Root and chain identity"; attribute :>> modelNeed="CS-source"; }
part seam1:Seam { ref part :>> producer=GambitRuntimeComposition::blueprintModule4; ref part :>> consumer=GambitRuntimeComposition::blueprintModule4; attribute :>> contract="Deferred chunk to scan"; attribute :>> modelNeed="CS-frameInduction"; }
part seam2:Seam { ref part :>> producer=GambitRuntimeComposition::blueprintModule4; ref part :>> consumer=GambitRuntimeComposition::blueprintModule5; attribute :>> contract="Frozen roster decision cut"; attribute :>> modelNeed="CS-weakInduction"; }
part seam3:Seam { ref part :>> producer=GambitRuntimeComposition::blueprintModule4; ref part :>> consumer=GambitRuntimeComposition::blueprintModule1; attribute :>> contract="C11 readiness publication"; attribute :>> modelNeed="CS-platform"; }
}
