/* Joint architectural witness; native SysML owns rows, edges and proof scopes. */
package GambitMapMultishot { private import ScalarValues::*;
part def Boundary { ref part owner:GambitRuntimeComposition::BlueprintModule; attribute componentId:String; attribute label:String; attribute contract:String; attribute replacement:String; attribute retirement:String; attribute benefit:String; attribute addedCost:String; attribute sourceAnchors:String; attribute premise:String; }
part boundary0:Boundary { ref part :>> owner=GambitRuntimeComposition::blueprintModule0; attribute :>> componentId="semantic"; attribute :>> label="GVM semantic completion"; attribute :>> contract="FrameSpec + PointId + EffectSpec + ModuleSpec + AllocationSpec"; attribute :>> replacement="Complete homes, live roots, tail/non-tail successors, denv/wind actions and allocation bounds in Scheme before C lowering"; attribute :>> retirement="Distributed semantic inference in C emission/macros; retain genuine target portability adapters"; attribute :>> benefit="Count semantic decisions once; lower invariant helper/parser bytes and stable ABI rebuild fanout"; attribute :>> addedCost="Contract descriptors, bootstrap and validation; no guaranteed code-size or time win"; attribute :>> sourceAnchors="vendor/gambit/gsc/_t-c-2.scm:823-916;vendor/gambit/gsc/_t-c-3.scm:471-522;vendor/gambit/lib/_std.c:74775-74813"; attribute :>> premise="Producer/decoder/root map equivalence for every collecting successor; L2 and L4 maps differ"; }
part boundary1:Boundary { ref part :>> owner=GambitRuntimeComposition::blueprintModule2; attribute :>> componentId="execution"; attribute :>> label="ExecutionContext and GCParticipant"; attribute :>> contract="GeneratedCheckpoint + Participation + RootCut"; attribute :>> replacement="Context owns Scheme registers/stack and stable identity; participant owns frozen/updateable root slots; VM owns heap epochs and membership"; attribute :>> retirement="PSTATE as inseparable carrier/execution/collector authority; TLS may cache an admitted context only"; attribute :>> benefit="A blocked native carrier need not hold up GC after its root cut; lightweight contexts can outnumber carriers"; attribute :>> addedCost="Publication/reload and context scheduling; affinity and opaque borrows limit migration"; attribute :>> sourceAnchors="vendor/gambit/lib/setup.c:745-836,3277-3421;vendor/ocaml/runtime/signals.c:147-205"; attribute :>> premise="No unreported pointers or active borrow at freeze; no reentry before root reload and new grant"; }
part boundary2:Boundary { ref part :>> owner=GambitRuntimeComposition::blueprintModule4; attribute :>> componentId="heap"; attribute :>> label="Generational heap and independent collector work"; attribute :>> contract="ControlRoots + RootCut + WorkClosure"; attribute :>> replacement="Context-local nursery with globally coordinated parallel STW minor; shared mature frames/objects; precise roots and remembered writes; major policy separate"; attribute :>> retirement="Full movable-heap copying as the only movable reclamation route; per-PSTATE work ownership; unchecked raw old-to-young stores"; attribute :>> benefit="Avoid m times the clean mature continuation graph scan; skip dead nursery data; expose load-balanced collection work"; attribute :>> addedCost="Barrier traffic, remembered scans, survivor promotion, nursery/reserve peak and synchronization; major cost remains"; attribute :>> sourceAnchors="vendor/gambit/lib/mem.c:3490-3815,6990-7085;vendor/ocaml/runtime/minor_gc.c:275-305,886-934;vendor/ocaml/runtime/memory.c:183-220"; attribute :>> premise="All frame/denv/FFI writers covered; overflow before store or conservative dirty fallback; promotion failure never loses source custody"; }
part boundary3:Boundary { ref part :>> owner=GambitRuntimeComposition::blueprintModule5; attribute :>> componentId="control"; attribute :>> label="Repeatable continuation and dynamic control"; attribute :>> contract="FrameSpec + ControlRoots + OutcomeLifetime"; attribute :>> replacement="Captured logical frames remain reusable; each invocation obtains private execution materialization; shared Scheme heap and denv identities remain shared; run wind transitions in Scheme"; attribute :>> retirement="Separate frame interpretations across emit/capture/GC/restore/serialize; never consume a multi-shot continuation as one-shot"; attribute :>> benefit="Share eligible unchanged frame storage across shots; one frame schema enables profiler/debugger/GC/backend consumers"; attribute :>> addedCost="Per-shot restore/dispatch and semantic side effects remain; lazy restoration and COW require alias/reflection proofs"; attribute :>> sourceAnchors="vendor/gambit/lib/_thread.scm:4623-4706,4913-4990;vendor/gambit/lib/_kernel.scm:1115-1346,3439-3558;vendor/gambit/lib/_io.scm:11690-11727"; attribute :>> premise="Multi-shot != parallel invocation guarantee; mutable frame APIs retain exact observable aliases; no C-stack resurrection"; }
part boundary4:Boundary { ref part :>> owner=GambitRuntimeComposition::blueprintModule6; attribute :>> componentId="foreign"; attribute :>> label="Root-safe FFI and effect boundary"; attribute :>> contract="Participation + RootCut + OutcomeLifetime + ReleaseDrain"; attribute :>> replacement="Register roots before allocation; generated managed entry; blocking transfers root custody; nested callbacks create child activations; VM holds outcome and release tasks"; attribute :>> retirement="Per-wrapper ad hoc root/marker/unwind ownership and collector-side owner-callback waiting; old foreign ABI stays behind explicit adapters until coverage"; attribute :>> benefit="Remove repeated wrapper ownership logic; unblock GC while admitted calls wait; reusable effect/resource metadata"; attribute :>> addedCost="Stable handles, reloads, result slots, native lifetime budgets and affinity queues; unknown writers keep conservative/refusal path"; attribute :>> sourceAnchors="vendor/gambit/lib/c_intf.c:6511-6565;vendor/gambit/lib/setup.c:3277-3421;vendor/ocaml/runtime/signals.c:147-205"; attribute :>> premise="Managed callback escape becomes explicit outcome before C unwinds; raw active C frames are not repeatable resources"; }
part boundary5:Boundary { ref part :>> owner=GambitRuntimeComposition::blueprintModule2; attribute :>> componentId="scheduler"; attribute :>> label="Scheduler and carrier independence"; attribute :>> contract="Participation + WorkClosure + OutcomeLifetime"; attribute :>> replacement="Queue explicit context continuations with exclusive run grants; admitted parked contexts scanned independently; task identity/cancellation separated from continuation reuse"; attribute :>> retirement="OS-thread identity implicitly authorizing execution and retaining collector responsibility after exit"; attribute :>> benefit="M suspended computations can use P carriers with M greater than P; scheduling substrate can support libraries for effects without weakening call/cc"; attribute :>> addedCost="Queues, grants, wakeups and fairness; no automatic parallel map or effect replay; caller-visible task affinity preserved"; attribute :>> sourceAnchors="vendor/gambit/lib/_thread.scm:4623-4706;vendor/gambit/lib/setup.c:745-836;vendor/ocaml/runtime/domain.c"; attribute :>> premise="No duplicate runnable owner; resource readiness does not grant Scheme execution; prove progress without GC/owner wait cycle"; }
part boundary6:Boundary { ref part :>> owner=GambitRuntimeComposition::blueprintModule8; attribute :>> componentId="build"; attribute :>> label="Contract artifacts and backend services"; attribute :>> contract="ArtifactClosure + PlanAbi"; attribute :>> replacement="Build semantic plans separately from generated native units/runtime ABI; LLVM/MLIR are plan consumers and optimization services"; attribute :>> retirement="Repeated unaffected expansion/emission/compilation; duplicate semantic layouts; no requirement for a second Zig runtime"; attribute :>> benefit="Measure actions, generated and preprocessed bytes, invalidation fanout and critical path on Darwin"; attribute :>> addedCost="Dependency/snapshot storage and validation; runtime/ABI changes still invalidate their consumers"; attribute :>> sourceAnchors="vendor/gambit/gsc/_t-c-1.scm;vendor/gambit/gsc/_t-c-2.scm;dev/architecture/toolchain"; attribute :>> premise="Clean/incremental observation equivalence; target contracts preserve all multishot successors before LLVM lowering"; }
part def ProofNeed { attribute obligation:String; attribute method:String; attribute artifact:String; attribute scope:String; attribute premise:String; }
part need0:ProofNeed { attribute :>> obligation="MM-Q"; attribute :>> method="quint"; attribute :>> artifact="dev/refactoring/modern-c/models/quint/map_multishot_composition.qnt"; attribute :>> scope="map-multishot:finite-custody"; attribute :>> premise="Finite relocation, two resumes, root reload, barrier and result-custody interleavings; not Scheme simulation"; }
part need1:ProofNeed { attribute :>> obligation="MM-L"; attribute :>> method="lean"; attribute :>> artifact="dev/refactoring/modern-c/models/lean/MapMultishotComposition.lean"; attribute :>> scope="map-multishot:conditional-laws"; attribute :>> premise="Restore/private-write/share and root/barrier premises only; no all-transition or C proof"; }
part need2:ProofNeed { attribute :>> obligation="MM-FRAME"; attribute :>> method="source"; attribute :>> artifact="dev/refactoring/modern-c/models/quint/map_multishot_composition.qnt"; attribute :>> scope="map-multishot:frame-refinement-open"; attribute :>> premise="FrameSpec encoder/decoder, variable homes and mutable frame API alias simulation"; }
part need3:ProofNeed { attribute :>> obligation="MM-WRITERS"; attribute :>> method="source"; attribute :>> artifact="dev/refactoring/modern-c/models/quint/map_multishot_composition.qnt"; attribute :>> scope="map-multishot:writer-closure-open"; attribute :>> premise="Complete frame/denv/serializer/FFI stores; card overflow and promotion failure coverage"; }
part need4:ProofNeed { attribute :>> obligation="MM-FOREIGN"; attribute :>> method="source"; attribute :>> artifact="dev/refactoring/modern-c/models/quint/map_multishot_composition.qnt"; attribute :>> scope="map-multishot:foreign-exit-open"; attribute :>> premise="Generated roots-before-allocation, nested callbacks, exceptional exit and live-C-frame limits"; }
part need5:ProofNeed { attribute :>> obligation="MM-MEMORY"; attribute :>> method="lean"; attribute :>> artifact="dev/refactoring/modern-c/models/lean/MapMultishotComposition.lean"; attribute :>> scope="map-multishot:c-memory-open"; attribute :>> premise="Race-free slots, release/acquire publication and relocation lifetime refinement"; }
part need6:ProofNeed { attribute :>> obligation="MM-PROGRESS"; attribute :>> method="quint"; attribute :>> artifact="dev/refactoring/modern-c/models/quint/map_multishot_composition.qnt"; attribute :>> scope="map-multishot:fair-progress-open"; attribute :>> premise="Fair scheduler, finite polls, collector completion and no owner/resource wait cycle"; }
part need7:ProofNeed { attribute :>> obligation="MM-SIM"; attribute :>> method="lean"; attribute :>> artifact="dev/refactoring/modern-c/models/lean/MapMultishotComposition.lean"; attribute :>> scope="map-multishot:observation-simulation-open"; attribute :>> premise="Map values, effects, frame aliases, multi-value/exception and dynamic-wind traces simulate source"; }
part def Flow { ref part producer:Boundary; ref part consumer:Boundary; attribute contract:String; }
part flow0:Flow { ref part :>> producer=boundary0; ref part :>> consumer=boundary1; attribute :>> contract="FrameSpec / PointId / GeneratedCheckpoint"; }
part flow1:Flow { ref part :>> producer=boundary1; ref part :>> consumer=boundary2; attribute :>> contract="RootCut / closed participant epoch"; }
part flow2:Flow { ref part :>> producer=boundary3; ref part :>> consumer=boundary2; attribute :>> contract="ControlRoots / remembered mature writes"; }
part flow3:Flow { ref part :>> producer=boundary2; ref part :>> consumer=boundary1; attribute :>> contract="Relocated roots / completed minor epoch"; }
part flow4:Flow { ref part :>> producer=boundary1; ref part :>> consumer=boundary4; attribute :>> contract="Root handles before conversion/allocation"; }
part flow5:Flow { ref part :>> producer=boundary4; ref part :>> consumer=boundary5; attribute :>> contract="Parked activation / result custody"; }
part flow6:Flow { ref part :>> producer=boundary5; ref part :>> consumer=boundary1; attribute :>> contract="Exclusive execution grant / reload"; }
part flow7:Flow { ref part :>> producer=boundary1; ref part :>> consumer=boundary3; attribute :>> contract="Resume same captured computation / wind"; }
part flow8:Flow { ref part :>> producer=boundary0; ref part :>> consumer=boundary6; attribute :>> contract="Closed semantic plan / ABI dependency"; }
part flow9:Flow { ref part :>> producer=boundary6; ref part :>> consumer=boundary0; attribute :>> contract="Target facts / independently validated lowering"; }
part def ObligationUse { ref part component:Boundary; ref part need:ProofNeed; }
part use0:ObligationUse { ref part :>> component=boundary0; ref part :>> need=need0; }
part use1:ObligationUse { ref part :>> component=boundary0; ref part :>> need=need1; }
part use2:ObligationUse { ref part :>> component=boundary0; ref part :>> need=need2; }
part use3:ObligationUse { ref part :>> component=boundary0; ref part :>> need=need7; }
part use4:ObligationUse { ref part :>> component=boundary1; ref part :>> need=need0; }
part use5:ObligationUse { ref part :>> component=boundary1; ref part :>> need=need5; }
part use6:ObligationUse { ref part :>> component=boundary1; ref part :>> need=need6; }
part use7:ObligationUse { ref part :>> component=boundary2; ref part :>> need=need0; }
part use8:ObligationUse { ref part :>> component=boundary2; ref part :>> need=need1; }
part use9:ObligationUse { ref part :>> component=boundary2; ref part :>> need=need3; }
part use10:ObligationUse { ref part :>> component=boundary2; ref part :>> need=need5; }
part use11:ObligationUse { ref part :>> component=boundary3; ref part :>> need=need0; }
part use12:ObligationUse { ref part :>> component=boundary3; ref part :>> need=need1; }
part use13:ObligationUse { ref part :>> component=boundary3; ref part :>> need=need2; }
part use14:ObligationUse { ref part :>> component=boundary3; ref part :>> need=need3; }
part use15:ObligationUse { ref part :>> component=boundary3; ref part :>> need=need7; }
part use16:ObligationUse { ref part :>> component=boundary4; ref part :>> need=need0; }
part use17:ObligationUse { ref part :>> component=boundary4; ref part :>> need=need4; }
part use18:ObligationUse { ref part :>> component=boundary4; ref part :>> need=need5; }
part use19:ObligationUse { ref part :>> component=boundary4; ref part :>> need=need6; }
part use20:ObligationUse { ref part :>> component=boundary5; ref part :>> need=need0; }
part use21:ObligationUse { ref part :>> component=boundary5; ref part :>> need=need6; }
part use22:ObligationUse { ref part :>> component=boundary5; ref part :>> need=need7; }
part use23:ObligationUse { ref part :>> component=boundary6; ref part :>> need=need2; }
part use24:ObligationUse { ref part :>> component=boundary6; ref part :>> need=need7; }
ref part semanticTarget=GambitModernizationTarget::decision0;
ref part domainTarget=GambitModernizationTarget::decision1;
ref part heapTarget=GambitModernizationTarget::decision2;
ref part controlTarget=GambitModernizationTarget::decision3;
ref part foreignTarget=GambitModernizationTarget::decision4;
ref part buildTarget=GambitModernizationTarget::decision5;
attribute architectureClaim:String="Amplify portable Scheme control through one semantic/frame/root contract; no one-shot restriction, no automatic shared-state rollback, no native adoption";
}
