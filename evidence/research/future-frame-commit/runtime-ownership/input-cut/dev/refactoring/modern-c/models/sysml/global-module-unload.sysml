package GambitGlobalModuleUnload { private import ScalarValues::*;
part def SourceRow { attribute key:String; attribute path:String; attribute needle:String; attribute obligation:String; }
part source0:SourceRow { attribute :>> key="image-list"; attribute :>> path="vendor/gambit/lib/os_dyn.c"; attribute :>> needle="___dyn_module ___dyn_mod ="; attribute :>> obligation="Global image-handle owner, not per-VM registry"; }
part source1:SourceRow { attribute :>> key="entry-shape"; attribute :>> path="vendor/gambit/lib/os_dyn.h"; attribute :>> needle="___DL_DESCR descr;"; attribute :>> obligation="Entry has next/handle, no module generation or VM owner manifest"; }
part source2:SourceRow { attribute :>> key="linker-recursion"; attribute :>> path="vendor/gambit/lib/setup.c"; attribute :>> needle="e = for_each_module (ctx, p->mol, proc);"; attribute :>> obligation="One linker can recursively name multiple modules"; }
part source3:SourceRow { attribute :>> key="image-publish"; attribute :>> path="vendor/gambit/lib/os_dyn.c"; attribute :>> needle="p->next = ___dyn_mod.dl_list;"; attribute :>> obligation="Successful handle published in process list"; }
part source4:SourceRow { attribute :>> key="setup-once"; attribute :>> path="vendor/gambit/lib/setup.c"; attribute :>> needle="mol->linkfile.version = -1;"; attribute :>> obligation="Already-setup sentinel is not an owner receipt"; }
part source5:SourceRow { attribute :>> key="native-fields"; attribute :>> path="vendor/gambit/include/gambit.h.in"; attribute :>> needle="___label_struct *lbltbl; int lblcount;"; attribute :>> obligation="Descriptor owns labels, OFD, data and native setup/init pointers"; }
part source6:SourceRow { attribute :>> key="ofd-field"; attribute :>> path="vendor/gambit/include/gambit.h.in"; attribute :>> needle="___WORD *ofdtbl; int ofd_length;"; attribute :>> obligation="OFD lifetime must cover scanners and inactive captured frames"; }
part source7:SourceRow { attribute :>> key="label-copy"; attribute :>> path="vendor/gambit/lib/setup.c"; attribute :>> needle="module->lbltbl = new_lbltbl;"; attribute :>> obligation="Aligned/copied label storage does not detach native host code"; }
part source8:SourceRow { attribute :>> key="ofd-relocate"; attribute :>> path="vendor/gambit/lib/setup.c"; attribute :>> needle="___LABEL_DESCR_SET(lbl, ___CAST(___SCMOBJ,ofd_alloc));"; attribute :>> obligation="Return label may point into relocated OFD allocation"; }
part source9:SourceRow { attribute :>> key="label-host"; attribute :>> path="vendor/gambit/lib/setup.c"; attribute :>> needle="current_host (___ps);"; attribute :>> obligation="Module setup calls host code to derive goto labels"; }
part source10:SourceRow { attribute :>> key="module-pointer"; attribute :>> path="vendor/gambit/lib/setup.c"; attribute :>> needle="___VECTORELEM(descr, ___MODULE_DESCR_MODULE_STRUCT) = module_scmobj;"; attribute :>> obligation="Permanent foreign wrapper exposes native module pointer with null release callback"; }
part source11:SourceRow { attribute :>> key="program-array"; attribute :>> path="vendor/gambit/lib/setup.c"; attribute :>> needle="___VECTORELEM(___VECTORELEM(ctx->program_descr, 0), ctx->module_count) = descr;"; attribute :>> obligation="Program descriptor keeps module descriptor aliases"; }
part source12:SourceRow { attribute :>> key="setup-call"; attribute :>> path="vendor/gambit/lib/setup.c"; attribute :>> needle="return module->setup_mod ();"; attribute :>> obligation="Native setup hook is an executable user"; }
part source13:SourceRow { attribute :>> key="init-call"; attribute :>> path="vendor/gambit/lib/_kernel.scm"; attribute :>> needle="->init_mod (___PSPNC);"; attribute :>> obligation="Real Scheme init path calls module-owned native entry"; }
part source14:SourceRow { attribute :>> key="program-alias"; attribute :>> path="vendor/gambit/lib/_kernel.scm"; attribute :>> needle="___RESULT = ___GSTATE->program_descr;"; attribute :>> obligation="Scheme sees process program descriptor alias"; }
part source15:SourceRow { attribute :>> key="vm-reference"; attribute :>> path="vendor/gambit/lib/_kernel.scm"; attribute :>> needle="___VMSTATE_FROM_PSTATE(___ps)->main_module_ref;"; attribute :>> obligation="VM identity and module reference are separate from process handle"; }
part source16:SourceRow { attribute :>> key="registry-add"; attribute :>> path="vendor/gambit/lib/_kernel.scm"; attribute :>> needle=";; TODO: make manipulation of ##registered-modules atomic"; attribute :>> obligation="Current registry TODO; no concurrent retirement protocol"; }
part source17:SourceRow { attribute :>> key="registry-remove"; attribute :>> path="vendor/gambit/lib/_kernel.scm"; attribute :>> needle="(and x (##set-car! x #f))"; attribute :>> obligation="Registry removal clears one list cell, not all descriptor aliases"; }
part source18:SourceRow { attribute :>> key="descriptor-accessor"; attribute :>> path="vendor/gambit/lib/_kernel#.scm"; attribute :>> needle="(##define-macro (macro-module-descr-module-struct module-descr)"; attribute :>> obligation="Module descriptor native pointer is observable through accessor"; }
part source19:SourceRow { attribute :>> key="scheme-init"; attribute :>> path="vendor/gambit/lib/_kernel.scm"; attribute :>> needle="((macro-module-descr-thunk module-descr))"; attribute :>> obligation="Scheme initializer also retains module procedure code"; }
part source20:SourceRow { attribute :>> key="captured-frame"; attribute :>> path="vendor/gambit/lib/mem.c"; attribute :>> needle="___RETN_GET_FS_LINK(ra1,fs,link)"; attribute :>> obligation="Captured frame traversal dereferences old return descriptor"; }
part source21:SourceRow { attribute :>> key="maintenance-frame"; attribute :>> path="vendor/gambit/lib/mem.c"; attribute :>> needle="descriptor = ___decode_frame_descriptor (___LABEL_DESCR_GET(ra1), 0);"; attribute :>> obligation="GC scan needs descriptor while executing maintenance"; }
part source22:SourceRow { attribute :>> key="restore-frame"; attribute :>> path="vendor/gambit/lib/_kernel.scm"; attribute :>> needle="___RETI_GET_FS_LINK(actual_ra,fs,link)"; attribute :>> obligation="Continuation restore requires RETI/RETN metadata independently of active execution"; }
part source23:SourceRow { attribute :>> key="frame-decode"; attribute :>> path="vendor/gambit/include/gambit.h.in"; attribute :>> needle="#define ___RETN_GET_FS_LINK_GCMAP"; attribute :>> obligation="Root map adapter dereferences frame/OFD representation"; }
part source24:SourceRow { attribute :>> key="ffi-static"; attribute :>> path="vendor/gambit/lib/c_intf.c"; attribute :>> needle="body[-___LABEL_SIZE+___LABEL_HOST]"; attribute :>> obligation="c-define may export static native function pointer"; }
part source25:SourceRow { attribute :>> key="ffi-closure"; attribute :>> path="vendor/gambit/lib/c_intf.c"; attribute :>> needle="___make_c_closure (obj, converter)"; attribute :>> obligation="Dynamic closure captures both procedure and converter code owner"; }
part source26:SourceRow { attribute :>> key="closure-root"; attribute :>> path="vendor/gambit/lib/os_dyn.c"; attribute :>> needle="___set_data_rc (c_closure, proc);"; attribute :>> obligation="RC roots Scheme proc, not a proof of converter image lifetime"; }
part source27:SourceRow { attribute :>> key="foreign-create"; attribute :>> path="vendor/gambit/lib/c_intf.c"; attribute :>> needle="___FOREIGN_RELEASE_FN_FIELD(r) = ___CAST(___SCMOBJ,release_fn);"; attribute :>> obligation="Foreign object stores raw release_fn address"; }
part source28:SourceRow { attribute :>> key="foreign-execute"; attribute :>> path="vendor/gambit/lib/c_intf.c"; attribute :>> needle="if ((e = release_fn (ptr)) != ___FIX(___NO_ERR))"; attribute :>> obligation="Callback executes after fields are cleared; completion still needs a code lease"; }
part source29:SourceRow { attribute :>> key="foreign-sweep"; attribute :>> path="vendor/gambit/lib/mem.c"; attribute :>> needle="___HIDDEN void free_unmarked_still_objs"; attribute :>> obligation="GC can call foreign release for unreachable still objects"; }
part source30:SourceRow { attribute :>> key="foreign-cleanup"; attribute :>> path="vendor/gambit/lib/mem.c"; attribute :>> needle="___HIDDEN void free_still_objs"; attribute :>> obligation="Processor cleanup also executes foreign release code"; }
part source31:SourceRow { attribute :>> key="tcl-call"; attribute :>> path="vendor/gambit/examples/tcltk/tcltk.scm"; attribute :>> needle="char *result = tcltk_call"; attribute :>> obligation="Real Tcl callback enters Scheme from retained RC payload"; }
part source32:SourceRow { attribute :>> key="tcl-delete"; attribute :>> path="vendor/gambit/examples/tcltk/tcltk.scm"; attribute :>> needle="___HIDDEN void scheme_delete_cmd"; attribute :>> obligation="Native registry retains deletion callback code independently of Scheme payload"; }
part source33:SourceRow { attribute :>> key="tcl-register"; attribute :>> path="vendor/gambit/examples/tcltk/tcltk.scm"; attribute :>> needle="Tcl_CreateCommand"; attribute :>> obligation="Native callback installation producer"; }
part source34:SourceRow { attribute :>> key="vm-list"; attribute :>> path="vendor/gambit/include/gambit.h.in"; attribute :>> needle="___MUTEX_DECL(vm_list_mut)"; attribute :>> obligation="VM list synchronization is not per-image borrow admission"; }
part source35:SourceRow { attribute :>> key="vm-cleanup"; attribute :>> path="vendor/gambit/lib/setup.c"; attribute :>> needle="___cleanup_vmstate (___vms);"; attribute :>> obligation="Process cleanup iterates VM owners before global OS cleanup"; }
part source36:SourceRow { attribute :>> key="global-cleanup"; attribute :>> path="vendor/gambit/lib/os_setup.c"; attribute :>> needle="___cleanup_dyn_module ();"; attribute :>> obligation="Both setup-error unwind and global shutdown call dynamic cleanup"; }
part source37:SourceRow { attribute :>> key="image-release"; attribute :>> path="vendor/gambit/lib/os_dyn.c"; attribute :>> needle="dlclose (p->descr);"; attribute :>> obligation="Failed-load and global-list cleanup sites; no return outcome recorded at cleanup site"; }
part source38:SourceRow { attribute :>> key="unload-policy"; attribute :>> path="vendor/gambit/lib/os_dyn.c"; attribute :>> needle="#ifndef ___DONT_UNLOAD_DYN_CODE"; attribute :>> obligation="Existing compile-time no-unload policy remains a required scope input"; }
part source39:SourceRow { attribute :>> key="profile-callback"; attribute :>> path="vendor/gambit/lib/os_dyn.c"; attribute :>> needle="gcov_exit"; attribute :>> obligation="Existing profiling teardown caveat demonstrates lifetime outside Scheme roots"; }
part def ConsumerRow { attribute key:String; attribute callers:String; attribute custody:String; attribute gap:String; }
part consumer0:ConsumerRow { attribute :>> key="image-and-linkers"; attribute :>> callers="dynamic_load / linker_to_mod_or_lnk / for_each_module"; attribute :>> custody="OS handle -> linker graph -> multiple module structs"; attribute :>> gap="New ImageId plus module membership; not one-module-one-handle"; }
part consumer1:ConsumerRow { attribute :>> key="program-and-registry"; attribute :>> callers="setup_module_collect_moddescrs / registered-modules"; attribute :>> custody="Permanent program arrays native foreign pointer and Scheme module wrappers"; attribute :>> gap="Removal must detach all known aliases; old raw representation remains image-pinned"; }
part consumer2:ConsumerRow { attribute :>> key="cross-VM"; attribute :>> callers="GSTATE program_descr / VM main ref / init-mod"; attribute :>> custody="Process code/data can be entered through VM-specific cells and context"; attribute :>> gap="Every VM incarnation must register before executable publication; build flags limit current paths"; }
part consumer3:ConsumerRow { attribute :>> key="captured-frames"; attribute :>> callers="mark_captured_continuation / kernel restoration"; attribute :>> custody="Inactive and multi-shot frames hold return point/OFD usage"; attribute :>> gap="No detach merely from inactive state; stable owner mapping and last reachability receipt required"; }
part consumer4:ConsumerRow { attribute :>> key="GC-maintenance"; attribute :>> callers="mark_continuation / stack transfer / free still"; attribute :>> custody="Descriptor scans and foreign cleanup can outlive the initiating activation"; attribute :>> gap="Transfer child lease before parent last use; unknown delivery retains parent"; }
part consumer5:ConsumerRow { attribute :>> key="native-functions"; attribute :>> callers="SCMOBJ_to_FUNCTION / make_c_closure"; attribute :>> custody="Static host pointer or trampoline with converter and rooted proc"; attribute :>> gap="Proc root alone omits converter code owner and native exports"; }
part consumer6:ConsumerRow { attribute :>> key="foreign-destructors"; attribute :>> callers="POINTER_to_SCMOBJ / release_foreign"; attribute :>> custody="Unreachable payload can still require executable release_fn"; attribute :>> gap="Keep callback image until invocation AND derived work known finished"; }
part consumer7:ConsumerRow { attribute :>> key="Tcl-callbacks"; attribute :>> callers="Tcl_CreateCommand / scheme_call_cmd / scheme_delete_cmd"; attribute :>> custody="Third-party registry stores both invocation and deletion addresses"; attribute :>> gap="Close external registration and drain callbacks; deleting Scheme payload alone insufficient"; }
part consumer8:ConsumerRow { attribute :>> key="loader-teardown"; attribute :>> callers="cleanup_dynamic_load / dlclose"; attribute :>> custody="OS loader may invoke finalizers and retain its own image references"; attribute :>> gap="Prequalify teardown effects; known handle release is not proof of unmapped bytes"; }
part def InventoryRow { attribute key:String; attribute path:String; attribute pattern:String; attribute count:String; attribute scope:String; }
part inventory0:InventoryRow { attribute :>> key="foreign-release-sites"; attribute :>> path="vendor/gambit/lib/mem.c"; attribute :>> pattern="\\b___release_foreign\\s*\\("; attribute :>> count="2"; attribute :>> scope="Bounded lexical alias inventory; not native preprocessed whole-program closure"; }
part inventory1:InventoryRow { attribute :>> key="native-dlclose-sites"; attribute :>> path="vendor/gambit/lib/os_dyn.c"; attribute :>> pattern="\\bdlclose \\(p->descr\\);"; attribute :>> count="2"; attribute :>> scope="Bounded lexical alias inventory; not native preprocessed whole-program closure"; }
part inventory2:InventoryRow { attribute :>> key="cleanup-callers"; attribute :>> path="vendor/gambit/lib/os_setup.c"; attribute :>> pattern="___cleanup_dyn_module \\(\\);"; attribute :>> count="2"; attribute :>> scope="Bounded lexical alias inventory; not native preprocessed whole-program closure"; }
part inventory3:InventoryRow { attribute :>> key="c-closure-proc-store"; attribute :>> path="vendor/gambit/lib/os_dyn.c"; attribute :>> pattern="___set_data_rc \\(c_closure, proc\\);"; attribute :>> count="1"; attribute :>> scope="Bounded lexical alias inventory; not native preprocessed whole-program closure"; }
part inventory4:InventoryRow { attribute :>> key="foreign-release-store"; attribute :>> path="vendor/gambit/lib/c_intf.c"; attribute :>> pattern="___FOREIGN_RELEASE_FN_FIELD\\(r\\) = ___CAST\\(___SCMOBJ,release_fn\\);"; attribute :>> count="1"; attribute :>> scope="Bounded lexical alias inventory; not native preprocessed whole-program closure"; }
part inventory5:InventoryRow { attribute :>> key="registry-mutation-todo"; attribute :>> path="vendor/gambit/lib/_kernel.scm"; attribute :>> pattern="TODO: make manipulation of ##registered-modules atomic"; attribute :>> count="1"; attribute :>> scope="Bounded lexical alias inventory; not native preprocessed whole-program closure"; }
part def ClaimRow { attribute key:String; attribute mechanism:String; attribute condition:String; attribute result:String; attribute gap:String; }
part claim0:ClaimRow { attribute :>> key="identity"; attribute :>> mechanism="Image group owns all member module generations and executable dependencies"; attribute :>> condition="ModuleSpec/loader adapter supplies complete frozen membership"; attribute :>> result="A local receipt identifies VM incarnation generation close epoch and scope digest"; attribute :>> gap="No existing dl_entry membership/owner ledger"; }
part claim1:ClaimRow { attribute :>> key="aggregation"; attribute :>> mechanism="Owner-keyed receipts form an idempotent mask rather than message count"; attribute :>> condition="Complete closed manifest and exact receipt tag match"; attribute :>> result="Duplicate same-owner receipt cannot replace another VM or module receipt"; attribute :>> gap="All-VM and raw native closure not established"; }
part claim2:ClaimRow { attribute :>> key="admission"; attribute :>> mechanism="Borrow reservation and close serialize under the same image authority"; attribute :>> condition="Stable non-image control storage and no overflow/ABA reuse"; attribute :>> result="Earlier observers remain debt; later borrowers fail before dereference"; attribute :>> gap="Actual C11 gate composition and native alias enrollment OPEN"; }
part claim3:ClaimRow { attribute :>> key="derived-work"; attribute :>> mechanism="Known child acceptance transfers existing parent credit"; attribute :>> condition="No parent last use until child owns descriptor and payload dependencies"; attribute :>> result="Post-close task handoff keeps same group alive without reopening public admission"; attribute :>> gap="Source-to-atomic-transfer refinement, executor affinity and unknown completion OPEN"; }
part claim4:ClaimRow { attribute :>> key="unload"; attribute :>> mechanism="Permit precedes pinned loader transaction under qualified teardown"; attribute :>> condition="No users observers pending transfers unknown outcomes; all owner receipts current"; attribute :>> result="Known result only releases owned loader reference; unknown result quarantines identity"; attribute :>> gap="Finalizers platform unload policy actual bytes reclaimed not proved"; }
part def MemoryRow { attribute key:String; attribute publication:String; attribute consumer:String; attribute gap:String; }
part memory0:MemoryRow { attribute :>> key="register-close"; attribute :>> publication="Reserve descriptor credit before reading image payload under stable authority"; attribute :>> consumer="Closing snapshots all accepted owner records; preclose reservations cannot disappear"; attribute :>> gap="vm_list traversal alone is not an image lifetime or native observer proof"; }
part memory1:MemoryRow { attribute :>> key="local-global"; attribute :>> publication="Local release-published receipt after owner admission closure and known drain"; attribute :>> consumer="Aggregator acquire checks ImageId module gen VM incarnation close epoch coverage"; attribute :>> gap="A zero count or duplicate acknowledgment is not an all-owner receipt"; }
part memory2:MemoryRow { attribute :>> key="handoff"; attribute :>> publication="Release publish rooted child task; acquire acceptance before parent return"; attribute :>> consumer="Use single atomic ledger transfer or prove two-step parent retention"; attribute :>> gap="Known failure returns custody; unknown acceptance retains parent and cannot refund"; }
part memory3:MemoryRow { attribute :>> key="final-zero"; attribute :>> publication="Close authority and credit updates serialize; acq_rel returns and acquire drain"; attribute :>> consumer="No new owner can enter after permission; stable metadata survives observers"; attribute :>> gap="Separate flag checks and counter loads require a real C11 proof"; }
part memory4:MemoryRow { attribute :>> key="loader"; attribute :>> publication="Register rooted pinned loader transaction before dropping runtime locks"; attribute :>> consumer="Call dlclose outside VM/GC/registry locks; reconcile once by operation identity"; attribute :>> gap="Destructor reentry escaping asynchronous work or unknown OS result blocks qualification"; }
part def GainRow { attribute key:String; attribute avoided:String; attribute added:String; attribute condition:String; }
part gain0:GainRow { attribute :>> key="code-lifetime"; attribute :>> avoided="Future safe retirement of obsolete code/data generations"; attribute :>> added="Owner registry image membership summary and descriptor dependencies"; attribute :>> condition="Reclaimed bytes must exceed metadata and quarantined memory; handle release may reclaim zero"; }
part gain1:GainRow { attribute :>> key="parallel-VM"; attribute :>> avoided="Independent VM local drains avoid process-wide stop as a default"; attribute :>> added="O(O) owner manifest and receipt aggregation; per-borrow admission bookkeeping"; attribute :>> condition="No benefit if all callers remain raw or global shutdown is the only release point"; }
part gain2:GainRow { attribute :>> key="GC-maintenance"; attribute :>> avoided="Explicit child custody avoids forgotten descriptor readers"; attribute :>> added="Task admission acceptance and exception reconciliation overhead"; attribute :>> condition="Does not eliminate captured frame/root scanning"; }
part gain3:GainRow { attribute :>> key="incremental-code"; attribute :>> avoided="Reusable immutable module/image summaries allow old/new generation coexistence"; attribute :>> added="Invalidation on ABI label/OFD constructor and image membership changes"; attribute :>> condition="No old generation may be dropped merely because a new artifact exists"; }
part gain4:GainRow { attribute :>> key="native-FFI"; attribute :>> avoided="Separate proc payload root from converter/destructor image ownership"; attribute :>> added="Native callback registry drain and raw escape fallback"; attribute :>> condition="All required support is expressible in modern C; no incremental Zig benefit proved"; }
part gain5:GainRow { attribute :>> key="retirement"; attribute :>> avoided="Eventually replace global-only loader list as sole lifetime authority on qualified routes"; attribute :>> added="Stable image records and side-effect-aware loader transaction adapter"; attribute :>> condition="Legacy raw permanent module pointers require retention; no current path retired"; }
part def ContractRow { attribute fromNode:String; attribute toNode:String; attribute custody:String; }
part contract0:ContractRow { attribute :>> fromNode="module-and-image-manifest"; attribute :>> toNode="closed-owner-roster"; attribute :>> custody="All linker members and native dependencies classified"; }
part contract1:ContractRow { attribute :>> fromNode="VM-frame-and-registry-users"; attribute :>> toNode="local-detachment"; attribute :>> custody="Close module entry and detach every VM alias"; }
part contract2:ContractRow { attribute :>> fromNode="FFI-and-external-registries"; attribute :>> toNode="native-code-leases"; attribute :>> custody="Proc root does not pin converter or delete callback"; }
part contract3:ContractRow { attribute :>> fromNode="GC-maintenance-parent"; attribute :>> toNode="accepted-child-task"; attribute :>> custody="Child acceptance before parent credit return"; }
part contract4:ContractRow { attribute :>> fromNode="accepted-child-task"; attribute :>> toNode="local-detachment"; attribute :>> custody="Transferred debt remains with image owner"; }
part contract5:ContractRow { attribute :>> fromNode="local-detachment"; attribute :>> toNode="keyed-receipt-aggregation"; attribute :>> custody="VM incarnation module gen close epoch scope match"; }
part contract6:ContractRow { attribute :>> fromNode="closed-owner-roster"; attribute :>> toNode="keyed-receipt-aggregation"; attribute :>> custody="Freeze enrollment and retain prior observers"; }
part contract7:ContractRow { attribute :>> fromNode="native-code-leases"; attribute :>> toNode="global-drain"; attribute :>> custody="Known callback completion only"; }
part contract8:ContractRow { attribute :>> fromNode="keyed-receipt-aggregation"; attribute :>> toNode="global-drain"; attribute :>> custody="Every distinct required owner represented once"; }
part contract9:ContractRow { attribute :>> fromNode="global-drain"; attribute :>> toNode="unload-permit"; attribute :>> custody="No pending transfer observer or unknown debt"; }
part contract10:ContractRow { attribute :>> fromNode="unload-permit"; attribute :>> toNode="pinned-loader-transaction"; attribute :>> custody="Qualified finalizers and no runtime locks held"; }
part contract11:ContractRow { attribute :>> fromNode="pinned-loader-transaction"; attribute :>> toNode="known-handle-release"; attribute :>> custody="Exactly one reconciled OS-reference operation"; }
part contract12:ContractRow { attribute :>> fromNode="pinned-loader-transaction"; attribute :>> toNode="unknown-quarantine"; attribute :>> custody="No old-code reentry and no blind retry"; }
part contract13:ContractRow { attribute :>> fromNode="known-handle-release"; attribute :>> toNode="platform-memory-observation"; attribute :>> custody="OS policy may still retain image mappings"; }
part def BindingRow { attribute actionName:String; attribute lemma:String; attribute scope:String; }
part binding0:BindingRow { attribute :>> actionName="global_module_unload.borrow0"; attribute :>> lemma="GlobalUnload.borrow0Preserves"; attribute :>> scope="Actual typed IR action; caller and C11 realization remain obligations"; }
part binding1:BindingRow { attribute :>> actionName="global_module_unload.borrow1"; attribute :>> lemma="GlobalUnload.borrow1Preserves"; attribute :>> scope="Actual typed IR action; caller and C11 realization remain obligations"; }
part binding2:BindingRow { attribute :>> actionName="global_module_unload.observe"; attribute :>> lemma="GlobalUnload.observePreserves"; attribute :>> scope="Actual typed IR action; caller and C11 realization remain obligations"; }
part binding3:BindingRow { attribute :>> actionName="global_module_unload.closeGlobal"; attribute :>> lemma="GlobalUnload.closeGlobalPreserves"; attribute :>> scope="Actual typed IR action; caller and C11 realization remain obligations"; }
part binding4:BindingRow { attribute :>> actionName="global_module_unload.closeLocal0"; attribute :>> lemma="GlobalUnload.closeLocal0Preserves"; attribute :>> scope="Actual typed IR action; caller and C11 realization remain obligations"; }
part binding5:BindingRow { attribute :>> actionName="global_module_unload.closeLocal1"; attribute :>> lemma="GlobalUnload.closeLocal1Preserves"; attribute :>> scope="Actual typed IR action; caller and C11 realization remain obligations"; }
part binding6:BindingRow { attribute :>> actionName="global_module_unload.return0"; attribute :>> lemma="GlobalUnload.return0Preserves"; attribute :>> scope="Actual typed IR action; caller and C11 realization remain obligations"; }
part binding7:BindingRow { attribute :>> actionName="global_module_unload.return1"; attribute :>> lemma="GlobalUnload.return1Preserves"; attribute :>> scope="Actual typed IR action; caller and C11 realization remain obligations"; }
part binding8:BindingRow { attribute :>> actionName="global_module_unload.issueLocal0"; attribute :>> lemma="GlobalUnload.issueLocal0Preserves"; attribute :>> scope="Actual typed IR action; caller and C11 realization remain obligations"; }
part binding9:BindingRow { attribute :>> actionName="global_module_unload.issueLocal1"; attribute :>> lemma="GlobalUnload.issueLocal1Preserves"; attribute :>> scope="Actual typed IR action; caller and C11 realization remain obligations"; }
part binding10:BindingRow { attribute :>> actionName="global_module_unload.deliver0"; attribute :>> lemma="GlobalUnload.deliver0Preserves"; attribute :>> scope="Actual typed IR action; caller and C11 realization remain obligations"; }
part binding11:BindingRow { attribute :>> actionName="global_module_unload.deliver1"; attribute :>> lemma="GlobalUnload.deliver1Preserves"; attribute :>> scope="Actual typed IR action; caller and C11 realization remain obligations"; }
part binding12:BindingRow { attribute :>> actionName="global_module_unload.rejectStale"; attribute :>> lemma="GlobalUnload.rejectStalePreserves"; attribute :>> scope="Actual typed IR action; caller and C11 realization remain obligations"; }
part binding13:BindingRow { attribute :>> actionName="global_module_unload.rejectLate"; attribute :>> lemma="GlobalUnload.rejectLatePreserves"; attribute :>> scope="Actual typed IR action; caller and C11 realization remain obligations"; }
part binding14:BindingRow { attribute :>> actionName="global_module_unload.nativeBorrow"; attribute :>> lemma="GlobalUnload.nativeBorrowPreserves"; attribute :>> scope="Actual typed IR action; caller and C11 realization remain obligations"; }
part binding15:BindingRow { attribute :>> actionName="global_module_unload.nativeReturn"; attribute :>> lemma="GlobalUnload.nativeReturnPreserves"; attribute :>> scope="Actual typed IR action; caller and C11 realization remain obligations"; }
part binding16:BindingRow { attribute :>> actionName="global_module_unload.unknownNative"; attribute :>> lemma="GlobalUnload.unknownNativePreserves"; attribute :>> scope="Actual typed IR action; caller and C11 realization remain obligations"; }
part binding17:BindingRow { attribute :>> actionName="global_module_unload.observerRetire"; attribute :>> lemma="GlobalUnload.observerRetirePreserves"; attribute :>> scope="Actual typed IR action; caller and C11 realization remain obligations"; }
part binding18:BindingRow { attribute :>> actionName="global_module_unload.beginChild"; attribute :>> lemma="GlobalUnload.beginChildPreserves"; attribute :>> scope="Actual typed IR action; caller and C11 realization remain obligations"; }
part binding19:BindingRow { attribute :>> actionName="global_module_unload.commitChild"; attribute :>> lemma="GlobalUnload.commitChildPreserves"; attribute :>> scope="Actual typed IR action; caller and C11 realization remain obligations"; }
part binding20:BindingRow { attribute :>> actionName="global_module_unload.rejectChild"; attribute :>> lemma="GlobalUnload.rejectChildPreserves"; attribute :>> scope="Actual typed IR action; caller and C11 realization remain obligations"; }
part binding21:BindingRow { attribute :>> actionName="global_module_unload.unknownChild"; attribute :>> lemma="GlobalUnload.unknownChildPreserves"; attribute :>> scope="Actual typed IR action; caller and C11 realization remain obligations"; }
part binding22:BindingRow { attribute :>> actionName="global_module_unload.taskDone"; attribute :>> lemma="GlobalUnload.taskDonePreserves"; attribute :>> scope="Actual typed IR action; caller and C11 realization remain obligations"; }
part binding23:BindingRow { attribute :>> actionName="global_module_unload.permit"; attribute :>> lemma="GlobalUnload.permitPreserves"; attribute :>> scope="Actual typed IR action; caller and C11 realization remain obligations"; }
part binding24:BindingRow { attribute :>> actionName="global_module_unload.beginUnload"; attribute :>> lemma="GlobalUnload.beginUnloadPreserves"; attribute :>> scope="Actual typed IR action; caller and C11 realization remain obligations"; }
part binding25:BindingRow { attribute :>> actionName="global_module_unload.closeKnown"; attribute :>> lemma="GlobalUnload.closeKnownPreserves"; attribute :>> scope="Actual typed IR action; caller and C11 realization remain obligations"; }
part binding26:BindingRow { attribute :>> actionName="global_module_unload.closeUnknown"; attribute :>> lemma="GlobalUnload.closeUnknownPreserves"; attribute :>> scope="Actual typed IR action; caller and C11 realization remain obligations"; }
part binding27:BindingRow { attribute :>> actionName="global_module_unload.rejectIncomplete"; attribute :>> lemma="GlobalUnload.rejectIncompletePreserves"; attribute :>> scope="Actual typed IR action; caller and C11 realization remain obligations"; }
part def ProofRow { attribute key:String; attribute lemma:String; }
part proof0:ProofRow { attribute :>> key="all-step"; attribute :>> lemma="GlobalUnload.stepPreserves"; }
part proof1:ProofRow { attribute :>> key="reachable"; attribute :>> lemma="GlobalUnload.reachableSafe"; }
part proof2:ProofRow { attribute :>> key="all-receipts"; attribute :>> lemma="GlobalUnload.permitNeedsAllReceipts"; }
part proof3:ProofRow { attribute :>> key="duplicate"; attribute :>> lemma="GlobalUnload.duplicateDeliveryIdempotent"; }
part proof4:ProofRow { attribute :>> key="child-credit"; attribute :>> lemma="GlobalUnload.childTransferConserves"; }
part proof5:ProofRow { attribute :>> key="closed"; attribute :>> lemma="GlobalUnload.knownCloseKeepsAdmissionsClosed"; }
part proof6:ProofRow { attribute :>> key="union"; attribute :>> lemma="GlobalUnloadComposition.allDetachedUnion"; }
part proof7:ProofRow { attribute :>> key="owner-key"; attribute :>> lemma="GlobalUnloadComposition.duplicateOwnerDoesNotSupplyAnotherReceipt"; }
part proof8:ProofRow { attribute :>> key="prior-ready"; attribute :>> lemma="GlobalUnloadComposition.permitRefinesPriorGlobalReadiness"; }
part proof9:ProofRow { attribute :>> key="quotient"; attribute :>> lemma="GlobalUnloadComposition.pairCoverage"; }
part proof10:ProofRow { attribute :>> key="actual-user-debt-zero"; attribute :>> lemma="GlobalUnload.permitOwnersQuiescent"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse6; attribute :>> contract="image-module-membership"; attribute :>> actionName="global_module_unload.permit"; attribute :>> lemma="GlobalUnloadComposition.pairCoverage"; }
part seam1:SeamRow { ref part :>> producer=GambitAssuranceRelations::modelUse3; ref part :>> consumer=GambitAssuranceRelations::modelUse6; attribute :>> contract="GC-child-credit-transfer"; attribute :>> actionName="global_module_unload.commitChild"; attribute :>> lemma="GlobalUnload.childTransferConserves"; }
part seam2:SeamRow { ref part :>> producer=GambitAssuranceRelations::modelUse4; ref part :>> consumer=GambitAssuranceRelations::modelUse6; attribute :>> contract="native-owner-drain"; attribute :>> actionName="global_module_unload.nativeReturn"; attribute :>> lemma="GlobalUnload.nativeReturnPreserves"; }
part seam3:SeamRow { ref part :>> producer=GambitAssuranceRelations::modelUse5; ref part :>> consumer=GambitAssuranceRelations::modelUse6; attribute :>> contract="captured-frame-detachment"; attribute :>> actionName="global_module_unload.issueLocal0"; attribute :>> lemma="GlobalUnload.issueLocal0Preserves"; }
part history:GambitAssuranceRouting::ModelNeed { ref part :>> owner=GambitAssuranceRelations::modelUse6; attribute :>> obligationId="GU-history"; attribute :>> kind="interleaving"; attribute :>> subjectPath="dev/refactoring/modern-c/models/quint/global_module_unload.qnt"; attribute :>> subjectScope="Two-owner aggregation late borrow child custody and loader outcome histories"; attribute :>> premise="Conditional source/formal research; no native unload acceptance"; }
part induction:GambitAssuranceRouting::ModelNeed { ref part :>> owner=GambitAssuranceRelations::modelUse6; attribute :>> obligationId="GU-induction"; attribute :>> kind="induction"; attribute :>> subjectPath="dev/refactoring/modern-c/models/lean/GlobalUnload.lean"; attribute :>> subjectScope="All extracted abstract-ledger steps not C11 weak memory"; attribute :>> premise="Conditional source/formal research; no native unload acceptance"; }
part composition:GambitAssuranceRouting::ModelNeed { ref part :>> owner=GambitAssuranceRelations::modelUse6; attribute :>> obligationId="GU-composition"; attribute :>> kind="induction"; attribute :>> subjectPath="dev/refactoring/modern-c/models/lean/GlobalUnloadComposition.lean"; attribute :>> subjectScope="Owner union and explicit quotient plus preceding global-readiness contract"; attribute :>> premise="Conditional source/formal research; no native unload acceptance"; }
part projection:GambitAssuranceRouting::ModelNeed { ref part :>> owner=GambitAssuranceRelations::modelUse6; attribute :>> obligationId="GU-projection"; attribute :>> kind="restricted-projection"; attribute :>> subjectPath="dev/refactoring/modern-c/models/lean/GlobalUnloadAst.lean"; attribute :>> subjectScope="Bound typed JSON state identity fields and complete action roster"; attribute :>> premise="Conditional source/formal research; no native unload acceptance"; }
part source:GambitAssuranceRouting::ModelNeed { ref part :>> owner=GambitAssuranceRelations::modelUse4; attribute :>> obligationId="GU-source"; attribute :>> kind="source-refinement"; attribute :>> subjectPath="dev/refactoring/modern-c/global-module-unload-design.org"; attribute :>> subjectScope="All VM image member frame FFI teardown producer/consumer closure OPEN"; attribute :>> premise="Conditional source/formal research; no native unload acceptance"; }
part platform:GambitAssuranceRouting::ModelNeed { ref part :>> owner=GambitAssuranceRelations::modelUse6; attribute :>> obligationId="GU-platform"; attribute :>> kind="native-memory-order"; attribute :>> subjectPath="dev/refactoring/modern-c/global-module-unload-design.org"; attribute :>> subjectScope="Actual C11 authority loader outcome and finalizer refinement OPEN"; attribute :>> premise="Conditional source/formal research; no native unload acceptance"; }
}
