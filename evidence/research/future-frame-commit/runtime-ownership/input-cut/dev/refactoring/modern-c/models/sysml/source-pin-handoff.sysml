package GambitSourcePinHandoff { private import ScalarValues::*;
part def Owner { attribute componentId:String; }
part sourceOwner:Owner { attribute :>> componentId="source"; }
part guardOwner:Owner { attribute :>> componentId="guard"; }
part rootsOwner:Owner { attribute :>> componentId="roots"; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-scheme"; attribute :>> path="vendor/gambit/examples/tcltk/tcltk.scm"; attribute :>> needle="___EXT(___release_scmobj) (___EXT(___data_rc)"; attribute :>> obligation="Scheme payload release is distinct from native RC release"; }
part source2:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source3:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source4:SourceRow { attribute :>> key="tcl-vector"; attribute :>> path="vendor/gambit/examples/tcltk/tcltk.scm"; attribute :>> needle="___SCMOBJ vect = ___EXT(___make_vector) (___ps, 1, ___FAL);"; attribute :>> obligation="Existing still vector ownership does not certify generic moving arguments"; }
part source5:SourceRow { attribute :>> key="rc-init"; attribute :>> path="vendor/gambit/lib/memory/rc-allocation.inc"; attribute :>> needle="h->data = ___FAL;"; attribute :>> obligation="Native allocation initializes data before registration; not a source lease"; }
part source6:SourceRow { attribute :>> key="rc-register"; attribute :>> path="vendor/gambit/lib/memory/rc-allocation.inc"; attribute :>> needle="tail->next = h;"; attribute :>> obligation="Plain list insertion requires owner and collector exclusion"; }
part source7:SourceRow { attribute :>> key="rc-free"; attribute :>> path="vendor/gambit/lib/memory/rc-allocation.inc"; attribute :>> needle="if (--h->refcount == 0)"; attribute :>> obligation="Nonatomic decrement and unlink are not safe arbitrary-thread admission"; }
part source8:SourceRow { attribute :>> key="rc-retain"; attribute :>> path="vendor/gambit/lib/memory/rc-allocation.inc"; attribute :>> needle="h->refcount++;"; attribute :>> obligation="Dereferences existing header; cannot safely retain already-freed raw client_data"; }
part source9:SourceRow { attribute :>> key="rc-read"; attribute :>> path="vendor/gambit/lib/memory/rc-allocation.inc"; attribute :>> needle="return h->data;"; attribute :>> obligation="Raw native copy is not a registered update slot"; }
part source10:SourceRow { attribute :>> key="rc-write"; attribute :>> path="vendor/gambit/lib/memory/rc-allocation.inc"; attribute :>> needle="h->data = val;"; attribute :>> obligation="All semantic writers must join freeze/generation protocol or deny admission"; }
part source11:SourceRow { attribute :>> key="rc-cleanup"; attribute :>> path="vendor/gambit/lib/memory/rc-allocation.inc"; attribute :>> needle="___HIDDEN void cleanup_rc"; attribute :>> obligation="Bulk cleanup frees chain independent of per-entry leases"; }
part source12:SourceRow { attribute :>> key="rc-scan"; attribute :>> path="vendor/gambit/lib/memory/rc-roots.inc"; attribute :>> needle="mark_array (work, &h->data, 1);"; attribute :>> obligation="Actual GC slot update; target private carrier is not implicitly scanned"; }
part source13:SourceRow { attribute :>> key="rc-next"; attribute :>> path="vendor/gambit/lib/memory/rc-roots.inc"; attribute :>> needle="___rc_header *next = h->next;"; attribute :>> obligation="RC unlink/free must exclude in-flight scanner list dereferences"; }
part source14:SourceRow { attribute :>> key="origin-context"; attribute :>> path="vendor/gambit/lib/memory/root-origins.inc"; attribute :>> needle="___execution_context *context = task->origin->context;"; attribute :>> obligation="Worker scans origin context; source lifetime is not worker identity"; }
part source15:SourceRow { attribute :>> key="origin-frozen"; attribute :>> path="vendor/gambit/lib/memory/root-origins.inc"; attribute :>> needle="The collective published this complete root origin"; attribute :>> obligation="Source/target registration cut must respect frozen roster"; }
part source16:SourceRow { attribute :>> key="context-scan"; attribute :>> path="vendor/gambit/lib/memory/root-origins.inc"; attribute :>> needle="mark_rc (work, context);"; attribute :>> obligation="Existing RC consumer reusable after origin/epoch qualification"; }
part source17:SourceRow { attribute :>> key="request-root"; attribute :>> path="vendor/gambit/lib/memory/root-origins.inc"; attribute :>> needle="mark_array (work, &___vms->resize_requests[i].thunk, 1);"; attribute :>> obligation="VM-owned root precedent survives absent source origin; not generic pin implementation"; }
part source18:SourceRow { attribute :>> key="retire-refuse"; attribute :>> path="vendor/gambit/lib/memory/capacity-resize.inc"; attribute :>> needle="return 0; /* no freeze receipt for external RC/native borrowers */"; attribute :>> obligation="Current processor retirement refuses nonempty RC rather than manufacturing a lease"; }
part source19:SourceRow { attribute :>> key="storage-transfer"; attribute :>> path="vendor/gambit/lib/memory/capacity-resize.inc"; attribute :>> needle="void ___transfer_retired_still"; attribute :>> obligation="Root transfer alone does not transfer backing still arena"; }
part source20:SourceRow { attribute :>> key="still-dec"; attribute :>> path="vendor/gambit/lib/memory/still-refcount.inc"; attribute :>> needle="___BODY0(obj)[___STILL_REFCOUNT-___STILL_BODY]--;"; attribute :>> obligation="Still ownership decrement differs from movable object root update"; }
part source21:SourceRow { attribute :>> key="release-object"; attribute :>> path="vendor/gambit/lib/memory/object-allocation.inc"; attribute :>> needle="___still_obj_refcount_dec (obj);"; attribute :>> obligation="release_scmobj only acts on allocated still objects in this branch"; }
part source22:SourceRow { attribute :>> key="reload"; attribute :>> path="vendor/gambit/lib/c_intf.c"; attribute :>> needle="proc_or_false = *proc_root; /* reload after allocating the marker */"; attribute :>> obligation="Reload from admitted slot after allocation; pointer address is not admission"; }
part source23:SourceRow { attribute :>> key="ambient"; attribute :>> path="vendor/gambit/lib/c_intf.c"; attribute :>> needle="___data_rc (___c_closure_self ())"; attribute :>> obligation="Payload selection must be bound before reentrant allocating work"; }
part source24:SourceRow { attribute :>> key="legacy"; attribute :>> path="vendor/gambit/lib/c_intf.c"; attribute :>> needle="Legacy raw SFUN entry is not made a registered-root interface"; attribute :>> obligation="No complete generic source-pin issuer identified"; }
part source25:SourceRow { attribute :>> key="closure-set"; attribute :>> path="vendor/gambit/lib/os_dyn.c"; attribute :>> needle="___set_data_rc (c_closure, proc);"; attribute :>> obligation="Other concrete RC payload producer; platform conditional"; }
part source26:SourceRow { attribute :>> key="sfun-prologue"; attribute :>> path="vendor/gambit/gsc/_ptree2.scm"; attribute :>> needle="(define (c-make-function sfun? name param-typs result-typ make-body)"; attribute :>> obligation="Pre-marker bootstrap spans generated host entry and source adapter"; }
part source27:SourceRow { attribute :>> key="pstate-cleanup"; attribute :>> path="vendor/gambit/lib/memory/memory-lifecycle.inc"; attribute :>> needle="free_still_objs (___ps);"; attribute :>> obligation="cleanup_mem_pstate frees still storage before cleanup_rc; not an active-lease release helper"; }
part source28:SourceRow { attribute :>> key="vm-cleanup"; attribute :>> path="vendor/gambit/lib/memory/memory-lifecycle.inc"; attribute :>> needle="___cleanup_mem_pstate (___PSTATE_FROM_PROCESSOR_ID(0,___vms));"; attribute :>> obligation="VM cleanup still has other-processors TODO; global retirement qualification cannot be inferred"; }
part source29:SourceRow { attribute :>> key="pstate-wrapper"; attribute :>> path="vendor/gambit/lib/setup.c"; attribute :>> needle="___cleanup_mem_pstate (___ps);"; attribute :>> obligation="PSTATE cleanup wrapper reaches destructive memory cleanup before OS cleanup"; }
part def IdentityRow { attribute key:String; attribute structure:String; attribute rule:String; attribute caveat:String; }
part identity0:IdentityRow { attribute :>> key="source"; attribute :>> structure="VM SourceSlotId + generation + payload lineage"; attribute :>> rule="Stable metadata exists before client_data dereference"; attribute :>> caveat="Do not CAS a freed native header"; }
part identity1:IdentityRow { attribute :>> key="pin"; attribute :>> structure="SourceId + PinId + owner generation"; attribute :>> rule="Exact return is idempotent; nested pin distinct"; attribute :>> caveat="Lifetime pin is not an immovable-object pin"; }
part identity2:IdentityRow { attribute :>> key="carrier"; attribute :>> structure="ReservedSlotId + registration generation + GC round"; attribute :>> rule="Private candidate cannot become authoritative until enrollment acknowledged"; attribute :>> caveat="Release/acquire alone does not enroll frozen root set"; }
part identity3:IdentityRow { attribute :>> key="handoff"; attribute :>> structure="PinId + CarrierId + GuardId + commit identity"; attribute :>> rule="Source pin drops only after exact commit outcome and target custody known"; attribute :>> caveat="Unknown reply is not failed reservation"; }
part identity4:IdentityRow { attribute :>> key="payload"; attribute :>> structure="Semantic payload identity plus GC relocation revision"; attribute :>> rule="GC relocation preserves identity; managed semantic replacement changes generation"; attribute :>> caveat="Two fixed leases model no arbitrary mutable payload replacement"; }
part def IssuerRow { attribute key:String; attribute proposedIssuer:String; attribute actualSource:String; attribute status:String; attribute responsibility:String; }
part issuer0:IssuerRow { attribute :>> key="pin"; attribute :>> proposedIssuer="Stable source-domain owner before native dispatch"; attribute :>> actualSource="data_rc/addref_rc dereference raw headers; no complete source gate"; attribute :>> status="Required native owner adapter"; attribute :>> responsibility="Validate generation; atomically accept pin before close without allocation"; }
part issuer1:IssuerRow { attribute :>> key="close"; attribute :>> proposedIssuer="Source deletion adapter on qualified owner"; attribute :>> actualSource="scheme_delete_cmd releases Scheme and native resources directly"; attribute :>> status="Must redesign logical delete versus physical cleanup"; attribute :>> responsibility="Close new pins immediately; defer release without blocking callback/GC"; }
part issuer2:IssuerRow { attribute :>> key="enroll"; attribute :>> proposedIssuer="RootRegistry or collective root-origin owner"; attribute :>> actualSource="mark_rc scans actual slots; origin set published before work"; attribute :>> status="Generic carrier enrollment receipt absent"; attribute :>> responsibility="Validate same GC round and refresh candidate if source moved"; }
part issuer3:IssuerRow { attribute :>> key="guard"; attribute :>> proposedIssuer="Stable host operation owner"; attribute :>> actualSource="Rooted helper reloads after allocation; generic wrapper disclaims registration"; attribute :>> status="Reservation/exit owner still not implemented"; attribute :>> responsibility="Bind exact carrier and source; retain record on unknown outcome"; }
part issuer4:IssuerRow { attribute :>> key="resolve"; attribute :>> proposedIssuer="Same reservation commit owner"; attribute :>> actualSource="No new keyed commit service implemented"; attribute :>> status="Conditional model oracle"; attribute :>> responsibility="Answer committed/failed by exact operation; query is not execution retry"; }
part issuer5:IssuerRow { attribute :>> key="storage"; attribute :>> proposedIssuer="VM storage/retirement owner"; attribute :>> actualSource="can_retire_pstate refuses external RC; still transfer has closed-collective preconditions"; attribute :>> status="Existing fail-closed path reusable"; attribute :>> responsibility="Keep backing arena and root descriptor alive through all pin/scan leases"; }
part def ClaimRow { attribute key:String; attribute mechanism:String; attribute condition:String; attribute result:String; attribute gap:String; }
part claim0:ClaimRow { attribute :>> key="close-pin"; attribute :>> mechanism="One metadata gate/count or serialized owner decision"; attribute :>> condition="Stable control record and no overflow"; attribute :>> result="Pin linearizes before close or is rejected"; attribute :>> gap="Raw header lifetime and actual C23 primitive selection open"; }
part claim1:ClaimRow { attribute :>> key="gc-private"; attribute :>> mechanism="GC leaves private candidate unregistered; enrollment compares relocation revision"; attribute :>> condition="Source lease stays scan-visible; freeze excludes root mutations"; attribute :>> result="Stale candidate cannot enroll without refresh"; attribute :>> gap="Source-to-native moving-GC simulation open"; }
part claim2:ClaimRow { attribute :>> key="nested"; attribute :>> mechanism="Two independent exact pin records"; attribute :>> condition="Real source adapter covers entry and deletion"; attribute :>> result="Returning outer pin cannot settle nested pin"; attribute :>> gap="Arbitrary nesting, exhaustion and finite generation open"; }
part claim3:ClaimRow { attribute :>> key="unknown"; attribute :>> mechanism="Reserved/unknown guard retains both source pin and carrier"; attribute :>> condition="Exact commit-owner lookup"; attribute :>> result="No blind retry or early source retirement"; attribute :>> gap="Actual non-abandonable owner and eventual reconciliation open"; }
part claim4:ClaimRow { attribute :>> key="bridge"; attribute :>> mechanism="CarrierAdmission relation to prior bootstrap model"; attribute :>> condition="Same carrier revision and supplied prior safety"; attribute :>> result="Prior guard reservation remains safe"; attribute :>> gap="Not a complete runtime source simulation"; }
part claim5:ClaimRow { attribute :>> key="storage"; attribute :>> mechanism="Separate root liveness from still backing storage"; attribute :>> condition="All arenas and source context retirements accounted"; attribute :>> result="Root receipt alone never permits freeing backing memory"; attribute :>> gap="VM-wide storage freeze and foreign cleanup closure unresolved"; }
part def MemoryRow { attribute key:String; attribute publication:String; attribute observation:String; attribute obligation:String; attribute overhead:String; }
part memory0:MemoryRow { attribute :>> key="gate"; attribute :>> publication="Close/pin serialized on stable SourceControl metadata"; attribute :>> observation="Acquire sees generation and admission outcome"; attribute :>> obligation="No check-open then later increment; no count wrap; no lock across GC"; attribute :>> overhead="Bounded atomic or owner-thread metadata operation"; }
part memory1:MemoryRow { attribute :>> key="candidate"; attribute :>> publication="Source read under registered root-access interval"; attribute :>> observation="Private copy may become stale when GC runs"; attribute :>> obligation="Pin prevents owner deletion, not relocation or concurrent raw setter"; attribute :>> overhead="Nonallocating root-access and refresh"; }
part memory2:MemoryRow { attribute :>> key="enrollment"; attribute :>> publication="Register target under same GC round or defer until source refresh"; attribute :>> observation="Collector acknowledges target slot coverage"; attribute :>> obligation="Do not release source when target missed frozen origin set"; attribute :>> overhead="Root-origin ack and one slot per admitted ingress"; }
part memory3:MemoryRow { attribute :>> key="guard"; attribute :>> publication="Allocating reservation reads enrolled target after GC"; attribute :>> observation="Commit response or keyed query names same carrier"; attribute :>> obligation="Unknown keeps pin and target; no owner lock while allocating"; attribute :>> overhead="Stable record and retained query result"; }
part memory4:MemoryRow { attribute :>> key="source-delete"; attribute :>> publication="After gate closed and all source pins gone, outside scan interval"; attribute :>> observation="Native block and Scheme ownership released separately"; attribute :>> obligation="Retain scan descriptor and storage if any maintenance reader remains"; attribute :>> overhead="Deferred deletion and scan-drain coordination"; }
part memory5:MemoryRow { attribute :>> key="nested"; attribute :>> publication="Each invocation owns its PinId and carrier"; attribute :>> observation="Outer return cannot decrement child custody"; attribute :>> obligation="No mutable ambient source retarget"; attribute :>> overhead="Depth-dependent reserved capacity"; }
part def GainRow { attribute key:String; attribute avoided:String; attribute added:String; attribute condition:String; }
part gain0:GainRow { attribute :>> key="root-reuse"; attribute :>> avoided="New generic roots where an admitted existing RC slot already suffices"; attribute :>> added="Source pin, GC participation and root-domain proof"; attribute :>> condition="Keep source registered if safe; do not mandate carrier copy for every static/owner path"; }
part gain1:GainRow { attribute :>> key="carrier"; attribute :>> avoided="Ad hoc per-wrapper roots and lost-outcome recovery"; attribute :>> added="Reserved slots and registration acknowledgements"; attribute :>> condition="Retire actual duplicated support instead of retaining two paths"; }
part gain2:GainRow { attribute :>> key="no-block-delete"; attribute :>> avoided="Delete/GC/callback cycle caused by synchronous wait"; attribute :>> added="Deferred logical deletion and owner polling/query"; attribute :>> condition="Old owner remains participant; no drain while holding needed lock"; }
part gain3:GainRow { attribute :>> key="nested"; attribute :>> avoided="Duplicate settlement or parent-child custody corruption"; attribute :>> added="Exact pin record and carrier per nested activation"; attribute :>> condition="Capacity/overflow and arbitrary nesting remain admission obligations"; }
part gain4:GainRow { attribute :>> key="normalization"; attribute :>> avoided="At most one redundant metadata traversal"; attribute :>> added="Pin, enrollment, refresh, scan and unknown-retention costs"; attribute :>> condition="Positive only after real source/guard/writer/storage gates and all marginal costs"; }
part def ContractRow { attribute fromNode:String; attribute toNode:String; attribute custody:String; }
part contract0:ContractRow { attribute :>> fromNode="Stable source adapter"; attribute :>> toNode="Admission gate"; attribute :>> custody="lookup stable generation before raw payload access"; }
part contract1:ContractRow { attribute :>> fromNode="Admission gate"; attribute :>> toNode="Exact source pin"; attribute :>> custody="pin before close or reject; no allocation"; }
part contract2:ContractRow { attribute :>> fromNode="Exact source pin"; attribute :>> toNode="Private carrier"; attribute :>> custody="read under root access; source remains scanned"; }
part contract3:ContractRow { attribute :>> fromNode="Private carrier"; attribute :>> toNode="Enrollment owner"; attribute :>> custody="same round or refresh after source moved"; }
part contract4:ContractRow { attribute :>> fromNode="Enrollment owner"; attribute :>> toNode="Stable guard owner"; attribute :>> custody="target scan coverage acknowledged before allocating"; }
part contract5:ContractRow { attribute :>> fromNode="Stable guard owner"; attribute :>> toNode="Commit lookup"; attribute :>> custody="reply lost queries same operation"; }
part contract6:ContractRow { attribute :>> fromNode="Commit lookup"; attribute :>> toNode="Source pin return"; attribute :>> custody="release only after target and guard outcome known"; }
part contract7:ContractRow { attribute :>> fromNode="Stable guard owner"; attribute :>> toNode="Nested callback"; attribute :>> custody="independent pin and carrier"; }
part contract8:ContractRow { attribute :>> fromNode="Source pin return"; attribute :>> toNode="Deferred source deletion"; attribute :>> custody="all source pins gone and scanners drained"; }
part contract9:ContractRow { attribute :>> fromNode="Deferred source deletion"; attribute :>> toNode="VM storage owner"; attribute :>> custody="root liveness and backing arena lifetime separate"; }
part contract10:ContractRow { attribute :>> fromNode="Stable guard owner"; attribute :>> toNode="Unknown escrow"; attribute :>> custody="retain source pin plus enrolled carrier"; }
part contract11:ContractRow { attribute :>> fromNode="Unknown escrow"; attribute :>> toNode="Commit lookup"; attribute :>> custody="exact owner resolves; no blind re-execution"; }
part def BindingRow { attribute actionName:String; attribute lemma:String; attribute scope:String; }
part binding0:BindingRow { attribute :>> actionName="source_pin_handoff.pinOuter"; attribute :>> lemma="SourcePin.pinOuterPreserves"; attribute :>> scope="typed two-fixed-pin model; real source/GC authorities external"; }
part binding1:BindingRow { attribute :>> actionName="source_pin_handoff.pinNested"; attribute :>> lemma="SourcePin.pinNestedPreserves"; attribute :>> scope="typed two-fixed-pin model; real source/GC authorities external"; }
part binding2:BindingRow { attribute :>> actionName="source_pin_handoff.closeSource"; attribute :>> lemma="SourcePin.closeSourcePreserves"; attribute :>> scope="typed two-fixed-pin model; real source/GC authorities external"; }
part binding3:BindingRow { attribute :>> actionName="source_pin_handoff.rejectLatePin"; attribute :>> lemma="SourcePin.rejectLatePinPreserves"; attribute :>> scope="typed two-fixed-pin model; real source/GC authorities external"; }
part binding4:BindingRow { attribute :>> actionName="source_pin_handoff.copy0"; attribute :>> lemma="SourcePin.copy0Preserves"; attribute :>> scope="typed two-fixed-pin model; real source/GC authorities external"; }
part binding5:BindingRow { attribute :>> actionName="source_pin_handoff.refresh0"; attribute :>> lemma="SourcePin.refresh0Preserves"; attribute :>> scope="typed two-fixed-pin model; real source/GC authorities external"; }
part binding6:BindingRow { attribute :>> actionName="source_pin_handoff.enroll0"; attribute :>> lemma="SourcePin.enroll0Preserves"; attribute :>> scope="typed two-fixed-pin model; real source/GC authorities external"; }
part binding7:BindingRow { attribute :>> actionName="source_pin_handoff.reserveGuard0"; attribute :>> lemma="SourcePin.reserveGuard0Preserves"; attribute :>> scope="typed two-fixed-pin model; real source/GC authorities external"; }
part binding8:BindingRow { attribute :>> actionName="source_pin_handoff.commitGuard0"; attribute :>> lemma="SourcePin.commitGuard0Preserves"; attribute :>> scope="typed two-fixed-pin model; real source/GC authorities external"; }
part binding9:BindingRow { attribute :>> actionName="source_pin_handoff.lostReservation0"; attribute :>> lemma="SourcePin.lostReservation0Preserves"; attribute :>> scope="typed two-fixed-pin model; real source/GC authorities external"; }
part binding10:BindingRow { attribute :>> actionName="source_pin_handoff.resolveCommitted0"; attribute :>> lemma="SourcePin.resolveCommitted0Preserves"; attribute :>> scope="typed two-fixed-pin model; real source/GC authorities external"; }
part binding11:BindingRow { attribute :>> actionName="source_pin_handoff.resolveFailed0"; attribute :>> lemma="SourcePin.resolveFailed0Preserves"; attribute :>> scope="typed two-fixed-pin model; real source/GC authorities external"; }
part binding12:BindingRow { attribute :>> actionName="source_pin_handoff.queryAck0"; attribute :>> lemma="SourcePin.queryAck0Preserves"; attribute :>> scope="typed two-fixed-pin model; real source/GC authorities external"; }
part binding13:BindingRow { attribute :>> actionName="source_pin_handoff.returnPin0"; attribute :>> lemma="SourcePin.returnPin0Preserves"; attribute :>> scope="typed two-fixed-pin model; real source/GC authorities external"; }
part binding14:BindingRow { attribute :>> actionName="source_pin_handoff.repeatReturn0"; attribute :>> lemma="SourcePin.repeatReturn0Preserves"; attribute :>> scope="typed two-fixed-pin model; real source/GC authorities external"; }
part binding15:BindingRow { attribute :>> actionName="source_pin_handoff.abortBeforeGuard0"; attribute :>> lemma="SourcePin.abortBeforeGuard0Preserves"; attribute :>> scope="typed two-fixed-pin model; real source/GC authorities external"; }
part binding16:BindingRow { attribute :>> actionName="source_pin_handoff.outerExit0"; attribute :>> lemma="SourcePin.outerExit0Preserves"; attribute :>> scope="typed two-fixed-pin model; real source/GC authorities external"; }
part binding17:BindingRow { attribute :>> actionName="source_pin_handoff.retireCarrier0"; attribute :>> lemma="SourcePin.retireCarrier0Preserves"; attribute :>> scope="typed two-fixed-pin model; real source/GC authorities external"; }
part binding18:BindingRow { attribute :>> actionName="source_pin_handoff.copy1"; attribute :>> lemma="SourcePin.copy1Preserves"; attribute :>> scope="typed two-fixed-pin model; real source/GC authorities external"; }
part binding19:BindingRow { attribute :>> actionName="source_pin_handoff.refresh1"; attribute :>> lemma="SourcePin.refresh1Preserves"; attribute :>> scope="typed two-fixed-pin model; real source/GC authorities external"; }
part binding20:BindingRow { attribute :>> actionName="source_pin_handoff.enroll1"; attribute :>> lemma="SourcePin.enroll1Preserves"; attribute :>> scope="typed two-fixed-pin model; real source/GC authorities external"; }
part binding21:BindingRow { attribute :>> actionName="source_pin_handoff.reserveGuard1"; attribute :>> lemma="SourcePin.reserveGuard1Preserves"; attribute :>> scope="typed two-fixed-pin model; real source/GC authorities external"; }
part binding22:BindingRow { attribute :>> actionName="source_pin_handoff.commitGuard1"; attribute :>> lemma="SourcePin.commitGuard1Preserves"; attribute :>> scope="typed two-fixed-pin model; real source/GC authorities external"; }
part binding23:BindingRow { attribute :>> actionName="source_pin_handoff.lostReservation1"; attribute :>> lemma="SourcePin.lostReservation1Preserves"; attribute :>> scope="typed two-fixed-pin model; real source/GC authorities external"; }
part binding24:BindingRow { attribute :>> actionName="source_pin_handoff.resolveCommitted1"; attribute :>> lemma="SourcePin.resolveCommitted1Preserves"; attribute :>> scope="typed two-fixed-pin model; real source/GC authorities external"; }
part binding25:BindingRow { attribute :>> actionName="source_pin_handoff.resolveFailed1"; attribute :>> lemma="SourcePin.resolveFailed1Preserves"; attribute :>> scope="typed two-fixed-pin model; real source/GC authorities external"; }
part binding26:BindingRow { attribute :>> actionName="source_pin_handoff.queryAck1"; attribute :>> lemma="SourcePin.queryAck1Preserves"; attribute :>> scope="typed two-fixed-pin model; real source/GC authorities external"; }
part binding27:BindingRow { attribute :>> actionName="source_pin_handoff.returnPin1"; attribute :>> lemma="SourcePin.returnPin1Preserves"; attribute :>> scope="typed two-fixed-pin model; real source/GC authorities external"; }
part binding28:BindingRow { attribute :>> actionName="source_pin_handoff.repeatReturn1"; attribute :>> lemma="SourcePin.repeatReturn1Preserves"; attribute :>> scope="typed two-fixed-pin model; real source/GC authorities external"; }
part binding29:BindingRow { attribute :>> actionName="source_pin_handoff.abortBeforeGuard1"; attribute :>> lemma="SourcePin.abortBeforeGuard1Preserves"; attribute :>> scope="typed two-fixed-pin model; real source/GC authorities external"; }
part binding30:BindingRow { attribute :>> actionName="source_pin_handoff.outerExit1"; attribute :>> lemma="SourcePin.outerExit1Preserves"; attribute :>> scope="typed two-fixed-pin model; real source/GC authorities external"; }
part binding31:BindingRow { attribute :>> actionName="source_pin_handoff.retireCarrier1"; attribute :>> lemma="SourcePin.retireCarrier1Preserves"; attribute :>> scope="typed two-fixed-pin model; real source/GC authorities external"; }
part binding32:BindingRow { attribute :>> actionName="source_pin_handoff.retireSource"; attribute :>> lemma="SourcePin.retireSourcePreserves"; attribute :>> scope="typed two-fixed-pin model; real source/GC authorities external"; }
part binding33:BindingRow { attribute :>> actionName="source_pin_handoff.freezeGc"; attribute :>> lemma="SourcePin.freezeGcPreserves"; attribute :>> scope="typed two-fixed-pin model; real source/GC authorities external"; }
part binding34:BindingRow { attribute :>> actionName="source_pin_handoff.finishGcNone"; attribute :>> lemma="SourcePin.finishGcNonePreserves"; attribute :>> scope="typed two-fixed-pin model; real source/GC authorities external"; }
part binding35:BindingRow { attribute :>> actionName="source_pin_handoff.finishGcOuter"; attribute :>> lemma="SourcePin.finishGcOuterPreserves"; attribute :>> scope="typed two-fixed-pin model; real source/GC authorities external"; }
part binding36:BindingRow { attribute :>> actionName="source_pin_handoff.finishGcNested"; attribute :>> lemma="SourcePin.finishGcNestedPreserves"; attribute :>> scope="typed two-fixed-pin model; real source/GC authorities external"; }
part binding37:BindingRow { attribute :>> actionName="source_pin_handoff.finishGcBoth"; attribute :>> lemma="SourcePin.finishGcBothPreserves"; attribute :>> scope="typed two-fixed-pin model; real source/GC authorities external"; }
part def ProofRow { attribute key:String; attribute lemma:String; }
part proof0:ProofRow { attribute :>> key="stepPreserves"; attribute :>> lemma="SourcePin.stepPreserves"; }
part proof1:ProofRow { attribute :>> key="reachableSafe"; attribute :>> lemma="SourcePin.reachableSafe"; }
part proof2:ProofRow { attribute :>> key="noRetireWithOuterPin"; attribute :>> lemma="SourcePin.noRetireWithOuterPin"; }
part proof3:ProofRow { attribute :>> key="noRetireWithNestedPin"; attribute :>> lemma="SourcePin.noRetireWithNestedPin"; }
part proof4:ProofRow { attribute :>> key="staleCandidateCannotEnroll"; attribute :>> lemma="SourcePin.staleCandidateCannotEnroll"; }
part proof5:ProofRow { attribute :>> key="unknownRetainsCustody"; attribute :>> lemma="SourcePin.unknownRetainsCustody"; }
part proof6:ProofRow { attribute :>> key="duplicateReturnPreservesChild"; attribute :>> lemma="SourcePin.duplicateReturnPreservesChild"; }
part proof7:ProofRow { attribute :>> key="enrolledCarrierFresh"; attribute :>> lemma="SourcePin.enrolledCarrierFresh"; }
part proof8:ProofRow { attribute :>> key="closedSourceRejectsPin"; attribute :>> lemma="SourcePin.closedSourceRejectsPin"; }
part proof9:ProofRow { attribute :>> key="sourceReleaseOutsideScan"; attribute :>> lemma="SourcePin.sourceReleaseOutsideScan"; }
part proof10:ProofRow { attribute :>> key="guardReservationAgreement"; attribute :>> lemma="SourcePinBridge.guardReservationAgreement"; }
part proof11:ProofRow { attribute :>> key="collectorRevisionAgreement"; attribute :>> lemma="SourcePinBridge.collectorRevisionAgreement"; }
part proof12:ProofRow { attribute :>> key="reservationSuccessorSafe"; attribute :>> lemma="SourcePinBridge.reservationSuccessorSafe"; }
part def RouteRow { attribute component:String; attribute actionName:String; attribute lemma:String; attribute producerAnchor:String; attribute obligationId:String; }
part route0:RouteRow { attribute :>> component="source"; attribute :>> actionName="source_pin_handoff.pinOuter"; attribute :>> lemma="SourcePin.pinOuterPreserves"; attribute :>> producerAnchor="rc-retain"; attribute :>> obligationId="SP-source"; }
part route1:RouteRow { attribute :>> component="source"; attribute :>> actionName="source_pin_handoff.pinNested"; attribute :>> lemma="SourcePin.pinNestedPreserves"; attribute :>> producerAnchor="tcl-call"; attribute :>> obligationId="SP-source"; }
part route2:RouteRow { attribute :>> component="source"; attribute :>> actionName="source_pin_handoff.closeSource"; attribute :>> lemma="SourcePin.closeSourcePreserves"; attribute :>> producerAnchor="tcl-delete-native"; attribute :>> obligationId="SP-source"; }
part route3:RouteRow { attribute :>> component="roots"; attribute :>> actionName="source_pin_handoff.copy0"; attribute :>> lemma="SourcePin.copy0Preserves"; attribute :>> producerAnchor="rc-read"; attribute :>> obligationId="SP-roots"; }
part route4:RouteRow { attribute :>> component="roots"; attribute :>> actionName="source_pin_handoff.enroll0"; attribute :>> lemma="SourcePin.enroll0Preserves"; attribute :>> producerAnchor="origin-frozen"; attribute :>> obligationId="SP-roots"; }
part route5:RouteRow { attribute :>> component="roots"; attribute :>> actionName="source_pin_handoff.finishGcBoth"; attribute :>> lemma="SourcePin.finishGcBothPreserves"; attribute :>> producerAnchor="rc-scan"; attribute :>> obligationId="SP-roots"; }
part route6:RouteRow { attribute :>> component="guard"; attribute :>> actionName="source_pin_handoff.reserveGuard0"; attribute :>> lemma="SourcePin.reserveGuard0Preserves"; attribute :>> producerAnchor="reload"; attribute :>> obligationId="SP-execution"; }
part route7:RouteRow { attribute :>> component="guard"; attribute :>> actionName="source_pin_handoff.lostReservation0"; attribute :>> lemma="SourcePin.lostReservation0Preserves"; attribute :>> producerAnchor="legacy"; attribute :>> obligationId="SP-execution"; }
part route8:RouteRow { attribute :>> component="guard"; attribute :>> actionName="source_pin_handoff.resolveCommitted0"; attribute :>> lemma="SourcePin.resolveCommitted0Preserves"; attribute :>> producerAnchor="legacy"; attribute :>> obligationId="SP-execution"; }
part route9:RouteRow { attribute :>> component="source"; attribute :>> actionName="source_pin_handoff.returnPin1"; attribute :>> lemma="SourcePin.returnPin1Preserves"; attribute :>> producerAnchor="tcl-delete-scheme"; attribute :>> obligationId="SP-source"; }
part route10:RouteRow { attribute :>> component="storage"; attribute :>> actionName="source_pin_handoff.retireSource"; attribute :>> lemma="SourcePin.retireSourcePreserves"; attribute :>> producerAnchor="retire-refuse"; attribute :>> obligationId="SP-storage"; }
part route11:RouteRow { attribute :>> component="roots"; attribute :>> actionName="source_pin_handoff.retireCarrier0"; attribute :>> lemma="SourcePin.retireCarrier0Preserves"; attribute :>> producerAnchor="rc-next"; attribute :>> obligationId="SP-roots"; }
part def Need { attribute obligationId:String; attribute kind:String; attribute subjectPath:String; attribute subjectScope:String; ref owner:Owner; }
part formal:Need { attribute :>> obligationId="SP-formal"; attribute :>> kind="induction"; attribute :>> subjectPath="dev/refactoring/modern-c/models/lean/SourcePin.lean"; attribute :>> subjectScope="two fixed leases, private/enrolled revision and deletion safety"; ref :>> owner=guardOwner; }
part bridge:Need { attribute :>> obligationId="SP-bridge"; attribute :>> kind="composition"; attribute :>> subjectPath="dev/refactoring/modern-c/models/lean/SourcePinBridge.lean"; attribute :>> subjectScope="carrier revision and prior guard-reservation agreement under explicit relation"; ref :>> owner=guardOwner; }
part sourceNeed:Need { attribute :>> obligationId="SP-source"; attribute :>> kind="source"; attribute :>> subjectPath="vendor/gambit/examples/tcltk/tcltk.scm"; attribute :>> subjectScope="stable handle lookup, actual nonallocating source pin and logical deletion adapter"; ref :>> owner=sourceOwner; }
part execution:Need { attribute :>> obligationId="SP-execution"; attribute :>> kind="source"; attribute :>> subjectPath="vendor/gambit/lib/c_intf.c"; attribute :>> subjectScope="stable reservation issuer, exact commit lookup and exception completion owner"; ref :>> owner=guardOwner; }
part roots:Need { attribute :>> obligationId="SP-roots"; attribute :>> kind="source"; attribute :>> subjectPath="vendor/gambit/lib/memory/root-origins.inc"; attribute :>> subjectScope="source access exclusion, target enrollment and frozen-round scan acknowledgement"; ref :>> owner=rootsOwner; }
part writers:Need { attribute :>> obligationId="SP-writers"; attribute :>> kind="source"; attribute :>> subjectPath="vendor/gambit/lib/memory/rc-allocation.inc"; attribute :>> subjectScope="all raw setter, release, bulk cleanup and indirect borrower closure"; ref :>> owner=sourceOwner; }
part platform:Need { attribute :>> obligationId="SP-platform"; attribute :>> kind="platform"; attribute :>> subjectPath="dev/refactoring/modern-c/language-baseline-design.org"; attribute :>> subjectScope="C23 atomic gate/count, finite IDs overflow, generation ABA and actual Darwin profile"; ref :>> owner=guardOwner; }
part storage:Need { attribute :>> obligationId="SP-storage"; attribute :>> kind="source"; attribute :>> subjectPath="vendor/gambit/lib/memory/capacity-resize.inc"; attribute :>> subjectScope="backing storage and old participant/scan-domain retirement closure"; ref :>> owner=storageOwner; }
}
