package GambitFormatterRestoreReentry { private import ScalarValues::*;
part def SourceRow { attribute key:String; attribute path:String; attribute needle:String; attribute obligation:String; }
part source0:SourceRow { attribute :>> key="save"; attribute :>> path="vendor/gambit/gsc/_gscdebug.scm"; attribute :>> needle="(let ((save-wr ##wr))"; attribute :>> obligation="Save is invocation-local current formatter, not necessarily the debug closure"; }
part source1:SourceRow { attribute :>> key="install"; attribute :>> path="vendor/gambit/gsc/_gscdebug.scm"; attribute :>> needle="(##wr-set! ##default-wr)"; attribute :>> obligation="Global mutation before conversion and output"; }
part source2:SourceRow { attribute :>> key="inner-call"; attribute :>> path="vendor/gambit/gsc/_gscdebug.scm"; attribute :>> needle="(##wr we"; attribute :>> obligation="Inner operator is mutable global; exact resolution cut needs host evidence"; }
part source3:SourceRow { attribute :>> key="conversion"; attribute :>> path="vendor/gambit/gsc/_gscdebug.scm"; attribute :>> needle="(c#parse-tree->expression obj)"; attribute :>> obligation="Transform executes while default writer is installed"; }
part source4:SourceRow { attribute :>> key="restore"; attribute :>> path="vendor/gambit/gsc/_gscdebug.scm"; attribute :>> needle="(##wr-set! save-wr)"; attribute :>> obligation="Plain restoration can be skipped or replayed and overwrite newer registration"; }
part source5:SourceRow { attribute :>> key="scalar"; attribute :>> path="vendor/gambit/gsc/_gscdebug.scm"; attribute :>> needle="(##default-wr we"; attribute :>> obligation="Scalar branch never enters temporary global swap"; }
part source6:SourceRow { attribute :>> key="var-test"; attribute :>> path="vendor/gambit/gsc/_envadt.scm"; attribute :>> needle="(define (var? x)"; attribute :>> obligation="Special branch requires vector; selected scalar binding excluded"; }
part source7:SourceRow { attribute :>> key="ptree-test"; attribute :>> path="vendor/gambit/gsc/_ptreeadt.scm"; attribute :>> needle="(define (ptree? obj)"; attribute :>> obligation="Special branch requires vector"; }
part source8:SourceRow { attribute :>> key="tree-entry"; attribute :>> path="vendor/gambit/gsc/_ptree2.scm"; attribute :>> needle="(define (parse-tree->expression ptree . rest)"; attribute :>> obligation="Actual transform creates context and traverses parse tree"; }
part source9:SourceRow { attribute :>> key="tree-constant"; attribute :>> path="vendor/gambit/gsc/_ptree2.scm"; attribute :>> needle="(se-constant val ptree ctx)"; attribute :>> obligation="Constants can survive into output payload"; }
part source10:SourceRow { attribute :>> key="tree-eval"; attribute :>> path="vendor/gambit/gsc/_ptree2.scm"; attribute :>> needle="(list quote-sym (eval name))"; attribute :>> obligation="Procedure-object branch evaluates name; does not itself call the resulting procedure"; }
part source11:SourceRow { attribute :>> key="tree-error"; attribute :>> path="vendor/gambit/gsc/_ptree2.scm"; attribute :>> needle="(compiler-internal-error \"se, unknown parse tree node type\")"; attribute :>> obligation="Diagnostic escape exists for malformed/unhandled node; legal-source reachability not inferred"; }
part source12:SourceRow { attribute :>> key="expansion"; attribute :>> path="vendor/gambit/gsc/_front.scm"; attribute :>> needle="(pp-expression (parse-tree->expression ptree) port)"; attribute :>> obligation="Ordinary expansion printing converts before printing; not direct evidence debug swap branch is entered"; }
part source13:SourceRow { attribute :>> key="arg-order"; attribute :>> path="vendor/gambit/gsc/_front.scm"; attribute :>> needle="(define (arg-eval-order oper nodes)"; attribute :>> obligation="Host artifact operand order not determined merely by source indentation"; }
part source14:SourceRow { attribute :>> key="dynamic-before"; attribute :>> path="vendor/gambit/lib/_thread.scm"; attribute :>> needle="((macro-dynwind-before dst))"; attribute :>> obligation="Winding invokes Scheme before procedures; not a no-callback cleanup primitive"; }
part source15:SourceRow { attribute :>> key="dynamic-after"; attribute :>> path="vendor/gambit/lib/_thread.scm"; attribute :>> needle="((macro-dynwind-after src))"; attribute :>> obligation="Unwinding invokes Scheme after procedures; may reenter/fail"; }
part source16:SourceRow { attribute :>> key="dynamic-wind"; attribute :>> path="vendor/gambit/lib/_thread.scm"; attribute :>> needle="(define-prim (##dynamic-wind before thunk after)"; attribute :>> obligation="Runtime supports dynamic extent; debug formatter does not use it"; }
part source17:SourceRow { attribute :>> key="handler"; attribute :>> path="vendor/gambit/lib/_thread.scm"; attribute :>> needle="(define-prim (with-exception-handler handler thunk)"; attribute :>> obligation="Returning dynamic handler may continue old frame"; }
part source18:SourceRow { attribute :>> key="catcher"; attribute :>> path="vendor/gambit/lib/_thread.scm"; attribute :>> needle="(define-prim (##with-exception-catcher catcher thunk)"; attribute :>> obligation="Catcher grafts outer continuation"; }
part source19:SourceRow { attribute :>> key="compiler-catch"; attribute :>> path="vendor/gambit/gsc/_utils.scm"; attribute :>> needle="(set! throw-to-exception-handler cont)"; attribute :>> obligation="Compiler diagnostic channel is separate"; }
part source20:SourceRow { attribute :>> key="compiler-abort"; attribute :>> path="vendor/gambit/gsc/_utils.scm"; attribute :>> needle="(throw-to-exception-handler #f)"; attribute :>> obligation="Compiler diagnostic escape can skip pending ordinary cleanup"; }
part source21:SourceRow { attribute :>> key="setter"; attribute :>> path="vendor/gambit/lib/_io.scm"; attribute :>> needle="(set! ##wr x)"; attribute :>> obligation="Formatter registration has no generation check in this setter"; }
part source22:SourceRow { attribute :>> key="default"; attribute :>> path="vendor/gambit/lib/_io.scm"; attribute :>> needle="(define ##wr ##default-wr)"; attribute :>> obligation="Global default initializer is not a per-invocation resolver"; }
part source23:SourceRow { attribute :>> key="generic"; attribute :>> path="vendor/gambit/lib/_io.scm"; attribute :>> needle="(define-prim (##write-generic-to-character-port style port rt force? limit obj)"; attribute :>> obligation="Writer dispatch includes marking/output events"; }
part source24:SourceRow { attribute :>> key="device"; attribute :>> path="vendor/gambit/lib/_io.scm"; attribute :>> needle="(##wr we obj)"; attribute :>> obligation="Device writer uses current global formatter"; }
part source25:SourceRow { attribute :>> key="recursive"; attribute :>> path="vendor/gambit/lib/_io.scm"; attribute :>> needle="(define-prim (##wr-pair we obj)"; attribute :>> obligation="Default recursive writer footprint must migrate, not just one outer call"; }
part source26:SourceRow { attribute :>> key="io-error"; attribute :>> path="vendor/gambit/lib/_io.scm"; attribute :>> needle="(define-prim (##raise-io-exception port exc)"; attribute :>> obligation="I/O callback may return, escape, capture or publish with capability"; }
part source27:SourceRow { attribute :>> key="gc-job"; attribute :>> path="vendor/gambit/lib/_kernel.scm"; attribute :>> needle="(##execute-jobs! ##gc-interrupt-jobs)"; attribute :>> obligation="Conditional callback producer; exact interleaving still unqualified"; }
part source28:SourceRow { attribute :>> key="table-reset"; attribute :>> path="vendor/gambit/gsc/_t-c-1.scm"; attribute :>> needle="(set! targ-glo-vars         (make-table 'test: eq?))"; attribute :>> obligation="Nested compilation changes metadata entry identity"; }
part source29:SourceRow { attribute :>> key="demand"; attribute :>> path="vendor/gambit/gsc/_t-c-1.scm"; attribute :>> needle="(targ-rsrc-demanders-set! (cdr x) '(\"\"))"; attribute :>> obligation="Canonical same-entry writer"; }
part source30:SourceRow { attribute :>> key="supply"; attribute :>> path="vendor/gambit/gsc/_t-c-1.scm"; attribute :>> needle="(targ-rsrc-suppliers-set! (cdr x) '(\"\"))"; attribute :>> obligation="Demand-preserving writer"; }
part source31:SourceRow { attribute :>> key="raw"; attribute :>> path="vendor/gambit/gsc/_t-c-1.scm"; attribute :>> needle="(vector-set! r 1 demanders)"; attribute :>> obligation="Raw writer can invalidate canonicality"; }
part source32:SourceRow { attribute :>> key="glo"; attribute :>> path="vendor/gambit/gsc/_t-c-1.scm"; attribute :>> needle="(def-mod-prm-glo \"DEF_MOD_GLO\")"; attribute :>> obligation="Second normalization remains required absent qualification"; }
part source33:SourceRow { attribute :>> key="igsc"; attribute :>> path="vendor/gambit/gsc/igsc.scm"; attribute :>> needle="\"_gscdebug\""; attribute :>> obligation="Actual interactive compiler formatter registration path"; }
part def WindowRow { attribute key:String; attribute cause:String; attribute effect:String; attribute reachability:String; attribute gap:String; }
part window0:WindowRow { attribute :>> key="escape"; attribute :>> cause="Nonlocal exit after default installation"; attribute :>> effect="Restoration statement not reached"; attribute :>> reachability="Conditional on special branch and actual escaping producer"; attribute :>> gap="Not demonstrated in selected scalar primitive emission"; }
part window1:WindowRow { attribute :>> key="replay"; attribute :>> cause="Capture inside conversion/write and multiple resume"; attribute :>> effect="Old lexical save may overwrite new writer repeatedly"; attribute :>> reachability="Source-composable once real capture is established"; attribute :>> gap="Exact legal payload/callback and native PC mapping OPEN"; }
part window2:WindowRow { attribute :>> key="late-entry"; attribute :>> cause="Old formatter closure dispatched after global replacement"; attribute :>> effect="Entry saves current writer; may restore newer writer correctly"; attribute :>> reachability="Requires retained callable and writeenv/port lifetime"; attribute :>> gap="Do not equate callable identity with current registration"; }
part window3:WindowRow { attribute :>> key="operator"; attribute :>> cause="Conversion/async registration between operand evaluations"; attribute :>> effect="Inner callable can differ depending on resolution cut"; attribute :>> reachability="Both schedules modeled as alternatives"; attribute :>> gap="Actual selected compiler/host evaluation order OPEN"; }
part window4:WindowRow { attribute :>> key="aba"; attribute :>> cause="Restore old function object after intervening changes"; attribute :>> effect="Object equality hides registration history"; attribute :>> reachability="Plain setter permits value reuse"; attribute :>> gap="Certificate needs generation, closure effects and producer drain"; }
part def ClaimRow { attribute key:String; attribute mechanism:String; attribute condition:String; attribute result:String; attribute gap:String; }
part claim0:ClaimRow { attribute :>> key="owned-restore"; attribute :>> mechanism="Compare ownership and generation at restore"; attribute :>> condition="Serialized registration and restoration; fresh operation token"; attribute :>> result="Do not clobber a newer registration"; attribute :>> gap="C23 instruction-level handoff and Scheme nonlocal exit integration OPEN"; }
part claim1:ClaimRow { attribute :>> key="scoped-resolver"; attribute :>> mechanism="Immutable per-invocation writer policy"; attribute :>> condition="Every recursive dispatch and denv/writeenv path migrated"; attribute :>> result="No global restoration obligation for that resolver"; attribute :>> gap="Defined semantic repair; not automatic equivalence to global mutation"; }
part claim2:ClaimRow { attribute :>> key="continuation"; attribute :>> mechanism="Separate continuation execution from reuse authority"; attribute :>> condition="Each activation/root remains owned; new operation identity on reexecution"; attribute :>> result="Reject stale permit, retain Scheme continuation capability"; attribute :>> gap="Full multi-shot/output/root refinement OPEN"; }
part claim3:ClaimRow { attribute :>> key="second"; attribute :>> mechanism="Canonical same-entry writer closure plus current formatter policy"; attribute :>> condition="Drained accepted callbacks/captures and equivalent faults/events"; attribute :>> result="Second value normalization may retire"; attribute :>> gap="Object restoration alone is insufficient"; }
part def GainRow { attribute key:String; attribute avoided:String; attribute added:String; attribute condition:String; }
part gain0:GainRow { attribute :>> key="local-view"; attribute :>> avoided="Two temporary global writes per special invocation; cross-session invalidation due solely to it"; attribute :>> added="Owned resolver/view; migrate 20 direct recursive writer applications and continuation roots"; attribute :>> condition="All writer sites use context; diagnostic/registration semantics explicitly defined"; }
part gain1:GainRow { attribute :>> key="second"; attribute :>> avoided="At most one second helper normalization per qualified emission; p*N over N emissions"; attribute :>> added="Capability generation, callback accounting and byte/fault verification"; attribute :>> condition="Canonicality, same entry, valid policy and no unresolved borrowers"; }
part gain2:GainRow { attribute :>> key="guard-only"; attribute :>> avoided="Prevents stale unconditional restoration from clobbering newer registration"; attribute :>> added="Owner tokens, conflict settlement and possible redispatch"; attribute :>> condition="Semantic repair for conflicting registration; not exact legacy behavior"; }
part gain3:GainRow { attribute :>> key="shared"; attribute :>> avoided="Reusable immutable stage/profile result across compiler consumers"; attribute :>> added="Profile invalidation, independent contexts and root lifetime"; attribute :>> condition="Do not add a lock wrapper around the same global bottleneck"; }
part gain4:GainRow { attribute :>> key="net"; attribute :>> avoided="Duplicate work D plus removed redundant effects W"; attribute :>> added="Resolver K + owner/root S + callback audit H + validation V"; attribute :>> condition="Runtime subset positive only if p*N*Cn > Cq+W*Cv; architecture ledger D+W>K+S+H+V; no measured timing or macro-expansion gain"; }
part def ContractRow { attribute fromNode:String; attribute toNode:String; attribute custody:String; }
part contract0:ContractRow { attribute :>> fromNode="Debug special entry"; attribute :>> toNode="Saved writer"; attribute :>> custody="current identity"; }
part contract1:ContractRow { attribute :>> fromNode="Saved writer"; attribute :>> toNode="Install default"; attribute :>> custody="global swap"; }
part contract2:ContractRow { attribute :>> fromNode="Install default"; attribute :>> toNode="Conversion and write"; attribute :>> custody="callback window"; }
part contract3:ContractRow { attribute :>> fromNode="Conversion and write"; attribute :>> toNode="Legacy restore"; attribute :>> custody="plain statement"; }
part contract4:ContractRow { attribute :>> fromNode="Captured continuation"; attribute :>> toNode="Legacy restore"; attribute :>> custody="old save replay"; }
part contract5:ContractRow { attribute :>> fromNode="New registration"; attribute :>> toNode="Legacy restore"; attribute :>> custody="overwrite risk"; }
part contract6:ContractRow { attribute :>> fromNode="Install default"; attribute :>> toNode="Owned scope"; attribute :>> custody="generation lease"; }
part contract7:ContractRow { attribute :>> fromNode="Owned scope"; attribute :>> toNode="Conflict settlement"; attribute :>> custody="preserve newer"; }
part contract8:ContractRow { attribute :>> fromNode="Accepted dispatch"; attribute :>> toNode="Drain barrier"; attribute :>> custody="late borrower"; }
part contract9:ContractRow { attribute :>> fromNode="Capture roots"; attribute :>> toNode="Drain barrier"; attribute :>> custody="multi-shot debt"; }
part contract10:ContractRow { attribute :>> fromNode="Drain barrier"; attribute :>> toNode="Capability receipt"; attribute :>> custody="all producers closed"; }
part contract11:ContractRow { attribute :>> fromNode="Capability receipt"; attribute :>> toNode="Second cut"; attribute :>> custody="current policy"; }
part contract12:ContractRow { attribute :>> fromNode="Scoped writer view"; attribute :>> toNode="Recursive dispatch"; attribute :>> custody="explicit resolver"; }
part def BindingRow { attribute actionName:String; attribute lemma:String; attribute scope:String; }
part binding0:BindingRow { attribute :>> actionName="formatter_restore_reentry.beginScope"; attribute :>> lemma="FormatterRestore.beginScopePreserves"; attribute :>> scope="Alternative legacy/managed worlds; conditional atomic transitions, source fidelity external"; }
part binding1:BindingRow { attribute :>> actionName="formatter_restore_reentry.bodyReturns"; attribute :>> lemma="FormatterRestore.bodyReturnsPreserves"; attribute :>> scope="Alternative legacy/managed worlds; conditional atomic transitions, source fidelity external"; }
part binding2:BindingRow { attribute :>> actionName="formatter_restore_reentry.restoreOwned"; attribute :>> lemma="FormatterRestore.restoreOwnedPreserves"; attribute :>> scope="Alternative legacy/managed worlds; conditional atomic transitions, source fidelity external"; }
part binding3:BindingRow { attribute :>> actionName="formatter_restore_reentry.escapeOwned"; attribute :>> lemma="FormatterRestore.escapeOwnedPreserves"; attribute :>> scope="Alternative legacy/managed worlds; conditional atomic transitions, source fidelity external"; }
part binding4:BindingRow { attribute :>> actionName="formatter_restore_reentry.publishOther"; attribute :>> lemma="FormatterRestore.publishOtherPreserves"; attribute :>> scope="Alternative legacy/managed worlds; conditional atomic transitions, source fidelity external"; }
part binding5:BindingRow { attribute :>> actionName="formatter_restore_reentry.publishSameIdentity"; attribute :>> lemma="FormatterRestore.publishSameIdentityPreserves"; attribute :>> scope="Alternative legacy/managed worlds; conditional atomic transitions, source fidelity external"; }
part binding6:BindingRow { attribute :>> actionName="formatter_restore_reentry.yieldConflict"; attribute :>> lemma="FormatterRestore.yieldConflictPreserves"; attribute :>> scope="Alternative legacy/managed worlds; conditional atomic transitions, source fidelity external"; }
part binding7:BindingRow { attribute :>> actionName="formatter_restore_reentry.changeEpoch"; attribute :>> lemma="FormatterRestore.changeEpochPreserves"; attribute :>> scope="Alternative legacy/managed worlds; conditional atomic transitions, source fidelity external"; }
part binding8:BindingRow { attribute :>> actionName="formatter_restore_reentry.acceptTicket"; attribute :>> lemma="FormatterRestore.acceptTicketPreserves"; attribute :>> scope="Alternative legacy/managed worlds; conditional atomic transitions, source fidelity external"; }
part binding9:BindingRow { attribute :>> actionName="formatter_restore_reentry.startTicket"; attribute :>> lemma="FormatterRestore.startTicketPreserves"; attribute :>> scope="Alternative legacy/managed worlds; conditional atomic transitions, source fidelity external"; }
part binding10:BindingRow { attribute :>> actionName="formatter_restore_reentry.finishBorrower"; attribute :>> lemma="FormatterRestore.finishBorrowerPreserves"; attribute :>> scope="Alternative legacy/managed worlds; conditional atomic transitions, source fidelity external"; }
part binding11:BindingRow { attribute :>> actionName="formatter_restore_reentry.capture"; attribute :>> lemma="FormatterRestore.capturePreserves"; attribute :>> scope="Alternative legacy/managed worlds; conditional atomic transitions, source fidelity external"; }
part binding12:BindingRow { attribute :>> actionName="formatter_restore_reentry.rejectStalePermit"; attribute :>> lemma="FormatterRestore.rejectStalePermitPreserves"; attribute :>> scope="Alternative legacy/managed worlds; conditional atomic transitions, source fidelity external"; }
part binding13:BindingRow { attribute :>> actionName="formatter_restore_reentry.detachCapture"; attribute :>> lemma="FormatterRestore.detachCapturePreserves"; attribute :>> scope="Alternative legacy/managed worlds; conditional atomic transitions, source fidelity external"; }
part binding14:BindingRow { attribute :>> actionName="formatter_restore_reentry.closeRegistration"; attribute :>> lemma="FormatterRestore.closeRegistrationPreserves"; attribute :>> scope="Alternative legacy/managed worlds; conditional atomic transitions, source fidelity external"; }
part binding15:BindingRow { attribute :>> actionName="formatter_restore_reentry.namedDemand"; attribute :>> lemma="FormatterRestore.namedDemandPreserves"; attribute :>> scope="Alternative legacy/managed worlds; conditional atomic transitions, source fidelity external"; }
part binding16:BindingRow { attribute :>> actionName="formatter_restore_reentry.namedSupply"; attribute :>> lemma="FormatterRestore.namedSupplyPreserves"; attribute :>> scope="Alternative legacy/managed worlds; conditional atomic transitions, source fidelity external"; }
part binding17:BindingRow { attribute :>> actionName="formatter_restore_reentry.rawMetadata"; attribute :>> lemma="FormatterRestore.rawMetadataPreserves"; attribute :>> scope="Alternative legacy/managed worlds; conditional atomic transitions, source fidelity external"; }
part binding18:BindingRow { attribute :>> actionName="formatter_restore_reentry.ioFailure"; attribute :>> lemma="FormatterRestore.ioFailurePreserves"; attribute :>> scope="Alternative legacy/managed worlds; conditional atomic transitions, source fidelity external"; }
part binding19:BindingRow { attribute :>> actionName="formatter_restore_reentry.qualifyProfile"; attribute :>> lemma="FormatterRestore.qualifyProfilePreserves"; attribute :>> scope="Alternative legacy/managed worlds; conditional atomic transitions, source fidelity external"; }
part binding20:BindingRow { attribute :>> actionName="formatter_restore_reentry.issue"; attribute :>> lemma="FormatterRestore.issuePreserves"; attribute :>> scope="Alternative legacy/managed worlds; conditional atomic transitions, source fidelity external"; }
part binding21:BindingRow { attribute :>> actionName="formatter_restore_reentry.consumeSecond"; attribute :>> lemma="FormatterRestore.consumeSecondPreserves"; attribute :>> scope="Alternative legacy/managed worlds; conditional atomic transitions, source fidelity external"; }
part binding22:BindingRow { attribute :>> actionName="formatter_restore_reentry.legacyEnter"; attribute :>> lemma="FormatterRestore.legacyEnterPreserves"; attribute :>> scope="Alternative legacy/managed worlds; conditional atomic transitions, source fidelity external"; }
part binding23:BindingRow { attribute :>> actionName="formatter_restore_reentry.legacyCapture"; attribute :>> lemma="FormatterRestore.legacyCapturePreserves"; attribute :>> scope="Alternative legacy/managed worlds; conditional atomic transitions, source fidelity external"; }
part binding24:BindingRow { attribute :>> actionName="formatter_restore_reentry.legacyEscape"; attribute :>> lemma="FormatterRestore.legacyEscapePreserves"; attribute :>> scope="Alternative legacy/managed worlds; conditional atomic transitions, source fidelity external"; }
part binding25:BindingRow { attribute :>> actionName="formatter_restore_reentry.legacyPublish"; attribute :>> lemma="FormatterRestore.legacyPublishPreserves"; attribute :>> scope="Alternative legacy/managed worlds; conditional atomic transitions, source fidelity external"; }
part binding26:BindingRow { attribute :>> actionName="formatter_restore_reentry.legacyResolve"; attribute :>> lemma="FormatterRestore.legacyResolvePreserves"; attribute :>> scope="Alternative legacy/managed worlds; conditional atomic transitions, source fidelity external"; }
part binding27:BindingRow { attribute :>> actionName="formatter_restore_reentry.legacyReturn"; attribute :>> lemma="FormatterRestore.legacyReturnPreserves"; attribute :>> scope="Alternative legacy/managed worlds; conditional atomic transitions, source fidelity external"; }
part binding28:BindingRow { attribute :>> actionName="formatter_restore_reentry.legacyRestore"; attribute :>> lemma="FormatterRestore.legacyRestorePreserves"; attribute :>> scope="Alternative legacy/managed worlds; conditional atomic transitions, source fidelity external"; }
part binding29:BindingRow { attribute :>> actionName="formatter_restore_reentry.legacyResume"; attribute :>> lemma="FormatterRestore.legacyResumePreserves"; attribute :>> scope="Alternative legacy/managed worlds; conditional atomic transitions, source fidelity external"; }
part binding30:BindingRow { attribute :>> actionName="formatter_restore_reentry.legacyLateEntry"; attribute :>> lemma="FormatterRestore.legacyLateEntryPreserves"; attribute :>> scope="Alternative legacy/managed worlds; conditional atomic transitions, source fidelity external"; }
part def ProofRow { attribute key:String; attribute lemma:String; }
part proof0:ProofRow { attribute :>> key="steps"; attribute :>> lemma="FormatterRestore.stepPreserves"; }
part proof1:ProofRow { attribute :>> key="reachable"; attribute :>> lemma="FormatterRestore.reachableSafe"; }
part proof2:ProofRow { attribute :>> key="drain"; attribute :>> lemma="FormatterRestore.permitNeedsDrain"; }
part proof3:ProofRow { attribute :>> key="generation"; attribute :>> lemma="FormatterRestore.permitNeedsGeneration"; }
part proof4:ProofRow { attribute :>> key="capture"; attribute :>> lemma="FormatterRestore.rejectedResumeKeepsCapture"; }
part proof5:ProofRow { attribute :>> key="aba"; attribute :>> lemma="FormatterRestoreAlgebra.sameObjectNotSameKey"; }
part proof6:ProofRow { attribute :>> key="overwrite"; attribute :>> lemma="FormatterRestoreAlgebra.unconditionalRestoreOverwritesNewer"; }
part proof7:ProofRow { attribute :>> key="conflict"; attribute :>> lemma="FormatterRestoreAlgebra.conflictPreservesCurrent"; }
part proof8:ProofRow { attribute :>> key="scoped"; attribute :>> lemma="FormatterRestoreAlgebra.scopedResolverIndependent"; }
part proof9:ProofRow { attribute :>> key="canonical"; attribute :>> lemma="FormatterRestoreAlgebra.secondUnderNamedWriters"; }
part def MigrationRow { attribute key:String; attribute producerAnchor:String; attribute consumerAnchor:String; attribute actionName:String; attribute lemma:String; }
part migration0:MigrationRow { attribute :>> key="plain-swap"; attribute :>> producerAnchor="save"; attribute :>> consumerAnchor="install"; attribute :>> actionName="formatter_restore_reentry.legacyEnter"; attribute :>> lemma="FormatterRestore.legacyEnterPreserves"; }
part migration1:MigrationRow { attribute :>> key="old-resume"; attribute :>> producerAnchor="restore"; attribute :>> consumerAnchor="conversion"; attribute :>> actionName="formatter_restore_reentry.legacyResume"; attribute :>> lemma="FormatterRestore.legacyResumePreserves"; }
part migration2:MigrationRow { attribute :>> key="late-identity"; attribute :>> producerAnchor="setter"; attribute :>> consumerAnchor="save"; attribute :>> actionName="formatter_restore_reentry.legacyLateEntry"; attribute :>> lemma="FormatterRestore.legacyLateEntryPreserves"; }
part migration3:MigrationRow { attribute :>> key="owned-restore"; attribute :>> producerAnchor="setter"; attribute :>> consumerAnchor="restore"; attribute :>> actionName="formatter_restore_reentry.restoreOwned"; attribute :>> lemma="FormatterRestoreAlgebra.conflictPreservesCurrent"; }
part migration4:MigrationRow { attribute :>> key="scoped-dispatch"; attribute :>> producerAnchor="default"; attribute :>> consumerAnchor="recursive"; attribute :>> actionName="formatter_restore_reentry.qualifyProfile"; attribute :>> lemma="FormatterRestoreAlgebra.scopedResolverIndependent"; }
part migration5:MigrationRow { attribute :>> key="canonical"; attribute :>> producerAnchor="demand"; attribute :>> consumerAnchor="glo"; attribute :>> actionName="formatter_restore_reentry.consumeSecond"; attribute :>> lemma="FormatterRestoreAlgebra.secondUnderNamedWriters"; }
part migration6:MigrationRow { attribute :>> key="capture-debt"; attribute :>> producerAnchor="catcher"; attribute :>> consumerAnchor="restore"; attribute :>> actionName="formatter_restore_reentry.rejectStalePermit"; attribute :>> lemma="FormatterRestore.rejectedResumeKeepsCapture"; }
part def InventoryRow { attribute key:String; attribute path:String; attribute pattern:String; attribute count:String; attribute scope:String; }
part inventory0:InventoryRow { attribute :>> key="recursive-writer"; attribute :>> path="vendor/gambit/lib/_io.scm"; attribute :>> pattern="\\(##wr\\s"; attribute :>> count="20"; attribute :>> scope="Exact lexical occurrence count; zero does not close indirect runtime effects"; }
part inventory1:InventoryRow { attribute :>> key="debug-setters"; attribute :>> path="vendor/gambit/gsc/_gscdebug.scm"; attribute :>> pattern="\\(##wr-set!\\s"; attribute :>> count="3"; attribute :>> scope="Exact lexical occurrence count; zero does not close indirect runtime effects"; }
part inventory2:InventoryRow { attribute :>> key="debug-capture"; attribute :>> path="vendor/gambit/gsc/_gscdebug.scm"; attribute :>> pattern="\\(call-with-current-continuation|\\(##continuation-capture|\\(dynamic-wind"; attribute :>> count="0"; attribute :>> scope="Exact lexical occurrence count; zero does not close indirect runtime effects"; }
part inventory3:InventoryRow { attribute :>> key="resource-reader"; attribute :>> path="vendor/gambit/gsc/_gscdebug.scm"; attribute :>> pattern="targ-glo-vars|targ-rsrc-|targ-use-glo"; attribute :>> count="0"; attribute :>> scope="Exact lexical occurrence count; zero does not close indirect runtime effects"; }
part def PolicyRow { attribute key:String; attribute writerClass:String; attribute assumptions:String; attribute firstExpected:String; attribute secondExpected:String; attribute scope:String; }
part policy0:PolicyRow { attribute :>> key="current-no-qualified-closure"; attribute :>> writerClass="named-only"; attribute :>> assumptions=""; attribute :>> firstExpected="false"; attribute :>> secondExpected="false"; attribute :>> scope="Sufficient assumptions only; not native or source qualification"; }
part policy1:PolicyRow { attribute :>> key="synthetic-qualified"; attribute :>> writerClass="named-only"; attribute :>> assumptions="first-retained;same-entry;canonical-writers;formatter-profile-current;restore-settled;registration-closed;borrowers-drained;captures-retired;fault-equivalence"; attribute :>> firstExpected="false"; attribute :>> secondExpected="true"; attribute :>> scope="Sufficient assumptions only; not native or source qualification"; }
part policy2:PolicyRow { attribute :>> key="synthetic-old-generation"; attribute :>> writerClass="named-only"; attribute :>> assumptions="first-retained;same-entry;canonical-writers;restore-settled;registration-closed;borrowers-drained;captures-retired;fault-equivalence"; attribute :>> firstExpected="false"; attribute :>> secondExpected="false"; attribute :>> scope="Sufficient assumptions only; not native or source qualification"; }
part policy3:PolicyRow { attribute :>> key="synthetic-late-callback"; attribute :>> writerClass="named-only"; attribute :>> assumptions="first-retained;same-entry;canonical-writers;formatter-profile-current;restore-settled;registration-closed;captures-retired;fault-equivalence"; attribute :>> firstExpected="false"; attribute :>> secondExpected="false"; attribute :>> scope="Sufficient assumptions only; not native or source qualification"; }
part policy4:PolicyRow { attribute :>> key="synthetic-live-capture"; attribute :>> writerClass="named-only"; attribute :>> assumptions="first-retained;same-entry;canonical-writers;formatter-profile-current;restore-settled;registration-closed;borrowers-drained;fault-equivalence"; attribute :>> firstExpected="false"; attribute :>> secondExpected="false"; attribute :>> scope="Sufficient assumptions only; not native or source qualification"; }
part policy5:PolicyRow { attribute :>> key="synthetic-raw-writer"; attribute :>> writerClass="named-only"; attribute :>> assumptions="first-retained;same-entry;formatter-profile-current;restore-settled;registration-closed;borrowers-drained;captures-retired;fault-equivalence"; attribute :>> firstExpected="false"; attribute :>> secondExpected="false"; attribute :>> scope="Sufficient assumptions only; not native or source qualification"; }
part policy6:PolicyRow { attribute :>> key="synthetic-exit-fault"; attribute :>> writerClass="named-only"; attribute :>> assumptions="first-retained;same-entry;canonical-writers;formatter-profile-current;restore-settled;registration-closed;borrowers-drained;captures-retired"; attribute :>> firstExpected="false"; attribute :>> secondExpected="false"; attribute :>> scope="Sufficient assumptions only; not native or source qualification"; }
part history:GambitAssuranceRouting::ModelNeed { ref part :>> owner=GambitAssuranceRelations::modelUse2; attribute :>> obligationId="FR-history"; attribute :>> kind="interleaving"; attribute :>> subjectPath="dev/refactoring/modern-c/models/quint/formatter_restore_reentry.qnt"; attribute :>> subjectScope="20 histories; alternative legacy restore/replay and managed admission, not one physical execution"; attribute :>> premise="C23 design only; no runtime implementation or native tests"; }
part induction:GambitAssuranceRouting::ModelNeed { ref part :>> owner=GambitAssuranceRelations::modelUse2; attribute :>> obligationId="FR-induction"; attribute :>> kind="induction"; attribute :>> subjectPath="dev/refactoring/modern-c/models/lean/FormatterRestore.lean"; attribute :>> subjectScope="All projected steps preserve conditional custody and permit invariant"; attribute :>> premise="C23 design only; no runtime implementation or native tests"; }
part algebra:GambitAssuranceRouting::ModelNeed { ref part :>> owner=GambitAssuranceRelations::modelUse2; attribute :>> obligationId="FR-algebra"; attribute :>> kind="induction"; attribute :>> subjectPath="dev/refactoring/modern-c/models/lean/FormatterRestoreAlgebra.lean"; attribute :>> subjectScope="Generation key distinction, conflict preservation, scoped value resolver and named writer closure"; attribute :>> premise="C23 design only; no runtime implementation or native tests"; }
part projection:GambitAssuranceRouting::ModelNeed { ref part :>> owner=GambitAssuranceRelations::modelUse2; attribute :>> obligationId="FR-projection"; attribute :>> kind="restricted-projection"; attribute :>> subjectPath="dev/refactoring/modern-c/models/lean/FormatterRestoreAst.lean"; attribute :>> subjectScope="Actual typed IR binding/field/expression/roster checks; extractor trusted"; attribute :>> premise="C23 design only; no runtime implementation or native tests"; }
part source:GambitAssuranceRouting::ModelNeed { ref part :>> owner=GambitAssuranceRelations::modelUse2; attribute :>> obligationId="FR-source"; attribute :>> kind="source-refinement"; attribute :>> subjectPath="dev/refactoring/modern-c/formatter-restore-reentry-design.org"; attribute :>> subjectScope="Special-branch legal caller and capture, actual operator order, complete registration and root closure OPEN"; attribute :>> premise="C23 design only; no runtime implementation or native tests"; }
part exceptions:GambitAssuranceRouting::ModelNeed { ref part :>> owner=GambitAssuranceRelations::modelUse2; attribute :>> obligationId="FR-exceptions"; attribute :>> kind="exception-equivalence"; attribute :>> subjectPath="dev/refactoring/modern-c/formatter-restore-reentry-design.org"; attribute :>> subjectScope="Fault prefixes, unwinding/reentry and multi-shot invocation equivalence OPEN"; attribute :>> premise="C23 design only; no runtime implementation or native tests"; }
part platform:GambitAssuranceRouting::ModelNeed { ref part :>> owner=GambitAssuranceRelations::modelUse2; attribute :>> obligationId="FR-platform"; attribute :>> kind="c23-platform-qualification"; attribute :>> subjectPath="dev/refactoring/modern-c/language-baseline-design.org"; attribute :>> subjectScope="Owner handoff, global slot visibility, root lifetime and target ABI qualification OPEN"; attribute :>> premise="C23 design only; no runtime implementation or native tests"; }
part emission:GambitAssuranceRouting::ModelNeed { ref part :>> owner=GambitAssuranceRelations::modelUse2; attribute :>> obligationId="FR-emission"; attribute :>> kind="emitter-fidelity"; attribute :>> subjectPath="dev/refactoring/modern-c/formatter-restore-reentry-design.org"; attribute :>> subjectScope="Complete recursive writer-context migration and output event/source refinement OPEN"; attribute :>> premise="C23 design only; no runtime implementation or native tests"; }
}
