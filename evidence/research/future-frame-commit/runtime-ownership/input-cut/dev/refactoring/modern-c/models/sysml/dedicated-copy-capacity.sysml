package GambitDedicatedCopyCapacity { private import ScalarValues::*;
part def SourceRow { attribute key:String; attribute path:String; attribute needle:String; attribute obligation:String; }
part source0:SourceRow { attribute :>> key="census"; attribute :>> path="vendor/gambit/lib/mem.c"; attribute :>> needle="#define words_movable_objs(ps)"; attribute :>> obligation="Factor two logical accounting is not raw unique source extent"; }
part source1:SourceRow { attribute :>> key="frozen"; attribute :>> path="vendor/gambit/lib/mem.c"; attribute :>> needle="alloc_stack_ptr = ___ps->context->fp;"; attribute :>> obligation="GC materializes allocation coordinates before frozen cut"; }
part source2:SourceRow { attribute :>> key="source-epoch"; attribute :>> path="vendor/gambit/lib/mem.c"; attribute :>> needle="___vms->gc_round.source_sections = the_msections->nb_sections;"; attribute :>> obligation="Proposed old source epoch must exclude newly reserved empty sections"; }
part source3:SourceRow { attribute :>> key="full-size"; attribute :>> path="vendor/gambit/lib/mem.c"; attribute :>> needle="#define compute_msection_size(nb_sections)"; attribute :>> obligation="Full physical section count is not usable tospace capacity"; }
part source4:SourceRow { attribute :>> key="usable"; attribute :>> path="vendor/gambit/lib/mem.c"; attribute :>> needle="#define compute_msection_space(nb_sections)"; attribute :>> obligation="Post-GC doubled accounting does not replace contiguous request fit"; }
part source5:SourceRow { attribute :>> key="reserve-cap"; attribute :>> path="vendor/gambit/lib/mem.c"; attribute :>> needle="required > (___MSECTION_SIZE>>1)-3"; attribute :>> obligation="Existing largest supported contiguous grant can make fragmentation bound degenerate"; }
part source6:SourceRow { attribute :>> key="reserve-loop"; attribute :>> path="vendor/gambit/lib/mem.c"; attribute :>> needle="work->context->mem.alloc_heap_limit_-alloc < required"; attribute :>> obligation="No-fit moves worker to next section before granting"; }
part source7:SourceRow { attribute :>> key="markers"; attribute :>> path="vendor/gambit/lib/mem.c"; attribute :>> needle="work->context->mem.alloc_heap_limit_ -= 2;"; attribute :>> obligation="Two terminal marker positions plus first link excluded from C"; }
part source8:SourceRow { attribute :>> key="first-link"; attribute :>> path="vendor/gambit/lib/mem.c"; attribute :>> needle="*work->context->mem.alloc_heap_ptr_++ = NULL_CHUNK_LINK;"; attribute :>> obligation="Initial link and threshold/empty terminal markers must be distinguished"; }
part source9:SourceRow { attribute :>> key="chunk-threshold"; attribute :>> path="vendor/gambit/lib/mem.c"; attribute :>> needle="if (alloc >= alloc_heap_chunk_limit)"; attribute :>> obligation="Ordinary and captured copies can close threshold chunks"; }
part source10:SourceRow { attribute :>> key="chunk-start"; attribute :>> path="vendor/gambit/lib/mem.c"; attribute :>> needle="alloc_heap_chunk_limit = work->context->mem.alloc_heap_ptr_ + ___MSECTION_CHUNK;"; attribute :>> obligation="Threshold marker charging depends on private committed span"; }
part source11:SourceRow { attribute :>> key="unique-object"; attribute :>> path="vendor/gambit/lib/mem.c"; attribute :>> needle="___COMPARE_AND_SWAP_WORD(&body[-1],"; attribute :>> obligation="Winning ordinary forwarding unique only under validated source identity"; }
part source12:SourceRow { attribute :>> key="cancel"; attribute :>> path="vendor/gambit/lib/mem.c"; attribute :>> needle="alloc = cancel_copy(work,&grant);"; attribute :>> obligation="Loser rewinds private grant; does not refund consumed earlier sections"; }
part source13:SourceRow { attribute :>> key="align"; attribute :>> path="vendor/gambit/lib/mem.c"; attribute :>> needle="if (align8) required++;"; attribute :>> obligation="32-bit alignment adds at most one reservation word"; }
part source14:SourceRow { attribute :>> key="frame-size"; attribute :>> path="vendor/gambit/lib/mem.c"; attribute :>> needle="words = fs + ___FRAME_EXTRA_SLOTS;"; attribute :>> obligation="Captured frame footprint differs from rounded source stack space"; }
part source15:SourceRow { attribute :>> key="frame-serial"; attribute :>> path="vendor/gambit/lib/mem.c"; attribute :>> needle="while (___COMPARE_AND_SWAP_WORD(&vms->gc_round.frame_gate,0,1) != 0)"; attribute :>> obligation="Frame uniqueness relies on access gate and forwarding slots"; }
part source16:SourceRow { attribute :>> key="frame-abi"; attribute :>> path="vendor/gambit/include/gambit.h.in"; attribute :>> needle="#define ___RETI_CFS_TO_FS(fs)"; attribute :>> obligation="RETI effective frame may exceed nominal descriptor size"; }
part source17:SourceRow { attribute :>> key="compiler-limit"; attribute :>> path="vendor/gambit/gsc/_t-c-1.scm"; attribute :>> needle="(define targ-max-nb-frame-slots  4096)"; attribute :>> obligation="Declaration with use-these-constants note is not full producer enforcement proof"; }
part source18:SourceRow { attribute :>> key="runtime-limit"; attribute :>> path="vendor/gambit/lib/mem.h"; attribute :>> needle="#define ___MAX_NB_FRAME_SLOTS   8192"; attribute :>> obligation="Runtime fudge macro alone is not a global maximum grant receipt"; }
part source19:SourceRow { attribute :>> key="late-grow"; attribute :>> path="vendor/gambit/lib/mem.c"; attribute :>> needle="determine_occupied_words (___vms);"; attribute :>> obligation="Live census for resize runs after tracing and continuation restore"; }
part source20:SourceRow { attribute :>> key="partial"; attribute :>> path="vendor/gambit/lib/mem.c"; attribute :>> needle="ms->nb_sections = ++ns;"; attribute :>> obligation="Only actual appended sections may be credited"; }
part source21:SourceRow { attribute :>> key="replace"; attribute :>> path="vendor/gambit/lib/mem.c"; attribute :>> needle="free_mem_aligned (ms);"; attribute :>> obligation="In-place growth can replace metadata before complete success"; }
part source22:SourceRow { attribute :>> key="reserve-rollback"; attribute :>> path="vendor/gambit/lib/mem.c"; attribute :>> needle="adjust_msections (&m->the_msections_, r->base_capacity);"; attribute :>> obligation="VM-resize partial rollback precedent requires isolated grant and no users"; }
part source23:SourceRow { attribute :>> key="unknown-join"; attribute :>> path="vendor/gambit/lib/mem.c"; attribute :>> needle="quarantined contexts, their roots, or their physical grant."; attribute :>> obligation="Unknown join is not proof of dead ownership"; }
part source24:SourceRow { attribute :>> key="post-fudge"; attribute :>> path="vendor/gambit/lib/mem.c"; attribute :>> needle="lower_bound_nb_sections += compute_resume_msections(normal_overflow_reserve);"; attribute :>> obligation="Separate post-copy and resumption reserve from heap packing"; }
part source25:SourceRow { attribute :>> key="origin"; attribute :>> path="vendor/gambit/lib/mem.c"; attribute :>> needle="GC copy source is not in frozen fromspace"; attribute :>> obligation="Existing check rejects tospace origin, not full canonical source partition"; }
part def ClaimRow { attribute key:String; attribute mechanism:String; attribute condition:String; attribute result:String; attribute gap:String; }
part claim0:ClaimRow { attribute :>> key="source"; attribute :>> mechanism="Validated union of old heap objects and old stack-frame footprints"; attribute :>> condition="Canonical disjoint source charges; old epoch immutable; strong and weak budgets combined"; attribute :>> result="64-bit U<=Q; 32-bit U<=Q+A<=2Q"; attribute :>> gap="Counter arithmetic and header-origin lookup do not establish source partition"; }
part claim1:ClaimRow { attribute :>> key="packing"; attribute :>> mechanism="C=H-3; maximum grant G<=C; threshold charge T"; attribute :>> condition="Every no-fit closed section has distinct charge at least d=C-G+1"; attribute :>> result="If B=U+T and B<(K-P+1)d, K heap sections suffice"; attribute :>> gap="Source injection, all writers and threshold charging still need refinement"; }
part claim2:ClaimRow { attribute :>> key="dedicated"; attribute :>> mechanism="Reserve P stack sections separately"; attribute :>> condition="R+J fits each dedicated section and all intervals disjoint"; attribute :>> result="Physical target N>=P+K+E"; attribute :>> gap="Global request placement and source/target census remain open"; }
part claim3:ClaimRow { attribute :>> key="semantic"; attribute :>> mechanism="Shared plan unsupported is internal outcome"; attribute :>> condition="Try dedicated or other qualified plan without changing program values/control"; attribute :>> result="Cannot map conservative envelope refusal directly to Scheme OOM"; attribute :>> gap="Total fallback, precise OOM policy and emergency failure continuation open"; }
part claim4:ClaimRow { attribute :>> key="growth"; attribute :>> mechanism="Detached reservation batch with stable owner and old source manifest"; attribute :>> condition="Actual destination count only; no native callback/GC during reserve"; attribute :>> result="Partial success retained for retry or retired after collective result delivery"; attribute :>> gap="Current adjust_msections is not transactional detached reservation"; }
part claim5:ClaimRow { attribute :>> key="unknown"; attribute :>> mechanism="Stable completion owner retains roots, plan and uncertain grant"; attribute :>> condition="No setup/free from unknown result; exact token resolution required"; attribute :>> result="No timeout inference and no coordinator-only release"; attribute :>> gap="Native orphan delivery and no-fail coordinator service open"; }
part def MemoryRow { attribute key:String; attribute publication:String; attribute consumer:String; attribute gap:String; }
part memory0:MemoryRow { attribute :>> key="source"; attribute :>> publication="Close source membership before ordinary reads"; attribute :>> consumer="Pin old sections and copy manifest away from mutable header"; attribute :>> gap="Existing phase barrier not full C11 provenance proof"; }
part memory1:MemoryRow { attribute :>> key="reserve"; attribute :>> publication="Private initialized grants -> release completion token"; attribute :>> consumer="Owner acquire actual identities and counts"; attribute :>> gap="Unknown can own allocations absent from known lower-bound count"; }
part memory2:MemoryRow { attribute :>> key="commit"; attribute :>> publication="Release immutable accepted plan; member acquires exact generation"; attribute :>> consumer="Old metadata readers retired before replacement and setup"; attribute :>> gap="Header commit is not permission to release old payload blocks"; }
part memory3:MemoryRow { attribute :>> key="failed"; attribute :>> publication="Known failure plus every last-reader/result acknowledgement"; attribute :>> consumer="Only batch-private new blocks may be reclaimed"; attribute :>> gap="Never shrink below roots or other resize grants"; }
part memory4:MemoryRow { attribute :>> key="copy"; attribute :>> publication="No-fit charge and source credit consumed exactly once"; attribute :>> consumer="Separate forwarding CAS from initialized payload READY"; attribute :>> gap="Weak phase shares same budget; cancellations do not reset it"; }
part memory5:MemoryRow { attribute :>> key="resume"; attribute :>> publication="Copy complete then post-GC fudge and executable headroom"; attribute :>> consumer="Old roster completes same sync-op result before Scheme resumes"; attribute :>> gap="Failure after flip cannot reuse pre-setup rejection protocol"; }
part def GainRow { attribute key:String; attribute avoided:String; attribute added:String; attribute condition:String; }
part gain0:GainRow { attribute :>> key="snapshot"; attribute :>> avoided="Use old source allocation envelope instead of exact liveness oracle"; attribute :>> added="Validated extent/identity census and generation pins"; attribute :>> condition="No claim that current factor-two counters are already sufficient"; }
part gain1:GainRow { attribute :>> key="dedicated"; attribute :>> avoided="Protect continuation without allocating a second stack section"; attribute :>> added="Reduced heap borrowing may require destination growth"; attribute :>> condition="Net benefit depends on live fraction and grant sizes"; }
part gain2:GainRow { attribute :>> key="packing"; attribute :>> avoided="Account for bounded fragmentation before forwarding"; attribute :>> added="Potentially conservative N and reserved unused capacity"; attribute :>> condition="Tighter qualified G yields useful bound; generic cap yields d=1"; }
part gain3:GainRow { attribute :>> key="retry"; attribute :>> avoided="Reuse known partial native allocation"; attribute :>> added="Stable batch ledger and no ambiguous new attempt"; attribute :>> condition="Unknown attempt cannot be retried until resolved or separately fenced"; }
part gain4:GainRow { attribute :>> key="transaction"; attribute :>> avoided="Avoid unsafe in-place rollback with live readers"; attribute :>> added="Candidate metadata copy and commit/retirement protocol"; attribute :>> condition="Modern C sufficient; existing adjust_msections not silently treated as transaction"; }
part gain5:GainRow { attribute :>> key="concurrency"; attribute :>> avoided="Reuse P current worker frontiers and existing allocation lock"; attribute :>> added="Static packing headroom includes P private end sections"; attribute :>> condition="No measured speedup or net memory saving established"; }
part def ContractRow { attribute fromNode:String; attribute toNode:String; attribute custody:String; }
part contract0:ContractRow { attribute :>> fromNode="old-source-epoch"; attribute :>> toNode="source-envelope"; attribute :>> custody="Old N and validated Q stay fixed during target growth"; }
part contract1:ContractRow { attribute :>> fromNode="source-envelope"; attribute :>> toNode="grant-profile"; attribute :>> custody="Bound payload, alignment and effective frame requests"; }
part contract2:ContractRow { attribute :>> fromNode="grant-profile"; attribute :>> toNode="packing-envelope"; attribute :>> custody="Include threshold charge and no-fit waste"; }
part contract3:ContractRow { attribute :>> fromNode="restore-spans"; attribute :>> toNode="dedicated-stacks"; attribute :>> custody="R plus execution headroom independently fits"; }
part contract4:ContractRow { attribute :>> fromNode="dedicated-stacks"; attribute :>> toNode="destination-target"; attribute :>> custody="P stacks plus K heap sections plus E future reserve"; }
part contract5:ContractRow { attribute :>> fromNode="packing-envelope"; attribute :>> toNode="destination-target"; attribute :>> custody="Global size alone is insufficient; contiguous grants must fit"; }
part contract6:ContractRow { attribute :>> fromNode="destination-target"; attribute :>> toNode="detached-reservation"; attribute :>> custody="Stable native owner; no GC callback or old-manifest mutation"; }
part contract7:ContractRow { attribute :>> fromNode="detached-reservation"; attribute :>> toNode="known-partial"; attribute :>> custody="Actual blocks retained for retry or qualified cleanup"; }
part contract8:ContractRow { attribute :>> fromNode="detached-reservation"; attribute :>> toNode="unknown-custody"; attribute :>> custody="Uncertain block ownership pins old roster and metadata"; }
part contract9:ContractRow { attribute :>> fromNode="known-partial"; attribute :>> toNode="collective-plan"; attribute :>> custody="Accept only qualified complete actual grant; otherwise internal refusal"; }
part contract10:ContractRow { attribute :>> fromNode="unknown-custody"; attribute :>> toNode="collective-plan"; attribute :>> custody="Resolve exact attempt before admission"; }
part contract11:ContractRow { attribute :>> fromNode="collective-plan"; attribute :>> toNode="setup"; attribute :>> custody="All members consume accepted plan and retire last read"; }
part contract12:ContractRow { attribute :>> fromNode="collective-plan"; attribute :>> toNode="alternative-plan"; attribute :>> custody="Refusal is not a Scheme error; preserve old source"; }
part contract13:ContractRow { attribute :>> fromNode="setup"; attribute :>> toNode="copy-and-resume"; attribute :>> custody="Enforce same budget through strong weak restore and headroom"; }
part def BindingRow { attribute actionName:String; attribute lemma:String; attribute scope:String; }
part binding0:BindingRow { attribute :>> actionName="dedicated_copy_capacity.freeze"; attribute :>> lemma="DedicatedCopy.freezePreserves"; attribute :>> scope="Actual typed AST action preservation; source refinement open"; }
part binding1:BindingRow { attribute :>> actionName="dedicated_copy_capacity.sharedUnsuitable"; attribute :>> lemma="DedicatedCopy.sharedUnsuitablePreserves"; attribute :>> scope="Actual typed AST action preservation; source refinement open"; }
part binding2:BindingRow { attribute :>> actionName="dedicated_copy_capacity.growFull"; attribute :>> lemma="DedicatedCopy.growFullPreserves"; attribute :>> scope="Actual typed AST action preservation; source refinement open"; }
part binding3:BindingRow { attribute :>> actionName="dedicated_copy_capacity.growPartial"; attribute :>> lemma="DedicatedCopy.growPartialPreserves"; attribute :>> scope="Actual typed AST action preservation; source refinement open"; }
part binding4:BindingRow { attribute :>> actionName="dedicated_copy_capacity.growFailed"; attribute :>> lemma="DedicatedCopy.growFailedPreserves"; attribute :>> scope="Actual typed AST action preservation; source refinement open"; }
part binding5:BindingRow { attribute :>> actionName="dedicated_copy_capacity.growUnknown"; attribute :>> lemma="DedicatedCopy.growUnknownPreserves"; attribute :>> scope="Actual typed AST action preservation; source refinement open"; }
part binding6:BindingRow { attribute :>> actionName="dedicated_copy_capacity.resolveFull"; attribute :>> lemma="DedicatedCopy.resolveFullPreserves"; attribute :>> scope="Actual typed AST action preservation; source refinement open"; }
part binding7:BindingRow { attribute :>> actionName="dedicated_copy_capacity.resolvePartial"; attribute :>> lemma="DedicatedCopy.resolvePartialPreserves"; attribute :>> scope="Actual typed AST action preservation; source refinement open"; }
part binding8:BindingRow { attribute :>> actionName="dedicated_copy_capacity.chooseDedicated"; attribute :>> lemma="DedicatedCopy.chooseDedicatedPreserves"; attribute :>> scope="Actual typed AST action preservation; source refinement open"; }
part binding9:BindingRow { attribute :>> actionName="dedicated_copy_capacity.planUnavailable"; attribute :>> lemma="DedicatedCopy.planUnavailablePreserves"; attribute :>> scope="Actual typed AST action preservation; source refinement open"; }
part binding10:BindingRow { attribute :>> actionName="dedicated_copy_capacity.retryPlan"; attribute :>> lemma="DedicatedCopy.retryPlanPreserves"; attribute :>> scope="Actual typed AST action preservation; source refinement open"; }
part binding11:BindingRow { attribute :>> actionName="dedicated_copy_capacity.beginCopy"; attribute :>> lemma="DedicatedCopy.beginCopyPreserves"; attribute :>> scope="Actual typed AST action preservation; source refinement open"; }
part binding12:BindingRow { attribute :>> actionName="dedicated_copy_capacity.retireCharged"; attribute :>> lemma="DedicatedCopy.retireChargedPreserves"; attribute :>> scope="Actual typed AST action preservation; source refinement open"; }
part binding13:BindingRow { attribute :>> actionName="dedicated_copy_capacity.consumeOne"; attribute :>> lemma="DedicatedCopy.consumeOnePreserves"; attribute :>> scope="Actual typed AST action preservation; source refinement open"; }
part binding14:BindingRow { attribute :>> actionName="dedicated_copy_capacity.retainUnknown"; attribute :>> lemma="DedicatedCopy.retainUnknownPreserves"; attribute :>> scope="Actual typed AST action preservation; source refinement open"; }
part binding15:BindingRow { attribute :>> actionName="dedicated_copy_capacity.cleanupKnownBatch"; attribute :>> lemma="DedicatedCopy.cleanupKnownBatchPreserves"; attribute :>> scope="Actual typed AST action preservation; source refinement open"; }
part def ProofRow { attribute key:String; attribute lemma:String; }
part proof0:ProofRow { attribute :>> key="envelope"; attribute :>> lemma="CopyCapacityComposition.destinationEnvelope"; }
part proof1:ProofRow { attribute :>> key="32bit"; attribute :>> lemma="CopyCapacityComposition.word32Envelope"; }
part proof2:ProofRow { attribute :>> key="64bit"; attribute :>> lemma="CopyCapacityComposition.word64Envelope"; }
part proof3:ProofRow { attribute :>> key="packing"; attribute :>> lemma="CopyCapacityComposition.enoughHeapSections"; }
part proof4:ProofRow { attribute :>> key="physical"; attribute :>> lemma="CopyCapacityComposition.totalPhysicalBudget"; }
part proof5:ProofRow { attribute :>> key="fragment-control"; attribute :>> lemma="CopyCapacityComposition.fragmentationCounterexample"; }
part proof6:ProofRow { attribute :>> key="profile-example"; attribute :>> lemma="CopyCapacityComposition.illustrativePlan"; }
part proof7:ProofRow { attribute :>> key="generic-control"; attribute :>> lemma="CopyCapacityComposition.genericGrantBoundDegenerates"; }
part proof8:ProofRow { attribute :>> key="capacity"; attribute :>> lemma="DedicatedCopy.acceptedPhysicalCapacity"; }
part proof9:ProofRow { attribute :>> key="unknown"; attribute :>> lemma="DedicatedCopy.unknownCannotSetupOrFree"; }
part proof10:ProofRow { attribute :>> key="fixed-source"; attribute :>> lemma="DedicatedCopy.oldSourceImmutable"; }
part proof11:ProofRow { attribute :>> key="composition"; attribute :>> lemma="CopyCapacityComposition.reachableCoupled"; }
part proof12:ProofRow { attribute :>> key="setup"; attribute :>> lemma="CopyCapacityComposition.setupHasCapacityAndRestore"; }
part proof13:ProofRow { attribute :>> key="unknown-copy"; attribute :>> lemma="CopyCapacityComposition.unknownCannotCopy"; }
part proof14:ProofRow { attribute :>> key="successful-run"; attribute :>> lemma="CopyCapacityComposition.successfulRun"; }
part history:GambitAssuranceRouting::ModelNeed { ref part :>> owner=GambitAssuranceRelations::modelUse3; attribute :>> obligationId="DC-history"; attribute :>> kind="interleaving"; attribute :>> subjectPath="dev/refactoring/modern-c/models/quint/dedicated_copy_capacity.qnt"; attribute :>> subjectScope="Two-worker fixed source envelope actual partial unknown retry and charge histories"; attribute :>> premise="Research only; symbolic and finite model proofs are not native qualification"; }
part induction:GambitAssuranceRouting::ModelNeed { ref part :>> owner=GambitAssuranceRelations::modelUse3; attribute :>> obligationId="DC-induction"; attribute :>> kind="induction"; attribute :>> subjectPath="dev/refactoring/modern-c/models/lean/DedicatedCopy.lean"; attribute :>> subjectScope="All actual typed ledger actions"; attribute :>> premise="Research only; symbolic and finite model proofs are not native qualification"; }
part composition:GambitAssuranceRouting::ModelNeed { ref part :>> owner=GambitAssuranceRelations::modelUse3; attribute :>> obligationId="DC-composition"; attribute :>> kind="induction"; attribute :>> subjectPath="dev/refactoring/modern-c/models/lean/CopyCapacityComposition.lean"; attribute :>> subjectScope="Conditional packing and exact preceding restore plus collective contracts"; attribute :>> premise="Research only; symbolic and finite model proofs are not native qualification"; }
part projection:GambitAssuranceRouting::ModelNeed { ref part :>> owner=GambitAssuranceRelations::modelUse3; attribute :>> obligationId="DC-projection"; attribute :>> kind="restricted-projection"; attribute :>> subjectPath="dev/refactoring/modern-c/models/lean/DedicatedCopyAst.lean"; attribute :>> subjectScope="Typed IR bound-state identity extraction"; attribute :>> premise="Research only; symbolic and finite model proofs are not native qualification"; }
part source:GambitAssuranceRouting::ModelNeed { ref part :>> owner=GambitAssuranceRelations::modelUse3; attribute :>> obligationId="DC-source"; attribute :>> kind="source-refinement"; attribute :>> subjectPath="dev/refactoring/modern-c/dedicated-copy-capacity-design.org"; attribute :>> subjectScope="Source partition largest request threshold charge and total Scheme fallback open"; attribute :>> premise="Research only; symbolic and finite model proofs are not native qualification"; }
part platform:GambitAssuranceRouting::ModelNeed { ref part :>> owner=GambitAssuranceRelations::modelUse3; attribute :>> obligationId="DC-platform"; attribute :>> kind="native-memory-order"; attribute :>> subjectPath="dev/refactoring/modern-c/dedicated-copy-capacity-design.org"; attribute :>> subjectScope="Native reservation completion and C11 metadata retirement open"; attribute :>> premise="Research only; symbolic and finite model proofs are not native qualification"; }
part def Dependency { ref part prior:GambitAssuranceRouting::ModelNeed; attribute contract:String; }
part priorRestore:Dependency { ref part :>> prior=GambitContinuationRestoreAdmission::composition; attribute :>> contract="Exact prior restore bounds plus accepted collective used by new capacity product"; }
part priorCharge:Dependency { ref part :>> prior=GambitDefaultLeaseAdmission::composition; attribute :>> contract="Threshold and visit charging are premises, not a substitute for contiguous capacity"; }
}
