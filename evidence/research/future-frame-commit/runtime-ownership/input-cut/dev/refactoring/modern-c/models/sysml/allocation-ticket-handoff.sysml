package GambitAllocationTicketHandoff { private import ScalarValues::*;
part def Owner { attribute componentId:String; }
part storageOwner:Owner { attribute :>> componentId="storage"; }
part def SourceRow { attribute key:String; attribute path:String; attribute needle:String; attribute obligation:String; }
part source0:SourceRow { attribute :>> key="allocate"; attribute :>> path="vendor/gambit/lib/_mem/rc-allocation.inc"; attribute :>> needle="___ALLOC_MEM(bytes + sizeof (___rc_header))"; attribute :>> obligation="Checked extent and stable allocation attempt must precede this effect"; }
part source1:SourceRow { attribute :>> key="initialize"; attribute :>> path="vendor/gambit/lib/_mem/rc-allocation.inc"; attribute :>> needle="h->data = ___FAL;"; attribute :>> obligation="Private storage has false Scheme payload; input Scheme roots are separate"; }
part source2:SourceRow { attribute :>> key="register"; attribute :>> path="vendor/gambit/lib/_mem/rc-allocation.inc"; attribute :>> needle="tail->next = h;"; attribute :>> obligation="Current append has no result ledger or admission transaction"; }
part source3:SourceRow { attribute :>> key="null"; attribute :>> path="vendor/gambit/lib/_mem/rc-allocation.inc"; attribute :>> needle="if (ptr != 0) ___register_rc (___PSP ptr);"; attribute :>> obligation="Definite NULL already avoids registration"; }
part source4:SourceRow { attribute :>> key="release"; attribute :>> path="vendor/gambit/lib/_mem/rc-allocation.inc"; attribute :>> needle="next->prev = prev;"; attribute :>> obligation="Never-linked candidate needs dedicated private free rather than linked release"; }
part source5:SourceRow { attribute :>> key="cleanup"; attribute :>> path="vendor/gambit/lib/_mem/rc-allocation.inc"; attribute :>> needle="___HIDDEN void cleanup_rc"; attribute :>> obligation="Current bulk free has no stable attempt or outstanding ticket census"; }
part source6:SourceRow { attribute :>> key="malloc"; attribute :>> path="vendor/gambit/lib/os_base.c"; attribute :>> needle="ptr = malloc (bytes);"; attribute :>> obligation="Native allocator is real issuer of pointer or NULL; not ticket signer"; }
part source7:SourceRow { attribute :>> key="allocator-log"; attribute :>> path="vendor/gambit/lib/os_base.c"; attribute :>> needle="bytes) ALLOCATED"; attribute :>> obligation="Debug logger lies after allocation and before wrapper return; profile must qualify it"; }
part source8:SourceRow { attribute :>> key="free"; attribute :>> path="vendor/gambit/lib/os_base.c"; attribute :>> needle="free (ptr);"; attribute :>> obligation="Synchronous physical release separated from uncertain delivery"; }
part source9:SourceRow { attribute :>> key="root-scan"; attribute :>> path="vendor/gambit/lib/_mem/rc-roots.inc"; attribute :>> needle="mark_array (work, &h->data, 1);"; attribute :>> obligation="New ticket root carrier not automatically covered by old RC chain"; }
part source10:SourceRow { attribute :>> key="tcl"; attribute :>> path="vendor/gambit/examples/tcltk/tcltk.scm"; attribute :>> needle="void *cd = ___EXT(___alloc_rc) (0);"; attribute :>> obligation="Real zero payload caller still owns header and later allocates Scheme vector"; }
part source11:SourceRow { attribute :>> key="tcl-failure"; attribute :>> path="vendor/gambit/examples/tcltk/tcltk.scm"; attribute :>> needle="___EXT(___release_rc) (cd);"; attribute :>> obligation="Vector failure releases already registered storage; different from private rollback"; }
part source12:SourceRow { attribute :>> key="closure"; attribute :>> path="vendor/gambit/lib/os_dyn.c"; attribute :>> needle="___set_data_rc (c_closure, proc);"; attribute :>> obligation="Architecture conditional closure caller requires source Scheme root protection"; }
part source13:SourceRow { attribute :>> key="throw"; attribute :>> path="vendor/gambit/include/_gambit/foreign_conversion.h.in"; attribute :>> needle="#define ___THROW(e)do { ___ps->longjmp_err = e;"; attribute :>> obligation="C nonlocal exit has no automatic ticket cleanup; reject unmediated crossing"; }
part source14:SourceRow { attribute :>> key="call"; attribute :>> path="vendor/gambit/lib/setup.c"; attribute :>> needle="___EXP_FUNC(___SCMOBJ,___call)"; attribute :>> obligation="Existing catcher and marker paths do not create stable allocation attempt records"; }
part source15:SourceRow { attribute :>> key="export"; attribute :>> path="vendor/gambit/lib/setup.c"; attribute :>> needle="= ___alloc_rc_no_register;"; attribute :>> obligation="Public indirect allocation callers not closed by literal inventory"; }
part source16:SourceRow { attribute :>> key="layout"; attribute :>> path="vendor/gambit/include/_gambit/memory_state.h.in"; attribute :>> needle="typedef struct ___rc_header_struct"; attribute :>> obligation="No stable ticket identity or operation result in legacy header"; }
part source17:SourceRow { attribute :>> key="teardown"; attribute :>> path="vendor/gambit/lib/_mem/memory-lifecycle.inc"; attribute :>> needle="free_still_objs (___ps);"; attribute :>> obligation="Source Scheme roots must survive cleanup ordering before RC bulk free"; }
part def IssuerRow { attribute key:String; attribute proposedIssuer:String; attribute actualSource:String; attribute status:String; attribute responsibility:String; }
part issuer0:IssuerRow { attribute :>> key="ticket"; attribute :>> proposedIssuer="VM stable TicketPool owner"; attribute :>> actualSource="alloc_rc has only local ptr and context RC head"; attribute :>> status="absent"; attribute :>> responsibility="Reserve stable cell result record index node and guard capacity before invoking allocator"; }
part issuer1:IssuerRow { attribute :>> key="allocator"; attribute :>> proposedIssuer="qualified native allocator adapter"; attribute :>> actualSource="alloc_mem default malloc branch"; attribute :>> status="present branch only; profile unqualified"; attribute :>> responsibility="Return pointer or NULL and preserve allocator provenance"; }
part issuer2:IssuerRow { attribute :>> key="capture"; attribute :>> proposedIssuer="stable nonescaping completion owner"; attribute :>> actualSource="alloc_rc_no_register local h and alloc_rc local ptr"; attribute :>> status="absent"; attribute :>> responsibility="Capture native return before any escape callback or cancellation; retain unknown otherwise"; }
part issuer3:IssuerRow { attribute :>> key="index"; attribute :>> proposedIssuer="VM storage transaction owner"; attribute :>> actualSource="register_rc plain context list append"; attribute :>> status="absent"; attribute :>> responsibility="Commit exactly one index effect under OperationId and answer status queries"; }
part issuer4:IssuerRow { attribute :>> key="roots"; attribute :>> proposedIssuer="VM root round owner"; attribute :>> actualSource="mark_rc scans registered h.data"; attribute :>> status="old consumer exists; carrier adapter absent"; attribute :>> responsibility="Protect Scheme inputs in every GC round until target root acknowledgment"; }
part issuer5:IssuerRow { attribute :>> key="abort"; attribute :>> proposedIssuer="private candidate owner"; attribute :>> actualSource="release_rc assumes initialized prev next"; attribute :>> status="absent"; attribute :>> responsibility="Use original allocation base after definite absent publication and settled borrowers"; }
part issuer6:IssuerRow { attribute :>> key="unknown"; attribute :>> proposedIssuer="VM quarantine owner"; attribute :>> actualSource="cleanup_rc unconditionally frees chain"; attribute :>> status="absent"; attribute :>> responsibility="Retain poisoned operation and receipt identities through processor exit"; }
part issuer7:IssuerRow { attribute :>> key="retire"; attribute :>> proposedIssuer="TicketPool lease owner"; attribute :>> actualSource="no ticket fields in rc header"; attribute :>> status="absent"; attribute :>> responsibility="Retire cell only after exact delivery acknowledgment observer grace and no future retry authority"; }
part def NeedRow { attribute key:String; attribute kind:String; attribute path:String; attribute scope:String; ref owner:Owner; }
part need0:NeedRow { attribute :>> key="Ticket-formal"; attribute :>> kind="formal"; attribute :>> path="dev/refactoring/modern-c/models/quint/allocation_ticket_handoff.qnt"; attribute :>> scope="single attempt finite state safety; no native effect atomicity"; ref :>> owner=storageOwner; }
part need1:NeedRow { attribute :>> key="Ticket-bridge"; attribute :>> kind="bridge"; attribute :>> path="dev/refactoring/modern-c/models/lean/AllocationTicket.lean"; attribute :>> scope="restricted typed IR mirror and finite reachable induction; trusted parser projector"; ref :>> owner=storageOwner; }
part need2:NeedRow { attribute :>> key="Ticket-pool"; attribute :>> kind="native"; attribute :>> path="vendor/gambit/lib/_mem/rc-allocation.inc"; attribute :>> scope="stable pool bootstrap nested capacity generation nonallocation and reclamation unqualified"; ref :>> owner=storageOwner; }
part need3:NeedRow { attribute :>> key="Ticket-window"; attribute :>> kind="native"; attribute :>> path="vendor/gambit/lib/os_base.c"; attribute :>> scope="allocator return capture and nonlocal exit profile has no qualified guard"; ref :>> owner=storageOwner; }
part need4:NeedRow { attribute :>> key="Ticket-index"; attribute :>> kind="native"; attribute :>> path="vendor/gambit/lib/_mem/rc-allocation.inc"; attribute :>> scope="linearizable index outcome query and private rollback absent"; ref :>> owner=storageOwner; }
part need5:NeedRow { attribute :>> key="Ticket-roots"; attribute :>> kind="native"; attribute :>> path="vendor/gambit/lib/_mem/rc-roots.inc"; attribute :>> scope="input root carrier to every GC and descriptor lifetime unresolved"; ref :>> owner=storageOwner; }
part need6:NeedRow { attribute :>> key="Ticket-exit"; attribute :>> kind="native"; attribute :>> path="vendor/gambit/include/_gambit/foreign_conversion.h.in"; attribute :>> scope="continuation reentry cancellation and cleanup owner closure unresolved"; ref :>> owner=storageOwner; }
part need7:NeedRow { attribute :>> key="Ticket-profile"; attribute :>> kind="native"; attribute :>> path="vendor/gambit/include/_gambit/runtime_protocols.h.in"; attribute :>> scope="effective C23 Darwin configuration arithmetic ABI and atomic capabilities unresolved"; ref :>> owner=storageOwner; }
part def ContractRow { attribute fromNode:String; attribute toNode:String; attribute custody:String; }
part contract0:ContractRow { attribute :>> fromNode="Admission"; attribute :>> toNode="StableTicketPool"; attribute :>> custody="Reserve ticket plus index and terminal record capacity; exhaustion returns before allocator"; }
part contract1:ContractRow { attribute :>> fromNode="StableTicketPool"; attribute :>> toNode="AllocatorInFlight"; attribute :>> custody="Publish stable attempt and GC input carrier; release pool lock before allocation"; }
part contract2:ContractRow { attribute :>> fromNode="AllocatorInFlight"; attribute :>> toNode="UnrecordedReturn"; attribute :>> custody="Native success is initially only local; nonescaping guard is an admission premise"; }
part contract3:ContractRow { attribute :>> fromNode="UnrecordedReturn"; attribute :>> toNode="PrivateCandidate"; attribute :>> custody="Capture original base checked extent and allocator provenance in stable record"; }
part contract4:ContractRow { attribute :>> fromNode="UnrecordedReturn"; attribute :>> toNode="Quarantine"; attribute :>> custody="Unrecorded escape has no reconstructible pointer; unknown is retained and not retried"; }
part contract5:ContractRow { attribute :>> fromNode="PrivateCandidate"; attribute :>> toNode="StorageIndex"; attribute :>> custody="Commit keyed effect; unknown index response retains ticket and source roots"; }
part contract6:ContractRow { attribute :>> fromNode="PrivateCandidate"; attribute :>> toNode="PrivateAbort"; attribute :>> custody="Only known absent publication and settled borrows permit original-base free"; }
part contract7:ContractRow { attribute :>> fromNode="PrivateAbort"; attribute :>> toNode="Quarantine"; attribute :>> custody="Unknown free is not permission for a second free or cell reuse"; }
part contract8:ContractRow { attribute :>> fromNode="StorageIndex"; attribute :>> toNode="TicketRetirement"; attribute :>> custody="Observe commit root coverage and exact result; cell recycling still requires replay and observer grace"; }
part def GainRow { attribute key:String; attribute avoided:String; attribute added:String; attribute condition:String; }
part gain0:GainRow { attribute :>> key="critical metadata"; attribute :>> avoided="0 metadata allocator calls inside qualified issuance"; attribute :>> added="fixed reserved memory and pool admission work"; attribute :>> condition="all needed cells exist before request; bootstrap excluded"; }
part gain1:GainRow { attribute :>> key="capacity"; attribute :>> avoided="T >= A + U + R + D + E"; attribute :>> added="U unknown R retained replies D nested attempts and emergency E reduce admission"; attribute :>> condition="hard workload bounds or explicit backpressure; no universal finite pool"; }
part gain2:GainRow { attribute :>> key="retry"; attribute :>> avoided="r same OperationId deliveries: 1 allocation and 1 index effect plus r-1 queries"; attribute :>> added="query ledger retained and synchronized"; attribute :>> condition="semantic retry only; fresh continuation execution needs fresh identity"; }
part gain3:GainRow { attribute :>> key="rollback"; attribute :>> avoided="at most 1 free invocation per private attempt in finite model"; attribute :>> added="unknown free holds quarantine indefinitely"; attribute :>> condition="known absent index and exact original allocator base; no speculative retry"; }
part gain4:GainRow { attribute :>> key="fast path"; attribute :>> avoided="no demonstrated CPU work removed from old malloc plus O(1) append"; attribute :>> added="ticket reservation capture index publication and acknowledgement added"; attribute :>> condition="avoided repeated or unsafe work exceeds added work; frequency not measured"; }
part gain5:GainRow { attribute :>> key="language"; attribute :>> avoided="C23 sufficient for pool owner and typed generated protocol"; attribute :>> added="same root lifetime and exit proofs in modern C or Zig"; attribute :>> condition="Zig incremental runtime performance and proof savings not established"; }
part gain6:GainRow { attribute :>> key="retirement"; attribute :>> avoided="0 current native paths retired"; attribute :>> added="old public exports and collector chain remain until complete migration"; attribute :>> condition="all callers profile GC adapters unknown drain and private abort qualified"; }
part def MemoryRow { attribute key:String; attribute publication:String; attribute observation:String; attribute obligation:String; }
part memory0:MemoryRow { attribute :>> key="issue"; attribute :>> publication="initialize exclusive cell then release-publish active state"; attribute :>> observation="acquire on owner index or GC consumer before reading fields"; attribute :>> obligation="pool lifetime publication and bounded scan protocol must be refined"; }
part memory1:MemoryRow { attribute :>> key="commit"; attribute :>> publication="index descriptor immutable fields before release commit"; attribute :>> observation="acquire result under same OperationId"; attribute :>> obligation="pool and index locks are distinct; no lock held across allocator callbacks GC or I/O"; }
part memory2:MemoryRow { attribute :>> key="rollback"; attribute :>> publication="definite absent index and exclusive original base before free"; attribute :>> observation="known return required before backing record retirement"; attribute :>> obligation="no assumption of free receipt for abandoned execution"; }
part memory3:MemoryRow { attribute :>> key="recycle"; attribute :>> publication="close borrow retry and scan admission then observe grace"; attribute :>> observation="generation checked together with slot ownership in same transaction"; attribute :>> obligation="generation wrap causes admission refusal; address-only lookup insufficient"; }
part def BindingRow { attribute actionName:String; attribute lemma:String; }
part binding0:BindingRow { attribute :>> actionName="allocation_ticket_handoff.issue"; attribute :>> lemma="AllocationTicket.issuePreserves"; }
part binding1:BindingRow { attribute :>> actionName="allocation_ticket_handoff.metadataExhausted"; attribute :>> lemma="AllocationTicket.metadataExhaustedPreserves"; }
part binding2:BindingRow { attribute :>> actionName="allocation_ticket_handoff.invoke"; attribute :>> lemma="AllocationTicket.invokePreserves"; }
part binding3:BindingRow { attribute :>> actionName="allocation_ticket_handoff.cancelBeforeInvoke"; attribute :>> lemma="AllocationTicket.cancelBeforeInvokePreserves"; }
part binding4:BindingRow { attribute :>> actionName="allocation_ticket_handoff.allocatorNull"; attribute :>> lemma="AllocationTicket.allocatorNullPreserves"; }
part binding5:BindingRow { attribute :>> actionName="allocation_ticket_handoff.allocatorReturn"; attribute :>> lemma="AllocationTicket.allocatorReturnPreserves"; }
part binding6:BindingRow { attribute :>> actionName="allocation_ticket_handoff.captureReturn"; attribute :>> lemma="AllocationTicket.captureReturnPreserves"; }
part binding7:BindingRow { attribute :>> actionName="allocation_ticket_handoff.interruptUnrecordedReturn"; attribute :>> lemma="AllocationTicket.interruptUnrecordedReturnPreserves"; }
part binding8:BindingRow { attribute :>> actionName="allocation_ticket_handoff.allocatorOutcomeUnknown"; attribute :>> lemma="AllocationTicket.allocatorOutcomeUnknownPreserves"; }
part binding9:BindingRow { attribute :>> actionName="allocation_ticket_handoff.commit"; attribute :>> lemma="AllocationTicket.commitPreserves"; }
part binding10:BindingRow { attribute :>> actionName="allocation_ticket_handoff.indexOutcomeUnknown"; attribute :>> lemma="AllocationTicket.indexOutcomeUnknownPreserves"; }
part binding11:BindingRow { attribute :>> actionName="allocation_ticket_handoff.resolveCommitted"; attribute :>> lemma="AllocationTicket.resolveCommittedPreserves"; }
part binding12:BindingRow { attribute :>> actionName="allocation_ticket_handoff.resolveAbsent"; attribute :>> lemma="AllocationTicket.resolveAbsentPreserves"; }
part binding13:BindingRow { attribute :>> actionName="allocation_ticket_handoff.observeCommit"; attribute :>> lemma="AllocationTicket.observeCommitPreserves"; }
part binding14:BindingRow { attribute :>> actionName="allocation_ticket_handoff.retryCommitQuery"; attribute :>> lemma="AllocationTicket.retryCommitQueryPreserves"; }
part binding15:BindingRow { attribute :>> actionName="allocation_ticket_handoff.requestPrivateAbort"; attribute :>> lemma="AllocationTicket.requestPrivateAbortPreserves"; }
part binding16:BindingRow { attribute :>> actionName="allocation_ticket_handoff.invokePrivateFree"; attribute :>> lemma="AllocationTicket.invokePrivateFreePreserves"; }
part binding17:BindingRow { attribute :>> actionName="allocation_ticket_handoff.privateFreeKnown"; attribute :>> lemma="AllocationTicket.privateFreeKnownPreserves"; }
part binding18:BindingRow { attribute :>> actionName="allocation_ticket_handoff.privateFreeUnknown"; attribute :>> lemma="AllocationTicket.privateFreeUnknownPreserves"; }
part def RouteRow { attribute component:String; attribute actionName:String; attribute lemma:String; attribute producerAnchor:String; attribute obligationId:String; }
part route0:RouteRow { attribute :>> component="storage"; attribute :>> actionName="allocation_ticket_handoff.issue"; attribute :>> lemma="AllocationTicket.issuePreserves"; attribute :>> producerAnchor="allocate"; attribute :>> obligationId="Ticket-pool"; }
part route1:RouteRow { attribute :>> component="storage"; attribute :>> actionName="allocation_ticket_handoff.metadataExhausted"; attribute :>> lemma="AllocationTicket.metadataExhaustedPreserves"; attribute :>> producerAnchor="allocate"; attribute :>> obligationId="Ticket-pool"; }
part route2:RouteRow { attribute :>> component="storage"; attribute :>> actionName="allocation_ticket_handoff.invoke"; attribute :>> lemma="AllocationTicket.invokePreserves"; attribute :>> producerAnchor="malloc"; attribute :>> obligationId="Ticket-window"; }
part route3:RouteRow { attribute :>> component="storage"; attribute :>> actionName="allocation_ticket_handoff.cancelBeforeInvoke"; attribute :>> lemma="AllocationTicket.cancelBeforeInvokePreserves"; attribute :>> producerAnchor="throw"; attribute :>> obligationId="Ticket-exit"; }
part route4:RouteRow { attribute :>> component="storage"; attribute :>> actionName="allocation_ticket_handoff.allocatorNull"; attribute :>> lemma="AllocationTicket.allocatorNullPreserves"; attribute :>> producerAnchor="malloc"; attribute :>> obligationId="Ticket-window"; }
part route5:RouteRow { attribute :>> component="storage"; attribute :>> actionName="allocation_ticket_handoff.allocatorReturn"; attribute :>> lemma="AllocationTicket.allocatorReturnPreserves"; attribute :>> producerAnchor="malloc"; attribute :>> obligationId="Ticket-window"; }
part route6:RouteRow { attribute :>> component="storage"; attribute :>> actionName="allocation_ticket_handoff.captureReturn"; attribute :>> lemma="AllocationTicket.captureReturnPreserves"; attribute :>> producerAnchor="malloc"; attribute :>> obligationId="Ticket-window"; }
part route7:RouteRow { attribute :>> component="storage"; attribute :>> actionName="allocation_ticket_handoff.interruptUnrecordedReturn"; attribute :>> lemma="AllocationTicket.interruptUnrecordedReturnPreserves"; attribute :>> producerAnchor="malloc"; attribute :>> obligationId="Ticket-window"; }
part route8:RouteRow { attribute :>> component="storage"; attribute :>> actionName="allocation_ticket_handoff.allocatorOutcomeUnknown"; attribute :>> lemma="AllocationTicket.allocatorOutcomeUnknownPreserves"; attribute :>> producerAnchor="malloc"; attribute :>> obligationId="Ticket-window"; }
part route9:RouteRow { attribute :>> component="storage"; attribute :>> actionName="allocation_ticket_handoff.commit"; attribute :>> lemma="AllocationTicket.commitPreserves"; attribute :>> producerAnchor="register"; attribute :>> obligationId="Ticket-index"; }
part route10:RouteRow { attribute :>> component="storage"; attribute :>> actionName="allocation_ticket_handoff.indexOutcomeUnknown"; attribute :>> lemma="AllocationTicket.indexOutcomeUnknownPreserves"; attribute :>> producerAnchor="register"; attribute :>> obligationId="Ticket-index"; }
part route11:RouteRow { attribute :>> component="storage"; attribute :>> actionName="allocation_ticket_handoff.resolveCommitted"; attribute :>> lemma="AllocationTicket.resolveCommittedPreserves"; attribute :>> producerAnchor="register"; attribute :>> obligationId="Ticket-index"; }
part route12:RouteRow { attribute :>> component="storage"; attribute :>> actionName="allocation_ticket_handoff.resolveAbsent"; attribute :>> lemma="AllocationTicket.resolveAbsentPreserves"; attribute :>> producerAnchor="register"; attribute :>> obligationId="Ticket-index"; }
part route13:RouteRow { attribute :>> component="storage"; attribute :>> actionName="allocation_ticket_handoff.observeCommit"; attribute :>> lemma="AllocationTicket.observeCommitPreserves"; attribute :>> producerAnchor="register"; attribute :>> obligationId="Ticket-index"; }
part route14:RouteRow { attribute :>> component="storage"; attribute :>> actionName="allocation_ticket_handoff.retryCommitQuery"; attribute :>> lemma="AllocationTicket.retryCommitQueryPreserves"; attribute :>> producerAnchor="register"; attribute :>> obligationId="Ticket-index"; }
part route15:RouteRow { attribute :>> component="storage"; attribute :>> actionName="allocation_ticket_handoff.requestPrivateAbort"; attribute :>> lemma="AllocationTicket.requestPrivateAbortPreserves"; attribute :>> producerAnchor="free"; attribute :>> obligationId="Ticket-index"; }
part route16:RouteRow { attribute :>> component="storage"; attribute :>> actionName="allocation_ticket_handoff.invokePrivateFree"; attribute :>> lemma="AllocationTicket.invokePrivateFreePreserves"; attribute :>> producerAnchor="free"; attribute :>> obligationId="Ticket-index"; }
part route17:RouteRow { attribute :>> component="storage"; attribute :>> actionName="allocation_ticket_handoff.privateFreeKnown"; attribute :>> lemma="AllocationTicket.privateFreeKnownPreserves"; attribute :>> producerAnchor="free"; attribute :>> obligationId="Ticket-index"; }
part route18:RouteRow { attribute :>> component="storage"; attribute :>> actionName="allocation_ticket_handoff.privateFreeUnknown"; attribute :>> lemma="AllocationTicket.privateFreeUnknownPreserves"; attribute :>> producerAnchor="free"; attribute :>> obligationId="Ticket-index"; }
part def ProofRow { attribute key:String; attribute lemma:String; }
part proof0:ProofRow { attribute :>> key="all-step"; attribute :>> lemma="AllocationTicket.stepPreserves"; }
part proof1:ProofRow { attribute :>> key="reachable"; attribute :>> lemma="AllocationTicket.reachableSafe"; }
part proof2:ProofRow { attribute :>> key="unknown-custody"; attribute :>> lemma="AllocationTicket.unknownRetainsTicket"; }
part proof3:ProofRow { attribute :>> key="single-allocation"; attribute :>> lemma="AllocationTicket.noSecondAllocation"; }
part proof4:ProofRow { attribute :>> key="single-free"; attribute :>> lemma="AllocationTicket.noSecondFree"; }
part proof5:ProofRow { attribute :>> key="capacity"; attribute :>> lemma="AllocationTicket.poolBudget"; }
part proof6:ProofRow { attribute :>> key="issued-before-native"; attribute :>> lemma="AllocationTicket.issuedBeforeNative"; }
part proof7:ProofRow { attribute :>> key="unrecorded-owner"; attribute :>> lemma="AllocationTicket.unrecordedHasCustody"; }
part proof8:ProofRow { attribute :>> key="unknown-root-capacity"; attribute :>> lemma="AllocationTicket.sourceHeldWhileUnknown"; }
}
