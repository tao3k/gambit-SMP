package GambitEmissionPipeRefinement { private import ScalarValues::*;
part def SourceRow { attribute key:String; attribute path:String; attribute needle:String; attribute obligation:String; }
part source0:SourceRow { attribute :>> key="interval"; attribute :>> path="vendor/gambit/gsc/_t-c-1.scm"; attribute :>> needle="(define (targ-dump-mod objs c-inits sym-list key-list)"; attribute :>> obligation="Exact first pass / C init text / second pass source order"; }
part source1:SourceRow { attribute :>> key="first"; attribute :>> path="vendor/gambit/gsc/_t-c-1.scm"; attribute :>> needle="(def-mod-prm-glo \"DEF_MOD_PRM\")"; attribute :>> obligation="First normalization before output of first binding tuple"; }
part source2:SourceRow { attribute :>> key="second"; attribute :>> path="vendor/gambit/gsc/_t-c-1.scm"; attribute :>> needle="(def-mod-prm-glo \"DEF_MOD_GLO\")"; attribute :>> obligation="Second normalization occurs after intervening output"; }
part source3:SourceRow { attribute :>> key="cinit-write"; attribute :>> path="vendor/gambit/gsc/_t-c-1.scm"; attribute :>> needle="(targ-display x)"; attribute :>> obligation="C init strings displayed, not evaluated as Scheme"; }
part source4:SourceRow { attribute :>> key="cinit-check"; attribute :>> path="vendor/gambit/gsc/_ptree2.scm"; attribute :>> needle="Argument to 'c-initialize' must be a string"; attribute :>> obligation="Legal parser producer constrains type; aliases/extensions still require closure"; }
part source5:SourceRow { attribute :>> key="cinit-add"; attribute :>> path="vendor/gambit/gsc/_ptree2.scm"; attribute :>> needle="(define (add-c-init initialization-code-string)"; attribute :>> obligation="Actual storage writer"; }
part source6:SourceRow { attribute :>> key="cinit-producer"; attribute :>> path="vendor/gambit/gsc/_ptree1.scm"; attribute :>> needle="(add-c-init body)"; attribute :>> obligation="Actual parser call"; }
part source7:SourceRow { attribute :>> key="display"; attribute :>> path="vendor/gambit/gsc/_t-c-1.scm"; attribute :>> needle="(display x targ-port)"; attribute :>> obligation="Real output caller"; }
part source8:SourceRow { attribute :>> key="code"; attribute :>> path="vendor/gambit/gsc/_t-c-1.scm"; attribute :>> needle="(define (targ-code x)"; attribute :>> obligation="Typed tagged C forms recursively emitted, not raw VAR payload in selected case"; }
part source9:SourceRow { attribute :>> key="port"; attribute :>> path="vendor/gambit/gsc/_t-c-1.scm"; attribute :>> needle="(set! targ-port (open-output-file-preserving-case filename))"; attribute :>> obligation="Default emitter opens filename-derived port"; }
part source10:SourceRow { attribute :>> key="host"; attribute :>> path="vendor/gambit/gsc/_host.scm"; attribute :>> needle="(define (open-output-file-preserving-case path)"; attribute :>> obligation="Gambit host branch selects readtable while opening file"; }
part source11:SourceRow { attribute :>> key="open"; attribute :>> path="vendor/gambit/lib/_io.scm"; attribute :>> needle="(define-prim (##open-output-file path-or-settings)"; attribute :>> obligation="Actual public file opener calls generic file path"; }
part source12:SourceRow { attribute :>> key="device"; attribute :>> path="vendor/gambit/lib/_io.scm"; attribute :>> needle="(define (write-datum port obj we)"; attribute :>> obligation="Concrete device method dispatch selected by bounded slice"; }
part source13:SourceRow { attribute :>> key="display-api"; attribute :>> path="vendor/gambit/lib/_io.scm"; attribute :>> needle="(define-prim (##display"; attribute :>> obligation="Display uses generic writer and global formatter"; }
part source14:SourceRow { attribute :>> key="formatter"; attribute :>> path="vendor/gambit/lib/_io.scm"; attribute :>> needle="(set! ##wr x)"; attribute :>> obligation="Callable registration remains mutable"; }
part source15:SourceRow { attribute :>> key="debug"; attribute :>> path="vendor/gambit/gsc/_gscdebug.scm"; attribute :>> needle="(let ((save-wr ##wr))"; attribute :>> obligation="Special branch requires actual VAR or PTREE"; }
part source16:SourceRow { attribute :>> key="var"; attribute :>> path="vendor/gambit/gsc/_envadt.scm"; attribute :>> needle="(define (var? x)"; attribute :>> obligation="Scalar strings/integers fail vector predicate"; }
part source17:SourceRow { attribute :>> key="igsc"; attribute :>> path="vendor/gambit/gsc/igsc.scm"; attribute :>> needle="\"_gscdebug\""; attribute :>> obligation="Explicit interpreted debug loader; no inference all compiler modes load it"; }
part source18:SourceRow { attribute :>> key="io-fault"; attribute :>> path="vendor/gambit/lib/_io.scm"; attribute :>> needle="(define-prim (##raise-io-exception port exc)"; attribute :>> obligation="Port-specific or dynamic handler, not compiler diagnostic continuation"; }
part source19:SourceRow { attribute :>> key="compiler-handler"; attribute :>> path="vendor/gambit/gsc/_utils.scm"; attribute :>> needle="(define (with-exception-handling proc)"; attribute :>> obligation="Separate compiler diagnostic catcher"; }
part source20:SourceRow { attribute :>> key="gc-job"; attribute :>> path="vendor/gambit/lib/_kernel.scm"; attribute :>> needle="(##execute-jobs! ##gc-interrupt-jobs)"; attribute :>> obligation="Async producer class; no metadata authority inferred"; }
part source21:SourceRow { attribute :>> key="resource"; attribute :>> path="vendor/gambit/gsc/_t-c-1.scm"; attribute :>> needle="(define (targ-use-glo glo supply?)"; attribute :>> obligation="Named effect preserves canonical same-entry demand"; }
part source22:SourceRow { attribute :>> key="raw"; attribute :>> path="vendor/gambit/gsc/_t-c-1.scm"; attribute :>> needle="(vector-set! r 1 demanders)"; attribute :>> obligation="Unknown raw alias remains qualification blocker"; }
part source23:SourceRow { attribute :>> key="read-char"; attribute :>> path="vendor/gambit/lib/_io.scm"; attribute :>> needle="(define-prim (##read-char1 port)"; attribute :>> obligation="Each accepted char advances current rlo then unlocks"; }
part source24:SourceRow { attribute :>> key="rebase"; attribute :>> path="vendor/gambit/lib/_io.scm"; attribute :>> needle="(macro-fifo-advance!"; attribute :>> obligation="Reader advances peer FIFO, then rebases wlo and rlo"; }
part source25:SourceRow { attribute :>> key="no-carry"; attribute :>> path="vendor/gambit/lib/_io.scm"; attribute :>> needle="(if (##fx= vect-rlo vect-rhi)"; attribute :>> obligation="Selected exhausted-reader branch has no carry-over concatenation"; }
part source26:SourceRow { attribute :>> key="drain"; attribute :>> path="vendor/gambit/lib/_io.scm"; attribute :>> needle="(define (,',vect-wbuf-drain port)"; attribute :>> obligation="Resume relocks then reenters loop; fresh-buffer locals are rebound"; }
part source27:SourceRow { attribute :>> key="publish"; attribute :>> path="vendor/gambit/lib/_io.scm"; attribute :>> needle="(,',macro-vect-port-wlo-set!"; attribute :>> obligation="Published current whi added to wlo"; }
part source28:SourceRow { attribute :>> key="substring"; attribute :>> path="vendor/gambit/lib/_io.scm"; attribute :>> needle="(define-prim (##write-substring str start end port)"; attribute :>> obligation="Continuation retains loop i; after drain loops with same i"; }
part source29:SourceRow { attribute :>> key="chunk"; attribute :>> path="vendor/gambit/lib/_io.scm"; attribute :>> needle="(define chunk-size 32)"; attribute :>> obligation="Fixed source string buffer size"; }
part source30:SourceRow { attribute :>> key="handler"; attribute :>> path="vendor/gambit/lib/_thread.scm"; attribute :>> needle="(define-prim (with-exception-handler handler thunk)"; attribute :>> obligation="Original Gambit handler source"; }
part source31:SourceRow { attribute :>> key="capture"; attribute :>> path="vendor/gambit/lib/_thread.scm"; attribute :>> needle="(define-prim (call-with-current-continuation"; attribute :>> obligation="Source capture mechanism, GC/program-point refinement external"; }
part def WindowRow { attribute key:String; attribute cause:String; attribute effect:String; attribute reachability:String; attribute gap:String; }
part window0:WindowRow { attribute :>> key="ordinary"; attribute :>> cause="DEF_MOD_PRM output, section delimiters, C init strings, BEGIN_MOD_GLO"; attribute :>> effect="Real scalar display dispatch through device writer"; attribute :>> reachability="Actual source interval"; attribute :>> gap="Hook/effect/handler and artifact closure not automatically established"; }
part window1:WindowRow { attribute :>> key="debug-scalar"; attribute :>> cause="igsc debug hook sees selected scalar payload"; attribute :>> effect="Delegates to default writer, no temporary save-wr branch"; attribute :>> reachability="Direct branch exclusion under stable predicates and payload types"; attribute :>> gap="Nested handler/GC callback may output a separate VAR if it has authority"; }
part window2:WindowRow { attribute :>> key="pipe-debug"; attribute :>> cause="Application explicitly opens bounded string-pipe and prints valid VAR"; attribute :>> effect="Special interval can capture then restore old writer"; attribute :>> reachability="Legal configurable debug session"; attribute :>> gap="Does not identify default targ-port or a stock interval callback"; }
part window3:WindowRow { attribute :>> key="carry"; attribute :>> cause="Reader has unread carry-over during FIFO advance"; attribute :>> effect="Concatenates buffer and may update peer writer identity/whi"; attribute :>> reachability="Real alternate source branch"; attribute :>> gap="Excluded by this exhausted-reader refinement, not silently modeled as no-carry"; }
part def ClaimRow { attribute key:String; attribute mechanism:String; attribute condition:String; attribute result:String; attribute gap:String; }
part claim0:ClaimRow { attribute :>> key="direct-exclusion"; attribute :>> mechanism="Selected typed scalar output and stable built-in hook"; attribute :>> condition="No payload/type/predicate mutation"; attribute :>> result="No direct VAR/PTREE special branch in emitter interval"; attribute :>> gap="No global absence-of-callback theorem"; }
part claim1:ClaimRow { attribute :>> key="cursor"; attribute :>> mechanism="Concrete read/expose/rebase/publish actions with ghost character counts"; attribute :>> condition="Peer primed after escape; exhausted no-carry branch, retained peers, successful allocation and bounded counters"; attribute :>> result="emitted-delivered equals wlo+whi-rlo across any modeled replay"; attribute :>> gap="General carry-over, faults, compiled roots and actual identities still external"; }
part claim2:ClaimRow { attribute :>> key="resume"; attribute :>> mechanism="Saved local index restored; current buffer generation retained"; attribute :>> condition="Capture at selected timeout continuation"; attribute :>> result="No stale write to the old cached full buffer after drain"; attribute :>> gap="Captured old buffer may remain a GC root even when not used"; }
part claim3:ClaimRow { attribute :>> key="retirement"; attribute :>> mechanism="Same-entry canonical value plus qualified effect/output/exception contract"; attribute :>> condition="Explicit current profile receipt"; attribute :>> result="Second value normalization conditionally unnecessary"; attribute :>> gap="Current complete retirement receipt remains absent"; }
part def GainRow { attribute key:String; attribute avoided:String; attribute added:String; attribute condition:String; }
part gain0:GainRow { attribute :>> key="normalization"; attribute :>> avoided="At most one helper normalization per qualified binding emission"; attribute :>> added="Effect closure, frozen binding plan, validation and invalidation"; attribute :>> condition="p*N*Cn exceeds Cq + W*Cv; no measured speed claim"; }
part gain1:GainRow { attribute :>> key="writer-view"; attribute :>> avoided="Two global stores per special debug invocation only"; attribute :>> added="Owned recursive resolver and captured roots"; attribute :>> condition="Zero such stores saved on direct scalar default branch"; }
part gain2:GainRow { attribute :>> key="cursor"; attribute :>> avoided="Wrongly restoring cached physical buffers; repeated ad hoc ownership reasoning"; attribute :>> added="Source labels, frontier/identity relation and failure custody"; attribute :>> condition="No claim of eliminating real queued characters or GC roots"; }
part gain3:GainRow { attribute :>> key="parallel"; attribute :>> avoided="Cross-session shared writer/target dependencies if consumers migrate"; attribute :>> added="Independent contexts and immutable plans"; attribute :>> condition="This local proof does not establish macOS latency or multicore throughput gain"; }
part def ContractRow { attribute fromNode:String; attribute toNode:String; attribute custody:String; }
part contract0:ContractRow { attribute :>> fromNode="Default binding passes"; attribute :>> toNode="C init text"; attribute :>> custody="source order"; }
part contract1:ContractRow { attribute :>> fromNode="C init text"; attribute :>> toNode="Scalar display"; attribute :>> custody="text, no Scheme eval"; }
part contract2:ContractRow { attribute :>> fromNode="Scalar display"; attribute :>> toNode="Device writer"; attribute :>> custody="real file path"; }
part contract3:ContractRow { attribute :>> fromNode="Device writer"; attribute :>> toNode="Global formatter"; attribute :>> custody="dispatch remains"; }
part contract4:ContractRow { attribute :>> fromNode="Global formatter"; attribute :>> toNode="Direct special excluded"; attribute :>> custody="stable scalar payload"; }
part contract5:ContractRow { attribute :>> fromNode="Global formatter"; attribute :>> toNode="Handler and async closure"; attribute :>> custody="separate authority needed"; }
part contract6:ContractRow { attribute :>> fromNode="Legal VAR debug session"; attribute :>> toNode="String-pipe capture"; attribute :>> custody="different port and context"; }
part contract7:ContractRow { attribute :>> fromNode="String-pipe capture"; attribute :>> toNode="Reader rebasing"; attribute :>> custody="prime peer; no carry-over"; }
part contract8:ContractRow { attribute :>> fromNode="Reader rebasing"; attribute :>> toNode="Current buffer publication"; attribute :>> custody="same physical frontier"; }
part contract9:ContractRow { attribute :>> fromNode="Current buffer publication"; attribute :>> toNode="Saved local index replay"; attribute :>> custody="fresh buffer, old loop i"; }
part contract10:ContractRow { attribute :>> fromNode="Saved local index replay"; attribute :>> toNode="Root and lifetime closure"; attribute :>> custody="captured dead locals may still be roots"; }
part contract11:ContractRow { attribute :>> fromNode="Direct special excluded"; attribute :>> toNode="Retirement receipt"; attribute :>> custody="not sufficient alone"; }
part contract12:ContractRow { attribute :>> fromNode="Handler and async closure"; attribute :>> toNode="Retirement receipt"; attribute :>> custody="effect and observation proof"; }
part contract13:ContractRow { attribute :>> fromNode="Root and lifetime closure"; attribute :>> toNode="Retirement receipt"; attribute :>> custody="source/GC refinement"; }
part def BindingRow { attribute actionName:String; attribute lemma:String; attribute scope:String; }
part binding0:BindingRow { attribute :>> actionName="emission_pipe_refinement.first"; attribute :>> lemma="EmissionPipe.firstPreserves"; attribute :>> scope="Two distinct contexts; concrete no-carry cursor subset and conditional emitter"; }
part binding1:BindingRow { attribute :>> actionName="emission_pipe_refinement.selectDebug"; attribute :>> lemma="EmissionPipe.selectDebugPreserves"; attribute :>> scope="Two distinct contexts; concrete no-carry cursor subset and conditional emitter"; }
part binding2:BindingRow { attribute :>> actionName="emission_pipe_refinement.selectCustom"; attribute :>> lemma="EmissionPipe.selectCustomPreserves"; attribute :>> scope="Two distinct contexts; concrete no-carry cursor subset and conditional emitter"; }
part binding3:BindingRow { attribute :>> actionName="emission_pipe_refinement.prmRemainder"; attribute :>> lemma="EmissionPipe.prmRemainderPreserves"; attribute :>> scope="Two distinct contexts; concrete no-carry cursor subset and conditional emitter"; }
part binding4:BindingRow { attribute :>> actionName="emission_pipe_refinement.initText"; attribute :>> lemma="EmissionPipe.initTextPreserves"; attribute :>> scope="Two distinct contexts; concrete no-carry cursor subset and conditional emitter"; }
part binding5:BindingRow { attribute :>> actionName="emission_pipe_refinement.gloPrefix"; attribute :>> lemma="EmissionPipe.gloPrefixPreserves"; attribute :>> scope="Two distinct contexts; concrete no-carry cursor subset and conditional emitter"; }
part binding6:BindingRow { attribute :>> actionName="emission_pipe_refinement.scalarDispatch"; attribute :>> lemma="EmissionPipe.scalarDispatchPreserves"; attribute :>> scope="Two distinct contexts; concrete no-carry cursor subset and conditional emitter"; }
part binding7:BindingRow { attribute :>> actionName="emission_pipe_refinement.namedEffect"; attribute :>> lemma="EmissionPipe.namedEffectPreserves"; attribute :>> scope="Two distinct contexts; concrete no-carry cursor subset and conditional emitter"; }
part binding8:BindingRow { attribute :>> actionName="emission_pipe_refinement.customRaw"; attribute :>> lemma="EmissionPipe.customRawPreserves"; attribute :>> scope="Two distinct contexts; concrete no-carry cursor subset and conditional emitter"; }
part binding9:BindingRow { attribute :>> actionName="emission_pipe_refinement.replaceEntry"; attribute :>> lemma="EmissionPipe.replaceEntryPreserves"; attribute :>> scope="Two distinct contexts; concrete no-carry cursor subset and conditional emitter"; }
part binding10:BindingRow { attribute :>> actionName="emission_pipe_refinement.unknownEffect"; attribute :>> lemma="EmissionPipe.unknownEffectPreserves"; attribute :>> scope="Two distinct contexts; concrete no-carry cursor subset and conditional emitter"; }
part binding11:BindingRow { attribute :>> actionName="emission_pipe_refinement.ioAbort"; attribute :>> lemma="EmissionPipe.ioAbortPreserves"; attribute :>> scope="Two distinct contexts; concrete no-carry cursor subset and conditional emitter"; }
part binding12:BindingRow { attribute :>> actionName="emission_pipe_refinement.attest"; attribute :>> lemma="EmissionPipe.attestPreserves"; attribute :>> scope="Two distinct contexts; concrete no-carry cursor subset and conditional emitter"; }
part binding13:BindingRow { attribute :>> actionName="emission_pipe_refinement.issue"; attribute :>> lemma="EmissionPipe.issuePreserves"; attribute :>> scope="Two distinct contexts; concrete no-carry cursor subset and conditional emitter"; }
part binding14:BindingRow { attribute :>> actionName="emission_pipe_refinement.second"; attribute :>> lemma="EmissionPipe.secondPreserves"; attribute :>> scope="Two distinct contexts; concrete no-carry cursor subset and conditional emitter"; }
part binding15:BindingRow { attribute :>> actionName="emission_pipe_refinement.omitSecond"; attribute :>> lemma="EmissionPipe.omitSecondPreserves"; attribute :>> scope="Two distinct contexts; concrete no-carry cursor subset and conditional emitter"; }
part binding16:BindingRow { attribute :>> actionName="emission_pipe_refinement.pause"; attribute :>> lemma="EmissionPipe.pausePreserves"; attribute :>> scope="Two distinct contexts; concrete no-carry cursor subset and conditional emitter"; }
part binding17:BindingRow { attribute :>> actionName="emission_pipe_refinement.readChunk"; attribute :>> lemma="EmissionPipe.readChunkPreserves"; attribute :>> scope="Two distinct contexts; concrete no-carry cursor subset and conditional emitter"; }
part binding18:BindingRow { attribute :>> actionName="emission_pipe_refinement.advanceReader"; attribute :>> lemma="EmissionPipe.advanceReaderPreserves"; attribute :>> scope="Two distinct contexts; concrete no-carry cursor subset and conditional emitter"; }
part binding19:BindingRow { attribute :>> actionName="emission_pipe_refinement.exposeWriter"; attribute :>> lemma="EmissionPipe.exposeWriterPreserves"; attribute :>> scope="Two distinct contexts; concrete no-carry cursor subset and conditional emitter"; }
part binding20:BindingRow { attribute :>> actionName="emission_pipe_refinement.consumeWriter"; attribute :>> lemma="EmissionPipe.consumeWriterPreserves"; attribute :>> scope="Two distinct contexts; concrete no-carry cursor subset and conditional emitter"; }
part binding21:BindingRow { attribute :>> actionName="emission_pipe_refinement.resume"; attribute :>> lemma="EmissionPipe.resumePreserves"; attribute :>> scope="Two distinct contexts; concrete no-carry cursor subset and conditional emitter"; }
part binding22:BindingRow { attribute :>> actionName="emission_pipe_refinement.publish"; attribute :>> lemma="EmissionPipe.publishPreserves"; attribute :>> scope="Two distinct contexts; concrete no-carry cursor subset and conditional emitter"; }
part binding23:BindingRow { attribute :>> actionName="emission_pipe_refinement.appendTail"; attribute :>> lemma="EmissionPipe.appendTailPreserves"; attribute :>> scope="Two distinct contexts; concrete no-carry cursor subset and conditional emitter"; }
part binding24:BindingRow { attribute :>> actionName="emission_pipe_refinement.finish"; attribute :>> lemma="EmissionPipe.finishPreserves"; attribute :>> scope="Two distinct contexts; concrete no-carry cursor subset and conditional emitter"; }
part binding25:BindingRow { attribute :>> actionName="emission_pipe_refinement.installNew"; attribute :>> lemma="EmissionPipe.installNewPreserves"; attribute :>> scope="Two distinct contexts; concrete no-carry cursor subset and conditional emitter"; }
part def ProofRow { attribute key:String; attribute lemma:String; }
part proof0:ProofRow { attribute :>> key="steps"; attribute :>> lemma="EmissionPipe.stepPreserves"; }
part proof1:ProofRow { attribute :>> key="reachable"; attribute :>> lemma="EmissionPipe.reachableSafe"; }
part proof2:ProofRow { attribute :>> key="epoch"; attribute :>> lemma="EmissionPipe.permitNeedsEpoch"; }
part proof3:ProofRow { attribute :>> key="pending"; attribute :>> lemma="EmissionPipe.pendingConserved"; }
part proof4:ProofRow { attribute :>> key="saved-index"; attribute :>> lemma="EmissionPipe.resumeLoadsSavedIndex"; }
part proof5:ProofRow { attribute :>> key="buffer"; attribute :>> lemma="EmissionPipe.resumeKeepsPhysicalBuffer"; }
part proof6:ProofRow { attribute :>> key="scalar"; attribute :>> lemma="EmissionPipe.scalarExcludesSpecial"; }
part proof7:ProofRow { attribute :>> key="canonical"; attribute :>> lemma="EmissionPipeAlgebra.secondUnderNamedWriters"; }
part proof8:ProofRow { attribute :>> key="rebase"; attribute :>> lemma="EmissionPipeAlgebra.rebasePending"; }
part proof9:ProofRow { attribute :>> key="publish"; attribute :>> lemma="EmissionPipeAlgebra.publishPending"; }
part proof10:ProofRow { attribute :>> key="tail"; attribute :>> lemma="EmissionPipeAlgebra.tailFitsFresh"; }
part def MigrationRow { attribute key:String; attribute producerAnchor:String; attribute consumerAnchor:String; attribute actionName:String; attribute lemma:String; }
part migration0:MigrationRow { attribute :>> key="first-output"; attribute :>> producerAnchor="first"; attribute :>> consumerAnchor="display"; attribute :>> actionName="emission_pipe_refinement.prmRemainder"; attribute :>> lemma="EmissionPipe.prmRemainderPreserves"; }
part migration1:MigrationRow { attribute :>> key="init-text"; attribute :>> producerAnchor="cinit-producer"; attribute :>> consumerAnchor="cinit-write"; attribute :>> actionName="emission_pipe_refinement.initText"; attribute :>> lemma="EmissionPipe.initTextPreserves"; }
part migration2:MigrationRow { attribute :>> key="scalar"; attribute :>> producerAnchor="display-api"; attribute :>> consumerAnchor="var"; attribute :>> actionName="emission_pipe_refinement.scalarDispatch"; attribute :>> lemma="EmissionPipe.scalarExcludesSpecial"; }
part migration3:MigrationRow { attribute :>> key="reader"; attribute :>> producerAnchor="read-char"; attribute :>> consumerAnchor="no-carry"; attribute :>> actionName="emission_pipe_refinement.advanceReader"; attribute :>> lemma="EmissionPipeAlgebra.rebasePending"; }
part migration4:MigrationRow { attribute :>> key="publish"; attribute :>> producerAnchor="drain"; attribute :>> consumerAnchor="publish"; attribute :>> actionName="emission_pipe_refinement.publish"; attribute :>> lemma="EmissionPipeAlgebra.publishPending"; }
part migration5:MigrationRow { attribute :>> key="replay"; attribute :>> producerAnchor="capture"; attribute :>> consumerAnchor="substring"; attribute :>> actionName="emission_pipe_refinement.resume"; attribute :>> lemma="EmissionPipe.resumeLoadsSavedIndex"; }
part migration6:MigrationRow { attribute :>> key="retire"; attribute :>> producerAnchor="resource"; attribute :>> consumerAnchor="second"; attribute :>> actionName="emission_pipe_refinement.issue"; attribute :>> lemma="EmissionPipe.permitNeedsEpoch"; }
part def InventoryRow { attribute key:String; attribute path:String; attribute pattern:String; attribute count:String; attribute scope:String; }
part inventory0:InventoryRow { attribute :>> key="direct-resource-write-in-hook"; attribute :>> path="vendor/gambit/gsc/_gscdebug.scm"; attribute :>> pattern="targ-use-glo|targ-rsrc-"; attribute :>> count="0"; attribute :>> scope="Lexical absence only, indirect handlers not closed"; }
part inventory1:InventoryRow { attribute :>> key="debug-load"; attribute :>> path="vendor/gambit/gsc/igsc.scm"; attribute :>> pattern="\"_gscdebug\""; attribute :>> count="1"; attribute :>> scope="Explicit debug loader entry, not all compiler configurations"; }
part def PolicyRow { attribute key:String; attribute writerClass:String; attribute routeClass:String; attribute assumptions:String; attribute firstExpected:String; attribute secondExpected:String; attribute scope:String; }
part policy0:PolicyRow { attribute :>> key="current"; attribute :>> writerClass="named-only"; attribute :>> routeClass="default-emitter"; attribute :>> assumptions=""; attribute :>> firstExpected="false"; attribute :>> secondExpected="false"; attribute :>> scope="Synthetic sufficient assumptions only; route evidence cannot silently cross contexts"; }
part policy1:PolicyRow { attribute :>> key="synthetic-default-qualified"; attribute :>> writerClass="named-only"; attribute :>> routeClass="default-emitter"; attribute :>> assumptions="first-retained;same-entry;canonical-writers;formatter-profile-current;restore-settled;registration-closed;borrowers-drained;captures-retired;fault-equivalence;legal-entry-qualified;output-equivalence;default-interval-qualified"; attribute :>> firstExpected="false"; attribute :>> secondExpected="true"; attribute :>> scope="Synthetic sufficient assumptions only; route evidence cannot silently cross contexts"; }
part policy2:PolicyRow { attribute :>> key="synthetic-debug-only"; attribute :>> writerClass="named-only"; attribute :>> routeClass="debug-pipe"; attribute :>> assumptions="first-retained;same-entry;canonical-writers;formatter-profile-current;restore-settled;registration-closed;borrowers-drained;captures-retired;fault-equivalence;legal-entry-qualified;output-equivalence;cursor-refinement-qualified"; attribute :>> firstExpected="false"; attribute :>> secondExpected="false"; attribute :>> scope="Synthetic sufficient assumptions only; route evidence cannot silently cross contexts"; }
part policy3:PolicyRow { attribute :>> key="synthetic-debug-bridged"; attribute :>> writerClass="named-only"; attribute :>> routeClass="debug-pipe"; attribute :>> assumptions="first-retained;same-entry;canonical-writers;formatter-profile-current;restore-settled;registration-closed;borrowers-drained;captures-retired;fault-equivalence;legal-entry-qualified;output-equivalence;cursor-refinement-qualified;emission-bridge-qualified"; attribute :>> firstExpected="false"; attribute :>> secondExpected="true"; attribute :>> scope="Synthetic sufficient assumptions only; route evidence cannot silently cross contexts"; }
part policy4:PolicyRow { attribute :>> key="synthetic-debug-cursor-gap"; attribute :>> writerClass="named-only"; attribute :>> routeClass="debug-pipe"; attribute :>> assumptions="first-retained;same-entry;canonical-writers;formatter-profile-current;restore-settled;registration-closed;borrowers-drained;captures-retired;fault-equivalence;legal-entry-qualified;output-equivalence;emission-bridge-qualified"; attribute :>> firstExpected="false"; attribute :>> secondExpected="false"; attribute :>> scope="Synthetic sufficient assumptions only; route evidence cannot silently cross contexts"; }
part policy5:PolicyRow { attribute :>> key="synthetic-handler-gap"; attribute :>> writerClass="named-only"; attribute :>> routeClass="default-emitter"; attribute :>> assumptions="first-retained;same-entry;canonical-writers;formatter-profile-current;restore-settled;registration-closed;borrowers-drained;captures-retired;legal-entry-qualified;output-equivalence;default-interval-qualified"; attribute :>> firstExpected="false"; attribute :>> secondExpected="false"; attribute :>> scope="Synthetic sufficient assumptions only; route evidence cannot silently cross contexts"; }
part policy6:PolicyRow { attribute :>> key="synthetic-epoch-gap"; attribute :>> writerClass="named-only"; attribute :>> routeClass="default-emitter"; attribute :>> assumptions="first-retained;canonical-writers;formatter-profile-current;restore-settled;registration-closed;borrowers-drained;captures-retired;fault-equivalence;legal-entry-qualified;output-equivalence;default-interval-qualified"; attribute :>> firstExpected="false"; attribute :>> secondExpected="false"; attribute :>> scope="Synthetic sufficient assumptions only; route evidence cannot silently cross contexts"; }
part policy7:PolicyRow { attribute :>> key="synthetic-live-root"; attribute :>> writerClass="named-only"; attribute :>> routeClass="default-emitter"; attribute :>> assumptions="first-retained;same-entry;canonical-writers;formatter-profile-current;restore-settled;registration-closed;borrowers-drained;fault-equivalence;legal-entry-qualified;output-equivalence;default-interval-qualified"; attribute :>> firstExpected="false"; attribute :>> secondExpected="false"; attribute :>> scope="Synthetic sufficient assumptions only; route evidence cannot silently cross contexts"; }
part def SliceRow { attribute key:String; attribute path:String; attribute beginNeedle:String; attribute endNeedle:String; attribute callNeedle:String; attribute matchIndex:String; attribute actionName:String; attribute lemma:String; }
part slice0:SliceRow { attribute :>> key="two-passes"; attribute :>> path="vendor/gambit/gsc/_t-c-1.scm"; attribute :>> beginNeedle="(define (targ-dump-mod objs c-inits sym-list key-list)"; attribute :>> endNeedle="(targ-code* '(\"BEGIN_MOD_SYM_KEY\"))"; attribute :>> callNeedle="(def-mod-prm-glo \"DEF_MOD_GLO\")"; attribute :>> matchIndex="0"; attribute :>> actionName="emission_pipe_refinement.second"; attribute :>> lemma="EmissionPipe.secondPreserves"; }
part slice1:SliceRow { attribute :>> key="display"; attribute :>> path="vendor/gambit/gsc/_t-c-1.scm"; attribute :>> beginNeedle="(define (targ-display-no-line-info x)"; attribute :>> endNeedle="(define (targ-macro-definition name value)"; attribute :>> callNeedle="(display x targ-port)"; attribute :>> matchIndex="0"; attribute :>> actionName="emission_pipe_refinement.scalarDispatch"; attribute :>> lemma="EmissionPipe.scalarExcludesSpecial"; }
part slice2:SliceRow { attribute :>> key="device-writer"; attribute :>> path="vendor/gambit/lib/_io.scm"; attribute :>> beginNeedle="(define-prim (##make-device-port"; attribute :>> endNeedle=";;; Implementation of vector ports."; attribute :>> callNeedle="(##wr we obj)"; attribute :>> matchIndex="0"; attribute :>> actionName="emission_pipe_refinement.scalarDispatch"; attribute :>> lemma="EmissionPipe.scalarDispatchPreserves"; }
part slice3:SliceRow { attribute :>> key="read-rebase"; attribute :>> path="vendor/gambit/lib/_io.scm"; attribute :>> beginNeedle="(define (,',vect-rbuf-fill port want block?)"; attribute :>> endNeedle="(define (,',vect-wbuf-drain port)"; attribute :>> callNeedle="(if (##fx= vect-rlo vect-rhi)"; attribute :>> matchIndex="0"; attribute :>> actionName="emission_pipe_refinement.advanceReader"; attribute :>> lemma="EmissionPipeAlgebra.rebasePending"; }
part slice4:SliceRow { attribute :>> key="publish-current"; attribute :>> path="vendor/gambit/lib/_io.scm"; attribute :>> beginNeedle="(define (,',vect-wbuf-drain port)"; attribute :>> endNeedle="(define (name port)"; attribute :>> callNeedle="(,',macro-vect-port-whi-set! port 0)"; attribute :>> matchIndex="0"; attribute :>> actionName="emission_pipe_refinement.publish"; attribute :>> lemma="EmissionPipeAlgebra.publishPending"; }
part slice5:SliceRow { attribute :>> key="reenter-loop"; attribute :>> path="vendor/gambit/lib/_io.scm"; attribute :>> beginNeedle="(define-prim (##write-substring str start end port)"; attribute :>> endNeedle="(define-prim (write-substring"; attribute :>> callNeedle="(loop i)"; attribute :>> matchIndex="0"; attribute :>> actionName="emission_pipe_refinement.resume"; attribute :>> lemma="EmissionPipe.resumeLoadsSavedIndex"; }
part history:GambitAssuranceRouting::ModelNeed { ref part :>> owner=GambitAssuranceRelations::modelUse2; attribute :>> obligationId="EP-history"; attribute :>> kind="interleaving"; attribute :>> subjectPath="dev/refactoring/modern-c/models/quint/emission_pipe_refinement.qnt"; attribute :>> subjectScope="18 histories, six negative controls; two independent source contexts"; attribute :>> premise="C23 source/formal research only; no runtime implementation/native tests"; }
part induction:GambitAssuranceRouting::ModelNeed { ref part :>> owner=GambitAssuranceRelations::modelUse2; attribute :>> obligationId="EP-induction"; attribute :>> kind="induction"; attribute :>> subjectPath="dev/refactoring/modern-c/models/lean/EmissionPipe.lean"; attribute :>> subjectScope="Actual projected actions preserve pending/epoch/index/identity invariants"; attribute :>> premise="C23 source/formal research only; no runtime implementation/native tests"; }
part algebra:GambitAssuranceRouting::ModelNeed { ref part :>> owner=GambitAssuranceRelations::modelUse2; attribute :>> obligationId="EP-algebra"; attribute :>> kind="induction"; attribute :>> subjectPath="dev/refactoring/modern-c/models/lean/EmissionPipeAlgebra.lean"; attribute :>> subjectScope="Named writer value law, pressure and coordinate conservation"; attribute :>> premise="C23 source/formal research only; no runtime implementation/native tests"; }
part projection:GambitAssuranceRouting::ModelNeed { ref part :>> owner=GambitAssuranceRelations::modelUse2; attribute :>> obligationId="EP-projection"; attribute :>> kind="restricted-projection"; attribute :>> subjectPath="dev/refactoring/modern-c/models/lean/EmissionPipeAst.lean"; attribute :>> subjectScope="Actual typed IR identity/field/operator/roster checks; extractor trusted"; attribute :>> premise="C23 source/formal research only; no runtime implementation/native tests"; }
part source:GambitAssuranceRouting::ModelNeed { ref part :>> owner=GambitAssuranceRelations::modelUse2; attribute :>> obligationId="EP-source"; attribute :>> kind="source-refinement"; attribute :>> subjectPath="dev/refactoring/modern-c/emission-pipe-refinement-design.org"; attribute :>> subjectScope="General carry-over, exact FIFO identity, generated root maps, interrupt closure and fixnum bounds OPEN"; attribute :>> premise="C23 source/formal research only; no runtime implementation/native tests"; }
part exceptions:GambitAssuranceRouting::ModelNeed { ref part :>> owner=GambitAssuranceRelations::modelUse2; attribute :>> obligationId="EP-exceptions"; attribute :>> kind="exception-equivalence"; attribute :>> subjectPath="dev/refactoring/modern-c/emission-pipe-refinement-design.org"; attribute :>> subjectScope="Default I/O-handler, async effects, exception/output prefix and emit-position mapping OPEN"; attribute :>> premise="C23 source/formal research only; no runtime implementation/native tests"; }
part platform:GambitAssuranceRouting::ModelNeed { ref part :>> owner=GambitAssuranceRelations::modelUse2; attribute :>> obligationId="EP-platform"; attribute :>> kind="c23-platform-qualification"; attribute :>> subjectPath="dev/refactoring/modern-c/language-baseline-design.org"; attribute :>> subjectScope="Native publication/lifetime and matching compiler artifact OPEN"; attribute :>> premise="C23 source/formal research only; no runtime implementation/native tests"; }
part emission:GambitAssuranceRouting::ModelNeed { ref part :>> owner=GambitAssuranceRelations::modelUse2; attribute :>> obligationId="EP-emission"; attribute :>> kind="emitter-fidelity"; attribute :>> subjectPath="dev/refactoring/modern-c/emission-pipe-refinement-design.org"; attribute :>> subjectScope="Full emitted C/ModuleSpec equality and qualified interval receipt OPEN"; attribute :>> premise="C23 source/formal research only; no runtime implementation/native tests"; }
part source32:SourceRow { attribute :>> key="compile-entry"; attribute :>> path="vendor/gambit/gsc/_gsclib.scm"; attribute :>> needle="(c#cf filename-or-source"; attribute :>> obligation="Actual compile-file-to-target invokes c#cf; no output-timeout registration here"; }
part source33:SourceRow { attribute :>> key="front-entry"; attribute :>> path="vendor/gambit/gsc/_front.scm"; attribute :>> needle="(define cf #f)"; attribute :>> obligation="cf installs compiler diagnostic escape channel, not a general dynamic I/O handler"; }
part source34:SourceRow { attribute :>> key="gc-register"; attribute :>> path="vendor/gambit/lib/_kernel.scm"; attribute :>> needle="(define-prim (##add-gc-interrupt-job! thunk)"; attribute :>> obligation="Real job producer API; which closure is installed during emission remains open"; }
part source35:SourceRow { attribute :>> key="peer-prime"; attribute :>> path="vendor/gambit/lib/_io.scm"; attribute :>> needle="(define-prim (##peek-char1 port)"; attribute :>> obligation="After escape, peek primes initial empty reader to first published chunk without consuming a character"; }
part source36:SourceRow { attribute :>> key="width-query"; attribute :>> path="vendor/gambit/lib/_io.scm"; attribute :>> needle="(##output-port-width port)"; attribute :>> obligation="Writeenv construction queries port width; device failure may invoke dynamic I/O handler before character output"; }
part claim4:ClaimRow { attribute :>> key="opaque-effect"; attribute :>> mechanism="unknownEffect drops the source resource-value correspondence; demand becomes last-known only"; attribute :>> condition="unknown=true admits any actual callback write; no certificate can be issued"; attribute :>> result="Model does not assume unknown callbacks leave metadata unchanged"; attribute :>> gap="Full source effect/callback reflection remains unissued"; }
}
