package GambitOrderedSynchronization {
  private import ScalarValues::*;
  ref part mailboxWriter:GambitMailboxPublication::Responsibility=GambitMailboxPublication::queue;
  ref part rootConsumer:GambitMailboxPublication::Responsibility=GambitMailboxPublication::roots;
  attribute sourceLock:String="evidence/research/ordered-sync/initialization/source.lock.json";
  attribute profile:String="evidence/fixtures/gerbil-bazel-build-profile/profile.json";
  attribute scope:String="Ticket/primitive lock ownership, collective fixed-slot publication and physical GC stop/resume; Scheme shared mailbox values and multi-shot continuations remain unchanged";
  attribute storage:String="Naturally aligned Scheme/native word storage, GCC/Clang ordered builtins. This is a documented compiler-extension refinement, not a claim that ordinary Scheme slots have ISO _Atomic declared types";
  attribute formalBoundary:String="Existing continuation QNT covers its finite root/permit histories; existing Lean covers issued-view relocation algebra. Neither is a weak-memory or FIFO proof. No additional QNT/Lean or transferred theorem claim";
  attribute commitAllowed:Boolean=false;
  part def Responsibility { attribute id:String; attribute source:String; attribute anchor:String; attribute invariant:String; attribute retirement:String; attribute cost:String; }
  part word:Responsibility { attribute :>> id="ordered-word"; attribute :>> source="vendor/gambit/include/gambit.h.in"; attribute :>> anchor="___WORD_LOAD_ACQUIRE"; attribute :>> invariant="Every concurrent ticket/stamp access uses one ordered service. Native acquire loads/release stores or RMWs; legacy backends conservatively use full RMW/mutex operations. Exclusive INIT never reads indeterminate storage"; attribute :>> retirement="Volatile polling as synchronization authority"; attribute :>> cost="Native wait uses acquire load; legacy read may require full RMW. No extra Scheme word or heap override"; }
  part ticket:Responsibility { attribute :>> id="ticket-owner"; attribute :>> source="vendor/gambit/include/gambit.h.in"; attribute :>> anchor="___TICKETLOCK_LOCK2"; attribute :>> invariant="Relaxed fetch reserves a unique encoded ticket; acquire reads the prior owner's release increment before entry. Trylock acquires current then atomically reserves next. Concurrent tickets must be fewer than the modulo namespace"; attribute :>> retirement="Duplicated debug/release volatile current reads and implicit full-fence ownership assumptions"; attribute :>> cost="Same two RMWs per lock/unlock; reserve becomes relaxed, handoff becomes release; no measured throughput or fairness bound"; }
  part slot:Responsibility { attribute :>> id="collective-slot"; attribute :>> source="vendor/gambit/include/gambit.h.in"; attribute :>> anchor="___SYNC_SLOT_ACK"; attribute :>> invariant="Fixed SPSC slot: payload write precedes READY release; acquire precedes complete copy; EMPTY release follows copy; next producer acquire of EMPTY grants overwrite. Same stamp values may recur under SPSC coherence and exclusive lifetime"; attribute :>> retirement="Separate sync_id0/1/2 and sync_op0/1/2 fields, early reset before payload copy"; attribute :>> cost="Three fixed slots per PSTATE, no identity table or allocation per round; 64-bit slot size must be measured"; }
  part waiting:Responsibility { attribute :>> id="predicate-wait"; attribute :>> source="vendor/gambit/lib/setup.c"; attribute :>> anchor="SYNC_RECEIVE"; attribute :>> invariant="Recipient mutex serializes predicate check and wait registration; publication and ACK broadcast because three predicates share one CV. Payload copy completes before acknowledgement; blocked producer retains its local operation"; attribute :>> retirement="SYNC_INIT_MSG, SYNC_GET_MSG and SYNC_SEND_MSG split protocol"; attribute :>> cost="Receiver adds one native mutex pair and broadcast per message; producer already used the recipient mutex, signal becomes broadcast. Existing2000-spin threshold unchanged"; }
  part stop:Responsibility { attribute :>> id="physical-stop"; attribute :>> source="vendor/gambit/lib/memory/collection-round.inc"; attribute :>> anchor="___GC_ROOTS_FROZEN"; attribute :>> invariant="Complete context roots and frozen phase precede upward release. Tree acquire/release propagation joins all member writes before scanning. Final collective joins all repairs before resume. A memory fence alone does not stop a writer"; attribute :>> retirement="GC phase visibility relying on volatile sync flags"; attribute :>> cost="No additional GC barrier round or mailbox lock in the collector; actual membership and physical writer exclusion remain required"; }
  part emulation:Responsibility { attribute :>> id="legacy-arithmetic"; attribute :>> source="vendor/gambit/lib/os_thread.c"; attribute :>> anchor="___emulated_fetch_and_add_word"; attribute :>> invariant="Mutex-protected emulated fetch-add wraps through unsigned word arithmetic; no signed-overflow assumption. Win32 and POSIX backend runtime qualification remains separate"; attribute :>> retirement="Signed-overflow increment in emulated word counter"; attribute :>> cost="Conservative fallback may be more expensive; existing empty emulated standalone fence is not used to justify this protocol"; }
  part def Transfer { ref part origin:Responsibility; ref part destination:Responsibility; attribute condition:String; }
  part lockHandoff:Transfer { ref part :>> origin=word; ref part :>> destination=ticket; attribute :>> condition="Release current-ticket write is read by acquire admission; ordinary protected queue data follows that edge"; }
  part slotHandoff:Transfer { ref part :>> origin=word; ref part :>> destination=slot; attribute :>> condition="Release READY/acquire read protects payload; release EMPTY/acquire observation protects reuse after copy"; }
  part wake:Transfer { ref part :>> origin=slot; ref part :>> destination=waiting; attribute :>> condition="Stamp owns visibility; recipient mutex and shared-CV broadcast own waiting, without extending deadlines"; }
  part stopHandoff:Transfer { ref part :>> origin=waiting; ref part :>> destination=stop; attribute :>> condition="Upward arrivals and downward result form the root-stop and resume happens-before cuts; membership stays fixed for that collective"; }
  part def Obligation { attribute id:String; attribute method:String; attribute program:String; attribute criterion:String; }
  part source:Obligation { attribute :>> id="source-ordering"; attribute :>> method="source-refinement"; attribute :>> program="vendor/gambit/include/gambit.h.in"; attribute :>> criterion="Real callers use ordered service; no legacy sync fields/macros; copy-before-ACK; no collector mailbox acquisition; conditional release/acquire and SPSC coherence proof"; }
  part kernel:Obligation { attribute :>> id="kernel-native"; attribute :>> method="native-kernel"; attribute :>> program="vendor/gambit/tests/ordered-sync.c"; attribute :>> criterion="Actual ticket/slot macros,16384 locked updates and publications, trylock and wrap, measured fixed-slot layout; finite observation only"; }
  part fallback:Obligation { attribute :>> id="kernel-legacy"; attribute :>> method="native-kernel-legacy"; attribute :>> program="vendor/gambit/tests/ordered-sync.c"; attribute :>> criterion="Same GCC fixture with forced conservative word backend; no claim of Win32/POSIX emulated runtime coverage"; }
  part emitted:Obligation { attribute :>> id="emitted-orders"; attribute :>> method="compiler-output"; attribute :>> program="vendor/gambit/tests/ordered-sync.c"; attribute :>> criterion="Bound actual preprocessor backend and LLVM IR/assembly to compiler hashes; acquire/release instructions or IR orders, no inference from timing"; }
  part nativeStop:Obligation { attribute :>> id="mailbox-stop"; attribute :>> method="native-scheme"; attribute :>> program="vendor/gambit/tests/smp/gc/mailbox-epoch-handoff.scm"; attribute :>> criterion="Four blocked senders, completed GC while mailbox permit is held,128 shared messages and subsequent collections; no scanner mailbox lock"; }
  part regression:Obligation { attribute :>> id="semantic-regression"; attribute :>> method="native-scheme-suite"; attribute :>> program="vendor/gambit/tests/smp/campaign.scm"; attribute :>> criterion="Exact-source two-pass bootstrap, current named cases including full map multi-shot and dynamic-wind, no heap/wait expansion; historical failures retained"; }
  part def OpenBoundary { attribute id:String; attribute condition:String; }
  part debug:OpenBoundary { attribute :>> id="debug-history"; attribute :>> condition="Debug lock core uses ordered words, but concurrent diagnostic-ring entries are not an authoritative trace and need a separate ownership redesign"; }
  part platforms:OpenBoundary { attribute :>> id="other-backends"; attribute :>> condition="Win32, non-GCC POSIX emulation,32-bit and no-thread runtime qualification remain open; no profile-only pass closes them"; }
  part ownership:OpenBoundary { attribute :>> id="unknown-owner"; attribute :>> condition="Unknown join or writer-stop outcome does not authorize slot reinitialization, membership reuse or root release. Independent worker exit and full carrier retirement remain canonical open obligations"; }
}
