package GambitModuleSpecHandleMigration { private import ScalarValues::*;
part def SourceRow { attribute key:String; attribute path:String; attribute needle:String; attribute obligation:String; }
part source0:SourceRow { attribute :>> key="front-placeholder"; attribute :>> path="vendor/gambit/gsc/_front.scm"; attribute :>> needle="#f ;; space for foreign pointer to ___module_struct"; attribute :>> obligation="Semantic descriptor has no complete native manifest"; }
part source1:SourceRow { attribute :>> key="front-native-main"; attribute :>> path="vendor/gambit/gsc/_front.scm"; attribute :>> needle="(car module-procs) ;; module main"; attribute :>> obligation="Scheme thunk identity must remain rooted and owned"; }
part source2:SourceRow { attribute :>> key="dump-capture"; attribute :>> path="vendor/gambit/gsc/_t-c-1.scm"; attribute :>> needle="(c-inits (c-intf-inits c-intf))"; attribute :>> obligation="Native init snippets remain opaque unless qualified"; }
part source3:SourceRow { attribute :>> key="dump-clear"; attribute :>> path="vendor/gambit/gsc/_t-c-1.scm"; attribute :>> needle="(c-intf-inits-set! c-intf '())"; attribute :>> obligation="Freeze must occur after ownership transfer from mutable interface"; }
part source4:SourceRow { attribute :>> key="scan-work"; attribute :>> path="vendor/gambit/gsc/_t-c-1.scm"; attribute :>> needle="(queue-get! targ-prc-objs-to-scan)"; attribute :>> obligation="Discover generated procedure closure before freezing resource view"; }
part source5:SourceRow { attribute :>> key="descriptor-reachable"; attribute :>> path="vendor/gambit/gsc/_t-c-1.scm"; attribute :>> needle="(targ-use-obj module-descr)"; attribute :>> obligation="Descriptor is part of emitted object graph"; }
part source6:SourceRow { attribute :>> key="late-c-objs"; attribute :>> path="vendor/gambit/gsc/_t-c-1.scm"; attribute :>> needle="(map (lambda (x) (cons (car x) (targ-use-obj (cdr x)))) c-objs)"; attribute :>> obligation="Late object registration precedes heap-dump snapshot"; }
part source7:SourceRow { attribute :>> key="leaf-resources"; attribute :>> path="vendor/gambit/gsc/_t-c-1.scm"; attribute :>> needle="(define (targ-heap-dump filename c-decls c-inits c-objs module-descr linker-name)"; attribute :>> obligation="Single immutable leaf view must drive C and ModuleSpec"; }
part source8:SourceRow { attribute :>> key="label-count"; attribute :>> path="vendor/gambit/gsc/_t-c-1.scm"; attribute :>> needle="(targ-define-count \"LBLCOUNT\" targ-lbl-alloc)"; attribute :>> obligation="Count emitted from actual allocation table; zero is not no member"; }
part source9:SourceRow { attribute :>> key="ofd-count"; attribute :>> path="vendor/gambit/gsc/_t-c-1.scm"; attribute :>> needle="(targ-define-count \"OFDCOUNT\" ofd-count)"; attribute :>> obligation="Frame metadata coverage tied to actual emitted procedure list"; }
part source10:SourceRow { attribute :>> key="native-dump"; attribute :>> path="vendor/gambit/gsc/_t-c-1.scm"; attribute :>> needle="(targ-dump-mod prm-list c-inits sym-list key-list)"; attribute :>> obligation="Native hooks belong to leaf even absent Scheme-visible descriptor"; }
part source11:SourceRow { attribute :>> key="link-header"; attribute :>> path="vendor/gambit/gsc/_t-c-1.scm"; attribute :>> needle="(equal? (car info) (compiler-version))"; attribute :>> obligation="Existing linker metadata identity check not full content/ABI seal"; }
part source12:SourceRow { attribute :>> key="mod-entries"; attribute :>> path="vendor/gambit/gsc/_t-c-1.scm"; attribute :>> needle="(append-lists (map targ-mod-mods-and-flags input-mods))"; attribute :>> obligation="Complete declared children differ from supply-name set"; }
part source13:SourceRow { attribute :>> key="supply-dedup"; attribute :>> path="vendor/gambit/gsc/_t-c-1.scm"; attribute :>> needle="(targ-set-of"; attribute :>> obligation="Supply name dedup is not native image dedup"; }
part source14:SourceRow { attribute :>> key="flag-merge"; attribute :>> path="vendor/gambit/gsc/_t-c-1.scm"; attribute :>> needle="(append flags1 flags2)"; attribute :>> obligation="Preserve inherited flags and ordered semantics"; }
part source15:SourceRow { attribute :>> key="extension-old"; attribute :>> path="vendor/gambit/gsc/_t-c-1.scm"; attribute :>> needle="(append-lists (map targ-mod-mods-and-flags (cdr input-mods)))"; attribute :>> obligation="Extension old inputs remain dependency owners; physical image resolution OPEN"; }
part source16:SourceRow { attribute :>> key="link-order"; attribute :>> path="vendor/gambit/gsc/_t-c-1.scm"; attribute :>> needle="(append old-mods-and-flags new-mods-and-flags)"; attribute :>> obligation="Preserve all ordered effects while membership set can deduplicate"; }
part source17:SourceRow { attribute :>> key="preload-flags"; attribute :>> path="vendor/gambit/gsc/_t-c-1.scm"; attribute :>> needle="\"DEF_LNK_NOPRELOAD\""; attribute :>> obligation="Preload false does not remove lifetime dependency"; }
part source18:SourceRow { attribute :>> key="native-snippets"; attribute :>> path="vendor/gambit/gsc/_t-c-1.scm"; attribute :>> needle="    c-inits)"; attribute :>> obligation="Arbitrary C init cannot yield a complete effect manifest by counts alone"; }
part source19:SourceRow { attribute :>> key="module-emission"; attribute :>> path="vendor/gambit/include/gambit.h.in"; attribute :>> needle="#define ___BEGIN_MOD_SYM_KEY"; attribute :>> obligation="ABI emitter constructs actual module record from counts/resources"; }
part source20:SourceRow { attribute :>> key="module-return"; attribute :>> path="vendor/gambit/include/gambit.h.in"; attribute :>> needle="return (___mod_or_lnk)&___module_descr;"; attribute :>> obligation="Native identity currently raw address"; }
part source21:SourceRow { attribute :>> key="linkfile-return"; attribute :>> path="vendor/gambit/include/gambit.h.in"; attribute :>> needle="return (___mod_or_lnk)&___linkfile_descr;"; attribute :>> obligation="Link graph identity and image ownership are distinct"; }
part source22:SourceRow { attribute :>> key="old-import"; attribute :>> path="vendor/gambit/include/gambit.h.in"; attribute :>> needle="#define ___DEF_OLD_LNK(id)"; attribute :>> obligation="OLD declares imported linker; not a loader image proof"; }
part source23:SourceRow { attribute :>> key="new-link"; attribute :>> path="vendor/gambit/include/gambit.h.in"; attribute :>> needle="#define ___DEF_NEW_LNK(id)"; attribute :>> obligation="NEW versus OLD must not be inferred as unique OS image membership"; }
part source24:SourceRow { attribute :>> key="preload-zero"; attribute :>> path="vendor/gambit/include/gambit.h.in"; attribute :>> needle="#define ___DEF_LNK_NOPRELOAD(id)"; attribute :>> obligation="Generated graph carries flag zero but still stores linker edge"; }
part source25:SourceRow { attribute :>> key="linker-exec"; attribute :>> path="vendor/gambit/lib/setup.c"; attribute :>> needle="mol = linker (___GSTATE);"; attribute :>> obligation="Own provisional loader operation before invoking executable resolver"; }
part source26:SourceRow { attribute :>> key="zero-label"; attribute :>> path="vendor/gambit/lib/setup.c"; attribute :>> needle="if (module->lblcount > 0)"; attribute :>> obligation="Returned vector is a subset; native hook runs outside branch"; }
part source27:SourceRow { attribute :>> key="permanent-wrapper"; attribute :>> path="vendor/gambit/lib/setup.c"; attribute :>> needle="NULL, /* allocate as permanent object */"; attribute :>> obligation="Permanent raw wrapper is not ordinary handle finalization"; }
part source28:SourceRow { attribute :>> key="raw-publication"; attribute :>> path="vendor/gambit/lib/setup.c"; attribute :>> needle="___VECTORELEM(descr, ___MODULE_DESCR_MODULE_STRUCT) = module_scmobj;"; attribute :>> obligation="Migration source for stable identity and legacy retention"; }
part source29:SourceRow { attribute :>> key="setup-hook"; attribute :>> path="vendor/gambit/lib/setup.c"; attribute :>> needle="return module->setup_mod ();"; attribute :>> obligation="Initialization order/effects cannot be erased by dedup"; }
part source30:SourceRow { attribute :>> key="loaded-sentinel"; attribute :>> path="vendor/gambit/lib/setup.c"; attribute :>> needle="mol->linkfile.version = -1;"; attribute :>> obligation="Error after setup does not prove absence of effects"; }
part source31:SourceRow { attribute :>> key="init-raw-reader"; attribute :>> path="vendor/gambit/lib/_kernel.scm"; attribute :>> needle="___CAST(___module_struct*,___FOREIGN_PTR_FIELD(___ARG1))->init_mod"; attribute :>> obligation="Must replace actual blind native entry on controlled route"; }
part source32:SourceRow { attribute :>> key="registry-wrapper"; attribute :>> path="vendor/gambit/lib/_kernel.scm"; attribute :>> needle="(macro-make-module module-ref module-descr)"; attribute :>> obligation="Distinct wrappers share descriptor but have independent stage cells"; }
part source33:SourceRow { attribute :>> key="supply-register"; attribute :>> path="vendor/gambit/lib/_kernel.scm"; attribute :>> needle="(##register-module-descr! module-ref module-descr)"; attribute :>> obligation="Repeated supply refs must preserve lookup and stage identity"; }
part source34:SourceRow { attribute :>> key="registry-remove"; attribute :>> path="vendor/gambit/lib/_kernel.scm"; attribute :>> needle="(and x (##set-car! x #f))"; attribute :>> obligation="Cell removal alone does not prove alias/root detachment"; }
part source35:SourceRow { attribute :>> key="stage-native-before"; attribute :>> path="vendor/gambit/lib/_kernel.scm"; attribute :>> needle="(macro-module-stage-set! module 1)"; attribute :>> obligation="Logical stage written before native call, not success receipt"; }
part source36:SourceRow { attribute :>> key="stage-scheme-before"; attribute :>> path="vendor/gambit/lib/_kernel.scm"; attribute :>> needle="(macro-module-stage-set! module 2)"; attribute :>> obligation="Logical stage written before Scheme thunk, not success receipt"; }
part source37:SourceRow { attribute :>> key="scheme-init-thunk"; attribute :>> path="vendor/gambit/lib/_kernel.scm"; attribute :>> needle="((macro-module-descr-thunk module-descr))"; attribute :>> obligation="Code dependency includes Scheme main and captured continuation"; }
part source38:SourceRow { attribute :>> key="module-vector"; attribute :>> path="vendor/gambit/lib/_kernel#.scm"; attribute :>> needle="`(##vector ,module-ref 0 ,module-descr)"; attribute :>> obligation="Do not merge per-ref stage cells while interning native handle"; }
part source39:SourceRow { attribute :>> key="mutable-field"; attribute :>> path="vendor/gambit/lib/_kernel#.scm"; attribute :>> needle="(##define-macro (macro-module-descr-module-struct-set!"; attribute :>> obligation="Generic vector/FFI alias closure remains external"; }
part source40:SourceRow { attribute :>> key="ffi-void-wildcard"; attribute :>> path="vendor/gambit/lib/c_intf.c"; attribute :>> needle="if (src_tags == ___FAL || /* source type == void* */"; attribute :>> obligation="Tag change is not access-control or borrow lifetime"; }
part source41:SourceRow { attribute :>> key="ffi-pointer-read"; attribute :>> path="vendor/gambit/lib/c_intf.c"; attribute :>> needle="*x = ___CAST(void*,___FOREIGN_PTR_FIELD(obj));"; attribute :>> obligation="Generic pointer conversion can escape legacy module address"; }
part source42:SourceRow { attribute :>> key="ffi-address-int"; attribute :>> path="vendor/gambit/lib/_kernel.scm"; attribute :>> needle="___CAST(void*,___FOREIGN_PTR_FIELD(___arg1))));"; attribute :>> obligation="Integer address export cannot be revoked by wrapper rewrite"; }
part source43:SourceRow { attribute :>> key="release-conditional"; attribute :>> path="vendor/gambit/lib/c_intf.c"; attribute :>> needle="if (release_fn != 0)"; attribute :>> obligation="Null release_fn leaves old module pointer unchanged"; }
part source44:SourceRow { attribute :>> key="release-clear"; attribute :>> path="vendor/gambit/lib/c_intf.c"; attribute :>> needle="___FOREIGN_PTR_FIELD(obj) ="; attribute :>> obligation="Clearing wrapper cannot revoke independent copies even with callback"; }
part source45:SourceRow { attribute :>> key="ffi-pointer-store"; attribute :>> path="vendor/gambit/lib/c_intf.c"; attribute :>> needle="___FOREIGN_PTR_FIELD(r) = ___CAST(___SCMOBJ,x);"; attribute :>> obligation="Root protection and native code/data ownership separate"; }
part source46:SourceRow { attribute :>> key="ffi-static-host"; attribute :>> path="vendor/gambit/lib/c_intf.c"; attribute :>> needle="body[-___LABEL_SIZE+___LABEL_HOST]"; attribute :>> obligation="Native function export bypasses ordinary procedure root lifetime"; }
part source47:SourceRow { attribute :>> key="ffi-dynamic-converter"; attribute :>> path="vendor/gambit/lib/c_intf.c"; attribute :>> needle="___make_c_closure (obj, converter)"; attribute :>> obligation="Track converter and proc image owners independently"; }
part source48:SourceRow { attribute :>> key="interpreted-descriptor"; attribute :>> path="vendor/gambit/lib/_module.scm"; attribute :>> needle="(macro-make-module-descr"; attribute :>> obligation="Interpreted path supplies field5 false; no native init must remain no-op"; }
part source49:SourceRow { attribute :>> key="object-register"; attribute :>> path="vendor/gambit/lib/_module.scm"; attribute :>> needle="(##register-module-descrs module-descrs)"; attribute :>> obligation="Actual object-file result enters Scheme registry"; }
part source50:SourceRow { attribute :>> key="callback-descriptor"; attribute :>> path="vendor/gambit/lib/_module.scm"; attribute :>> needle="(macro-module-module-descr mod)"; attribute :>> obligation="Script callback aliases descriptor metadata"; }
part source51:SourceRow { attribute :>> key="vm-early-publish"; attribute :>> path="vendor/gambit/lib/mem.c"; attribute :>> needle="tail->next = ___vms;"; attribute :>> obligation="Topology presence does not settle owner enrollment"; }
part source52:SourceRow { attribute :>> key="dynamic-list-publish"; attribute :>> path="vendor/gambit/lib/os_dyn.c"; attribute :>> needle="p->next = ___dyn_mod.dl_list;"; attribute :>> obligation="Stable operation must own loader handle before setup result"; }
part def InventoryRow { attribute key:String; attribute path:String; attribute pattern:String; attribute count:String; attribute scope:String; }
part inventory0:InventoryRow { attribute :>> key="field5-setter-definition"; attribute :>> path="vendor/gambit/lib/_kernel#.scm"; attribute :>> pattern="\\(##define-macro \\(macro-module-descr-module-struct-set!"; attribute :>> count="1"; attribute :>> scope="Exact lexical scope; no preprocessed whole-program or concrete external module-pointer client closure"; }
part inventory1:InventoryRow { attribute :>> key="named-field5-setter-calls"; attribute :>> path="vendor/gambit/lib/_kernel.scm"; attribute :>> pattern="macro-module-descr-module-struct-set!"; attribute :>> count="0"; attribute :>> scope="Exact lexical scope; no preprocessed whole-program or concrete external module-pointer client closure"; }
part inventory2:InventoryRow { attribute :>> key="pointer-family-raw-reads"; attribute :>> path="vendor/gambit/lib/c_intf.c"; attribute :>> pattern="\\*x = ___CAST\\(void\\*,___FOREIGN_PTR_FIELD\\(obj\\)\\);"; attribute :>> count="4"; attribute :>> scope="Exact lexical scope; no preprocessed whole-program or concrete external module-pointer client closure"; }
part inventory3:InventoryRow { attribute :>> key="wildcard-source"; attribute :>> path="vendor/gambit/lib/c_intf.c"; attribute :>> pattern="if \\(src_tags == ___FAL \\|\\|"; attribute :>> count="1"; attribute :>> scope="Exact lexical scope; no preprocessed whole-program or concrete external module-pointer client closure"; }
part inventory4:InventoryRow { attribute :>> key="address-export"; attribute :>> path="vendor/gambit/lib/_kernel.scm"; attribute :>> pattern="\\(define-prim \\(##foreign-address f\\)"; attribute :>> count="1"; attribute :>> scope="Exact lexical scope; no preprocessed whole-program or concrete external module-pointer client closure"; }
part inventory5:InventoryRow { attribute :>> key="init-direct-cast"; attribute :>> path="vendor/gambit/lib/_kernel.scm"; attribute :>> pattern="___CAST\\(___module_struct\\*,___FOREIGN_PTR_FIELD\\(___ARG1\\)\\)->init_mod"; attribute :>> count="1"; attribute :>> scope="Exact lexical scope; no preprocessed whole-program or concrete external module-pointer client closure"; }
part def ConsumerRow { attribute key:String; attribute callers:String; attribute custody:String; attribute gap:String; }
part consumer0:ConsumerRow { attribute :>> key="leaf-generator"; attribute :>> callers="front module-procs -> targ-dump -> use-obj -> heap-dump"; attribute :>> custody="LeafSpec owns generated native storage and code metadata"; attribute :>> gap="Freeze after late object uses; not merely front descriptor"; }
part consumer1:ConsumerRow { attribute :>> key="linker-aggregator"; attribute :>> callers="targ-get-mod -> link-aux -> dump-linkfile"; attribute :>> custody="Ordered edges and inherited flags plus deduplicated identity set"; attribute :>> gap="All child specs and OLD/NEW native placement need qualification"; }
part consumer2:ConsumerRow { attribute :>> key="native-setup"; attribute :>> callers="dynamic_load -> resolver -> setup_modules"; attribute :>> custody="Provisional OperationId holds loader dependency across effects/errors"; attribute :>> gap="No success sentinel or error is a detachment receipt"; }
part consumer3:ConsumerRow { attribute :>> key="init-module"; attribute :>> callers="init-modules wrapper stage -> init-mod / Scheme thunk"; attribute :>> custody="Per-ref stage identity and code/root lease"; attribute :>> gap="Before-call stage is not proof of successful completion"; }
part consumer4:ConsumerRow { attribute :>> key="registry-aliases"; attribute :>> callers="make-module -> supply refs -> program-descr / callback"; attribute :>> custody="Shared descriptor identity; distinct ref wrappers/stage cells"; attribute :>> gap="Registry deletion leaves old descriptor and raw wrapper references"; }
part consumer5:ConsumerRow { attribute :>> key="ffi-generic"; attribute :>> callers="foreign-address and SCMOBJ_to_POINTER/STRUCT/UNION/TYPE"; attribute :>> custody="Legacy raw export retains image; controlled handle is separate representation"; attribute :>> gap="Actual converter/address mechanisms established; specific external module-pointer client OPEN"; }
part consumer6:ConsumerRow { attribute :>> key="ffi-functions"; attribute :>> callers="c-define host or make_c_closure proc/converter"; attribute :>> custody="Proc root plus converter/code lease plus native registry drain"; attribute :>> gap="Direct native bypass cannot be sandboxed by a tag"; }
part consumer7:ConsumerRow { attribute :>> key="interpreted"; attribute :>> callers="get-from-source descriptor field5 false -> init-mod and thunk"; attribute :>> custody="Preserve no-native-init branch and Scheme main roots"; attribute :>> gap="Do not force interpreted modules into native image membership"; }
part def ClaimRow { attribute key:String; attribute mechanism:String; attribute condition:String; attribute result:String; attribute gap:String; }
part claim0:ClaimRow { attribute :>> key="complete-spec"; attribute :>> mechanism="Single frozen leaf view drives both ModuleSpec and modern C ABI emission"; attribute :>> condition="Every resource code label FrameSpec hook export and opaque snippet classified"; attribute :>> result="Avoid drift between native output and ownership metadata"; attribute :>> gap="Current generator emits no such complete sealed ModuleSpec"; }
part claim1:ClaimRow { attribute :>> key="aggregate"; attribute :>> mechanism="Compose declared child manifests and separate ordered edge plan"; attribute :>> condition="Input artifact digests child specs flags and actual native placement agree"; attribute :>> result="No zero-label or nonpreloaded child omitted"; attribute :>> gap="Native dynamic dependencies and open C effects require explicit adapter"; }
part claim2:ClaimRow { attribute :>> key="opaque-handle"; attribute :>> mechanism="Separate interned native identity from Scheme wrapper/ref stage identity"; attribute :>> condition="Actual init reader raw exporters and ABI upgraded coherently"; attribute :>> result="No generic foreign conversion on controlled handle"; attribute :>> gap="Arbitrary unsafe C remains trusted; legacy behavior retained by pinning"; }
part claim3:ClaimRow { attribute :>> key="root-publish"; attribute :>> mechanism="Keep candidate rooted until stable registry/root acceptance known"; attribute :>> condition="RootRegistry covers relevant processors and collector moves"; attribute :>> result="Publish-before-source-release prevents root gap"; attribute :>> gap="Actual scanner and C11 source refinement OPEN"; }
part claim4:ClaimRow { attribute :>> key="operation"; attribute :>> mechanism="Idempotent reply retrieval is distinct from semantic reexecution"; attribute :>> condition="Stable operation exists before effects; same OperationId on delivery retry"; attribute :>> result="Lost reply cannot justify repeating native init"; attribute :>> gap="Nested continuation multi-shot intent identity remains source obligation"; }
part claim5:ClaimRow { attribute :>> key="close-unknown"; attribute :>> mechanism="Accepted preclose registration settles under original coordinator"; attribute :>> condition="Close shares authority with enrollment and native borrowing"; attribute :>> result="Unknown effects/exit retain stable record and image dependencies"; attribute :>> gap="No automatic timeout cleanup or raw alias revocation"; }
part def MemoryRow { attribute key:String; attribute publication:String; attribute consumer:String; attribute gap:String; }
part memory0:MemoryRow { attribute :>> key="freeze"; attribute :>> publication="Private single-writer view after all emission roots registered"; attribute :>> consumer="C and spec read same snapshot; hash all material inputs"; attribute :>> gap="Snapshot canonicalization mutable target tables and exact emission equivalence OPEN"; }
part memory1:MemoryRow { attribute :>> key="publish"; attribute :>> publication="Root candidate; register stable control/root bundle; release-publish applied operation"; attribute :>> consumer="Acquire acknowledgment or query confirms same operation before candidate root drops"; attribute :>> gap="Source atomic publication and RC/nonzero processor scan coverage OPEN"; }
part memory2:MemoryRow { attribute :>> key="borrow"; attribute :>> publication="Reserve image generation lease under same authority as close"; attribute :>> consumer="Resolve module pointer only after accepted reservation; known last use before release"; attribute :>> gap="Uncontrolled native addresses and callback escape cannot be made safe by tags"; }
part memory3:MemoryRow { attribute :>> key="init"; attribute :>> publication="Set logical wrapper stage as source does; track invocation/completion separately"; attribute :>> consumer="Do not hold registry/topology lock across Scheme GC callback or continuation"; attribute :>> gap="Exception completed versus effects rolled back must stay distinct"; }
part memory4:MemoryRow { attribute :>> key="unknown"; attribute :>> publication="Stable external coordinator owns unknown operation and native dependencies"; attribute :>> consumer="No source release after unacknowledged handoff or unknown abort"; attribute :>> gap="VM disappearance and caller abandonment do not delete the record"; }
part def GainRow { attribute key:String; attribute avoided:String; attribute added:String; attribute condition:String; }
part gain0:GainRow { attribute :>> key="single-source"; attribute :>> avoided="Duplicate count/layout/linker discovery across C emitter ownership and incremental service"; attribute :>> added="O(M+E+R+X) sealed spec plus digest/dependency validation"; attribute :>> condition="M members E ordered edges R resource records X exports; no open native effects omitted"; }
part gain1:GainRow { attribute :>> key="incremental"; attribute :>> avoided="Whole-process restart solely for qualified generation replacement"; attribute :>> added="Generation-indexed handles semantic ABI invalidation old-code leases"; attribute :>> condition="Cannot retire generation with captured frame or untracked raw alias"; }
part gain2:GainRow { attribute :>> key="module-entry"; attribute :>> avoided="Repeated whole-VM topology inspection for admitted native access"; attribute :>> added="Short gate and stable handle lookup per borrow"; attribute :>> condition="Local cost below avoided coordination; no measured speedup"; }
part gain3:GainRow { attribute :>> key="reply-retry"; attribute :>> avoided="Potential setup/init reexecution from delivery retry in the planned service"; attribute :>> added="Operation-keyed result record and stable outcome custody"; attribute :>> condition="Same logical operation identity; not an observed existing retry bug; intentional execution not coalesced"; }
part gain4:GainRow { attribute :>> key="memory"; attribute :>> avoided="Unnecessary image retention on fully controlled routes"; attribute :>> added="Roots handle records pending operations and observer cleanup"; attribute :>> condition="Reclaimed bytes ZERO on legacy raw or unknown dependency route"; }
part gain5:GainRow { attribute :>> key="shared-support"; attribute :>> avoided="Separate ad hoc module FFI and GC lifetime supports"; attribute :>> added="Shared RootRegistry lease and release-coordinator contracts"; attribute :>> condition="Modern C can express all mechanisms; Zig marginal net benefit not demonstrated"; }
part def MemberRow { attribute key:String; attribute fields:String; attribute producer:String; attribute lifetime:String; attribute migration:String; }
part member0:MemberRow { attribute :>> key="semantic"; attribute :>> fields="supply demand metadata flags Scheme main"; attribute :>> producer="front module-descr"; attribute :>> lifetime="Identity/phase/exception semantics remain Scheme"; attribute :>> migration="Field5 binding is a separate typed discriminant"; }
part member1:MemberRow { attribute :>> key="leaf"; attribute :>> fields="symbols keys globals constants subtyped objects procedures labels OFD"; attribute :>> producer="targ-heap-dump frozen resources"; attribute :>> lifetime="C tables and Scheme payload roots tied to generation"; attribute :>> migration="Emit ModuleSpec from same frozen resource view"; }
part member2:MemberRow { attribute :>> key="native-effects"; attribute :>> fields="C decls objects inits setup hook FFI export/converter/release code"; attribute :>> producer="c-intf and dump-mod/prc"; attribute :>> lifetime="Opaque code may register dependencies not visible in Scheme graph"; attribute :>> migration="Admit qualified adapter or preserve legacy retained lifetime"; }
part member3:MemberRow { attribute :>> key="link-edges"; attribute :>> fields="all mods inherited flags OLD NEW preload order"; attribute :>> producer="targ-link/get-mod/dump-linkfile"; attribute :>> lifetime="Ownership union differs from ordered execution plan"; attribute :>> migration="Input digests bind child manifests; native image placement separate"; }
part member4:MemberRow { attribute :>> key="image-placement"; attribute :>> fields="native module -> actual ImageId/generation and dependencies"; attribute :>> producer="loader/link adapter"; attribute :>> lifetime="OLD/NEW or supply names alone do not prove OS ownership"; attribute :>> migration="Seal only after actual group and imported dependencies reconciled"; }
part member5:MemberRow { attribute :>> key="runtime-identity"; attribute :>> fields="ModuleHandle OperationId OwnerKey BorrowId"; attribute :>> producer="runtime coordinator outside unloadable module"; attribute :>> lifetime="Stable control record may outlive VM and OS image"; attribute :>> migration="No raw module address in ordinary Scheme handle representation"; }
part member6:MemberRow { attribute :>> key="roots"; attribute :>> fields="candidate bundle published payload captured frames callbacks"; attribute :>> producer="GC RootRegistry and actual semantic users"; attribute :>> lifetime="Registry removal is only one alias deletion"; attribute :>> migration="Retire payload only with complete root and native detach receipt"; }
part def ContractRow { attribute fromNode:String; attribute toNode:String; attribute custody:String; }
part contract0:ContractRow { attribute :>> fromNode="Scheme-semantics"; attribute :>> toNode="frozen-emission-view"; attribute :>> custody="Keep ref identities stages source and exceptions in Scheme"; }
part contract1:ContractRow { attribute :>> fromNode="frozen-emission-view"; attribute :>> toNode="modern-C-output"; attribute :>> custody="C"; }
part contract2:ContractRow { attribute :>> fromNode="frozen-emission-view"; attribute :>> toNode="leaf-ModuleSpec"; attribute :>> custody="Spec"; }
part contract3:ContractRow { attribute :>> fromNode="leaf-ModuleSpec"; attribute :>> toNode="aggregate-member-manifest"; attribute :>> custody="All child specs dependencies digests plus ordered flag edges"; }
part contract4:ContractRow { attribute :>> fromNode="aggregate-member-manifest"; attribute :>> toNode="qualified-image-group"; attribute :>> custody="Loader resolves physical membership; native adapters cover opaque effects"; }
part contract5:ContractRow { attribute :>> fromNode="legacy-raw-alias"; attribute :>> toNode="retained-generation"; attribute :>> custody="Raw exports retain generation"; }
part contract6:ContractRow { attribute :>> fromNode="aggregate-member-manifest"; attribute :>> toNode="stable-operation-owner"; attribute :>> custody="Reserve before loader open and executable linker discovery"; }
part contract7:ContractRow { attribute :>> fromNode="candidate-root"; attribute :>> toNode="published-root-bundle"; attribute :>> custody="Known target acceptance precedes source root release"; }
part contract8:ContractRow { attribute :>> fromNode="stable-operation-owner"; attribute :>> toNode="published-root-bundle"; attribute :>> custody="Commit identity root and reply record under same authority"; }
part contract9:ContractRow { attribute :>> fromNode="published-root-bundle"; attribute :>> toNode="ModuleHandle"; attribute :>> custody="Stable interned native identity; Scheme wrappers retain separate stages"; }
part contract10:ContractRow { attribute :>> fromNode="ModuleHandle"; attribute :>> toNode="guarded-init-and-FFI"; attribute :>> custody="Lease before pointer resolution; preserve interpreted false binding"; }
part contract11:ContractRow { attribute :>> fromNode="guarded-init-and-FFI"; attribute :>> toNode="close-and-drain"; attribute :>> custody="Accepted preclose calls settle; fresh entry denied"; }
part contract12:ContractRow { attribute :>> fromNode="stable-operation-owner"; attribute :>> toNode="unknown-outcome-custodian"; attribute :>> custody="Lost reply queries same operation; unknown effects retain dependencies"; }
part contract13:ContractRow { attribute :>> fromNode="unknown-outcome-custodian"; attribute :>> toNode="retained-generation"; attribute :>> custody="Unknown debt survives VM exit"; }
part contract14:ContractRow { attribute :>> fromNode="close-and-drain"; attribute :>> toNode="global-unload-prerequisites"; attribute :>> custody="All aliases roots frame metadata native users and reservations detached"; }
part def BindingRow { attribute actionName:String; attribute lemma:String; attribute scope:String; }
part binding0:BindingRow { attribute :>> actionName="module_spec_handle.recordLeaf"; attribute :>> lemma="ModuleHandle.recordLeafPreserves"; attribute :>> scope="Actual typed IR step; complete source model and C11 realization OPEN"; }
part binding1:BindingRow { attribute :>> actionName="module_spec_handle.recordEdges"; attribute :>> lemma="ModuleHandle.recordEdgesPreserves"; attribute :>> scope="Actual typed IR step; complete source model and C11 realization OPEN"; }
part binding2:BindingRow { attribute :>> actionName="module_spec_handle.declareOpaque"; attribute :>> lemma="ModuleHandle.declareOpaquePreserves"; attribute :>> scope="Actual typed IR step; complete source model and C11 realization OPEN"; }
part binding3:BindingRow { attribute :>> actionName="module_spec_handle.qualifyNative"; attribute :>> lemma="ModuleHandle.qualifyNativePreserves"; attribute :>> scope="Actual typed IR step; complete source model and C11 realization OPEN"; }
part binding4:BindingRow { attribute :>> actionName="module_spec_handle.sealSpec"; attribute :>> lemma="ModuleHandle.sealSpecPreserves"; attribute :>> scope="Actual typed IR step; complete source model and C11 realization OPEN"; }
part binding5:BindingRow { attribute :>> actionName="module_spec_handle.reserve"; attribute :>> lemma="ModuleHandle.reservePreserves"; attribute :>> scope="Actual typed IR step; complete source model and C11 realization OPEN"; }
part binding6:BindingRow { attribute :>> actionName="module_spec_handle.protectCandidate"; attribute :>> lemma="ModuleHandle.protectCandidatePreserves"; attribute :>> scope="Actual typed IR step; complete source model and C11 realization OPEN"; }
part binding7:BindingRow { attribute :>> actionName="module_spec_handle.startEffects"; attribute :>> lemma="ModuleHandle.startEffectsPreserves"; attribute :>> scope="Actual typed IR step; complete source model and C11 realization OPEN"; }
part binding8:BindingRow { attribute :>> actionName="module_spec_handle.commit"; attribute :>> lemma="ModuleHandle.commitPreserves"; attribute :>> scope="Actual typed IR step; complete source model and C11 realization OPEN"; }
part binding9:BindingRow { attribute :>> actionName="module_spec_handle.acknowledge"; attribute :>> lemma="ModuleHandle.acknowledgePreserves"; attribute :>> scope="Actual typed IR step; complete source model and C11 realization OPEN"; }
part binding10:BindingRow { attribute :>> actionName="module_spec_handle.retryReply"; attribute :>> lemma="ModuleHandle.retryReplyPreserves"; attribute :>> scope="Actual typed IR step; complete source model and C11 realization OPEN"; }
part binding11:BindingRow { attribute :>> actionName="module_spec_handle.dropCandidate"; attribute :>> lemma="ModuleHandle.dropCandidatePreserves"; attribute :>> scope="Actual typed IR step; complete source model and C11 realization OPEN"; }
part binding12:BindingRow { attribute :>> actionName="module_spec_handle.abortBeforeEffects"; attribute :>> lemma="ModuleHandle.abortBeforeEffectsPreserves"; attribute :>> scope="Actual typed IR step; complete source model and C11 realization OPEN"; }
part binding13:BindingRow { attribute :>> actionName="module_spec_handle.unknownReserved"; attribute :>> lemma="ModuleHandle.unknownReservedPreserves"; attribute :>> scope="Actual typed IR step; complete source model and C11 realization OPEN"; }
part binding14:BindingRow { attribute :>> actionName="module_spec_handle.unknownCommitted"; attribute :>> lemma="ModuleHandle.unknownCommittedPreserves"; attribute :>> scope="Actual typed IR step; complete source model and C11 realization OPEN"; }
part binding15:BindingRow { attribute :>> actionName="module_spec_handle.exposeRaw"; attribute :>> lemma="ModuleHandle.exposeRawPreserves"; attribute :>> scope="Actual typed IR step; complete source model and C11 realization OPEN"; }
part binding16:BindingRow { attribute :>> actionName="module_spec_handle.borrowNative"; attribute :>> lemma="ModuleHandle.borrowNativePreserves"; attribute :>> scope="Actual typed IR step; complete source model and C11 realization OPEN"; }
part binding17:BindingRow { attribute :>> actionName="module_spec_handle.returnBorrow"; attribute :>> lemma="ModuleHandle.returnBorrowPreserves"; attribute :>> scope="Actual typed IR step; complete source model and C11 realization OPEN"; }
part binding18:BindingRow { attribute :>> actionName="module_spec_handle.beginNativeInit"; attribute :>> lemma="ModuleHandle.beginNativeInitPreserves"; attribute :>> scope="Actual typed IR step; complete source model and C11 realization OPEN"; }
part binding19:BindingRow { attribute :>> actionName="module_spec_handle.returnNativeInit"; attribute :>> lemma="ModuleHandle.returnNativeInitPreserves"; attribute :>> scope="Actual typed IR step; complete source model and C11 realization OPEN"; }
part binding20:BindingRow { attribute :>> actionName="module_spec_handle.beginSchemeInit"; attribute :>> lemma="ModuleHandle.beginSchemeInitPreserves"; attribute :>> scope="Actual typed IR step; complete source model and C11 realization OPEN"; }
part binding21:BindingRow { attribute :>> actionName="module_spec_handle.returnSchemeInit"; attribute :>> lemma="ModuleHandle.returnSchemeInitPreserves"; attribute :>> scope="Actual typed IR step; complete source model and C11 realization OPEN"; }
part binding22:BindingRow { attribute :>> actionName="module_spec_handle.failInit"; attribute :>> lemma="ModuleHandle.failInitPreserves"; attribute :>> scope="Actual typed IR step; complete source model and C11 realization OPEN"; }
part binding23:BindingRow { attribute :>> actionName="module_spec_handle.removeAlias"; attribute :>> lemma="ModuleHandle.removeAliasPreserves"; attribute :>> scope="Actual typed IR step; complete source model and C11 realization OPEN"; }
part binding24:BindingRow { attribute :>> actionName="module_spec_handle.publishAlias"; attribute :>> lemma="ModuleHandle.publishAliasPreserves"; attribute :>> scope="Actual typed IR step; complete source model and C11 realization OPEN"; }
part binding25:BindingRow { attribute :>> actionName="module_spec_handle.close"; attribute :>> lemma="ModuleHandle.closePreserves"; attribute :>> scope="Actual typed IR step; complete source model and C11 realization OPEN"; }
part binding26:BindingRow { attribute :>> actionName="module_spec_handle.retirePayload"; attribute :>> lemma="ModuleHandle.retirePayloadPreserves"; attribute :>> scope="Actual typed IR step; complete source model and C11 realization OPEN"; }
part binding27:BindingRow { attribute :>> actionName="module_spec_handle.issue"; attribute :>> lemma="ModuleHandle.issuePreserves"; attribute :>> scope="Actual typed IR step; complete source model and C11 realization OPEN"; }
part binding28:BindingRow { attribute :>> actionName="module_spec_handle.permit"; attribute :>> lemma="ModuleHandle.permitPreserves"; attribute :>> scope="Actual typed IR step; complete source model and C11 realization OPEN"; }
part binding29:BindingRow { attribute :>> actionName="module_spec_handle.rejectLate"; attribute :>> lemma="ModuleHandle.rejectLatePreserves"; attribute :>> scope="Actual typed IR step; complete source model and C11 realization OPEN"; }
part def ProofRow { attribute key:String; attribute lemma:String; }
part proof0:ProofRow { attribute :>> key="all-step"; attribute :>> lemma="ModuleHandle.stepPreserves"; }
part proof1:ProofRow { attribute :>> key="reachable"; attribute :>> lemma="ModuleHandle.reachableSafe"; }
part proof2:ProofRow { attribute :>> key="permit-local"; attribute :>> lemma="ModuleHandle.permitMigrationReady"; }
part proof3:ProofRow { attribute :>> key="native-capability"; attribute :>> lemma="ModuleHandle.sealedNativeCoverage"; }
part proof4:ProofRow { attribute :>> key="reply"; attribute :>> lemma="ModuleHandle.replyRetryDoesNotRerun"; }
part proof5:ProofRow { attribute :>> key="raw"; attribute :>> lemma="ModuleHandle.facadeDoesNotRevokeRaw"; }
part proof6:ProofRow { attribute :>> key="declared-union"; attribute :>> lemma="ModuleHandleComposition.declaredChildCovered"; }
part proof7:ProofRow { attribute :>> key="order"; attribute :>> lemma="ModuleHandleComposition.orderedEffectsPreserved"; }
part proof8:ProofRow { attribute :>> key="duplicate-effect"; attribute :>> lemma="ModuleHandleComposition.duplicateEffectsRemain"; }
part proof9:ProofRow { attribute :>> key="prior-raw-denial"; attribute :>> lemma="ModuleHandleComposition.rawMigrationBlocksPriorPermit"; }
part def MigrationRow { attribute key:String; attribute producerAnchor:String; attribute consumerAnchor:String; attribute actionName:String; attribute lemma:String; }
part migration0:MigrationRow { attribute :>> key="generator-to-native"; attribute :>> producerAnchor="label-count"; attribute :>> consumerAnchor="module-emission"; attribute :>> actionName="module_spec_handle.recordLeaf"; attribute :>> lemma="ModuleHandle.recordLeafPreserves"; }
part migration1:MigrationRow { attribute :>> key="raw-to-guarded-init"; attribute :>> producerAnchor="raw-publication"; attribute :>> consumerAnchor="init-raw-reader"; attribute :>> actionName="module_spec_handle.beginNativeInit"; attribute :>> lemma="ModuleHandle.beginNativeInitPreserves"; }
part migration2:MigrationRow { attribute :>> key="descriptor-to-registry"; attribute :>> producerAnchor="front-placeholder"; attribute :>> consumerAnchor="registry-wrapper"; attribute :>> actionName="module_spec_handle.commit"; attribute :>> lemma="ModuleHandle.commitPreserves"; }
part migration3:MigrationRow { attribute :>> key="pointer-to-controlled-FFI"; attribute :>> producerAnchor="raw-publication"; attribute :>> consumerAnchor="ffi-pointer-read"; attribute :>> actionName="module_spec_handle.borrowNative"; attribute :>> lemma="ModuleHandle.borrowNativePreserves"; }
part migration4:MigrationRow { attribute :>> key="root-handoff"; attribute :>> producerAnchor="ffi-pointer-store"; attribute :>> consumerAnchor="object-register"; attribute :>> actionName="module_spec_handle.dropCandidate"; attribute :>> lemma="ModuleHandle.dropCandidatePreserves"; }
part migration5:MigrationRow { attribute :>> key="setup-unknown"; attribute :>> producerAnchor="dynamic-list-publish"; attribute :>> consumerAnchor="loaded-sentinel"; attribute :>> actionName="module_spec_handle.unknownReserved"; attribute :>> lemma="ModuleHandle.unknownReservedPreserves"; }
part def SeamRow { ref part producer:GambitAssuranceRelations::ComponentModelUse; ref part consumer:GambitAssuranceRelations::ComponentModelUse; attribute contract:String; attribute actionName:String; attribute lemma:String; }
part seam0:SeamRow { ref part :>> producer=GambitAssuranceRelations::modelUse2; ref part :>> consumer=GambitAssuranceRelations::modelUse6; attribute :>> contract="ModuleSpec-native-members"; attribute :>> actionName="module_spec_handle.sealSpec"; attribute :>> lemma="ModuleHandle.sealedNativeCoverage"; }
part seam1:SeamRow { ref part :>> producer=GambitAssuranceRelations::modelUse4; ref part :>> consumer=GambitAssuranceRelations::modelUse6; attribute :>> contract="root-publication-and-native-borrow"; attribute :>> actionName="module_spec_handle.commit"; attribute :>> lemma="ModuleHandle.commitPreserves"; }
part seam2:SeamRow { ref part :>> producer=GambitAssuranceRelations::modelUse5; ref part :>> consumer=GambitAssuranceRelations::modelUse6; attribute :>> contract="old-frame-and-raw-retention"; attribute :>> actionName="module_spec_handle.exposeRaw"; attribute :>> lemma="ModuleHandleComposition.rawMigrationBlocksPriorPermit"; }
part seam3:SeamRow { ref part :>> producer=GambitAssuranceRelations::modelUse3; ref part :>> consumer=GambitAssuranceRelations::modelUse6; attribute :>> contract="complete-payload-root-retirement"; attribute :>> actionName="module_spec_handle.retirePayload"; attribute :>> lemma="ModuleHandle.permitMigrationReady"; }
part history:GambitAssuranceRouting::ModelNeed { ref part :>> owner=GambitAssuranceRelations::modelUse6; attribute :>> obligationId="MH-history"; attribute :>> kind="interleaving"; attribute :>> subjectPath="dev/refactoring/modern-c/models/quint/module_spec_handle.qnt"; attribute :>> subjectScope="Rooted commit close unknown effects raw export init completion and delivery retry histories"; attribute :>> premise="Research only; no native or source admission"; }
part induction:GambitAssuranceRouting::ModelNeed { ref part :>> owner=GambitAssuranceRelations::modelUse6; attribute :>> obligationId="MH-induction"; attribute :>> kind="induction"; attribute :>> subjectPath="dev/refactoring/modern-c/models/lean/ModuleHandle.lean"; attribute :>> subjectScope="All extracted sequential steps; alias counts represent externally complete user coverage"; attribute :>> premise="Research only; no native or source admission"; }
part composition:GambitAssuranceRouting::ModelNeed { ref part :>> owner=GambitAssuranceRelations::modelUse6; attribute :>> obligationId="MH-composition"; attribute :>> kind="induction"; attribute :>> subjectPath="dev/refactoring/modern-c/models/lean/ModuleHandleComposition.lean"; attribute :>> subjectScope="Declared child union ordered effects and prior raw-permit rejection; no native completeness theorem"; attribute :>> premise="Research only; no native or source admission"; }
part projection:GambitAssuranceRouting::ModelNeed { ref part :>> owner=GambitAssuranceRelations::modelUse6; attribute :>> obligationId="MH-projection"; attribute :>> kind="restricted-projection"; attribute :>> subjectPath="dev/refactoring/modern-c/models/lean/ModuleHandleAst.lean"; attribute :>> subjectScope="Full action roster binding IDs state field kinds and restricted typed IR expressions"; attribute :>> premise="Research only; no native or source admission"; }
part source:GambitAssuranceRouting::ModelNeed { ref part :>> owner=GambitAssuranceRelations::modelUse6; attribute :>> obligationId="MH-source"; attribute :>> kind="source-refinement"; attribute :>> subjectPath="dev/refactoring/modern-c/module-spec-handle-migration-design.org"; attribute :>> subjectScope="Complete emitter/input/native manifests per-ref alias closure actual roots and multi-shot refinement OPEN"; attribute :>> premise="Research only; no native or source admission"; }
part platform:GambitAssuranceRouting::ModelNeed { ref part :>> owner=GambitAssuranceRelations::modelUse6; attribute :>> obligationId="MH-platform"; attribute :>> kind="native-memory-order"; attribute :>> subjectPath="dev/refactoring/modern-c/module-spec-handle-migration-design.org"; attribute :>> subjectScope="Concrete C11 authority root scanning native teardown and effective profile refinement OPEN"; attribute :>> premise="Research only; no native or source admission"; }

part claim6:ClaimRow { attribute :>> key="capability-envelope"; attribute :>> mechanism="Sealed static members plus qualified native capability envelope"; attribute :>> condition="All later native dependency creation is mediated before access under the same lifetime authority"; attribute :>> result="Closed parent cannot silently acquire an unaccounted dependency"; attribute :>> gap="Open-world C effects and unmanaged registrations retain the generation; no native envelope proof"; }

part contract15:ContractRow { attribute :>> fromNode="stable-operation-owner"; attribute :>> toNode="qualified-image-group"; attribute :>> custody="Own provisional dependencies while native placement and effects are reconciled"; }
part contract16:ContractRow { attribute :>> fromNode="qualified-image-group"; attribute :>> toNode="published-root-bundle"; attribute :>> custody="Complete group and capability envelope required before publication"; }
}
