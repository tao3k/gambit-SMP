package GambitMailboxPublication {
  private import ScalarValues::*;
  attribute sourceLock:String="evidence/research/mailbox-publication/source.lock.json";
  attribute profile:String="evidence/fixtures/gerbil-bazel-build-profile/profile.json";
  attribute purpose:String="Modern C mutator publication ownership and shared GC reachability; preserve Scheme shared values, selective receive and multi-shot roots";
  attribute formalOwnership:String="Existing CS-SCHEDULE QNT covers continuation safe-point/permit schedules, not mailbox FIFO linearizability. Existing CS-COHERENCE Lean covers authentic issued-view relocation, not queue mutation. Apply these only to their root/continuation preconditions; mailbox source/native obligations remain separate. No additional formal model or transferred theorem claim";
  attribute historicalBoundary:String="Original binary failed expecting32 without recording the received value; source-projected old procedure deterministically observes33 with zero GC; this proves a reachable source defect, not the unrecorded historical schedule";
  attribute budgets:String="64 messages, receive5 seconds, executable30 seconds, existing profile and heap policy; bootstrap600 seconds; no extensions";
  attribute commitAllowed:Boolean=false;
  part def FormalBoundary { attribute id:String; attribute owner:String; attribute artifact:String; attribute declaration:String; attribute scope:String; }
  part scheduleBoundary:FormalBoundary { attribute :>> id="CS-SCHEDULE"; attribute :>> owner="quint"; attribute :>> artifact="dev/architecture/runtime/control/models/quint/continuation_segments.qnt"; attribute :>> declaration="safe"; attribute :>> scope="Existing continuation GC/root/wind/reentry schedules only; no mailbox queue theorem"; }
  part coherenceBoundary:FormalBoundary { attribute :>> id="CS-COHERENCE"; attribute :>> owner="lean"; attribute :>> artifact="dev/architecture/runtime/control/models/lean/ContinuationSegments.lean"; attribute :>> declaration="issuedViewRemainsCoherent"; attribute :>> scope="Authentic issued root-view relocation only; no scheduler/queue theorem"; }
  part def Responsibility { attribute id:String; attribute source:String; attribute anchor:String; attribute invariant:String; attribute retires:String; attribute added:String; }
  part identity:Responsibility { attribute :>> id="identity"; attribute :>> source="vendor/gambit/lib/_thread.scm"; attribute :>> anchor="##thread-mailbox-get!"; attribute :>> invariant="Allocate candidate outside the target thread lock; recheck and publish one mailbox identity under that lock; no nested mailbox permit"; attribute :>> retires="Unsynchronized first lookup and double-check publication"; attribute :>> added="One thread lock/unlock for existing identity; two on cold lookup, losing candidates remain GC owned"; }
  part cell:Responsibility { attribute :>> id="cell"; attribute :>> source="vendor/gambit/lib/_thread.scm"; attribute :>> anchor="##thread-send"; attribute :>> invariant="Detached initialized cons and payload remain caller/frame roots before publication, across heap checks and mutex wait; successful link transfers reachability to mailbox"; attribute :>> retires="Queue node allocation inside mutation permit"; attribute :>> added="Same one cons per message, live across wait; no extra per-message node or identity table"; }
  part queue:Responsibility { attribute :>> id="queue"; attribute :>> source="vendor/gambit/lib/_fifo#.scm"; attribute :>> anchor="macro-fifo-link-tail-cell!"; attribute :>> invariant="Mailbox permit serializes head, tail and cursor; initialized cell link has two pointer stores, no allocation or explicit safe point between stores; failed wait has not modified queue"; attribute :>> retires="Unlocked nonempty extraction and unguarded selective cursor mutation"; attribute :>> added="One mailbox acquire/release per nonempty receive, peek, extract or rewind; existing send already paid this permit"; }
  part roots:Responsibility { attribute :>> id="roots"; attribute :>> source="vendor/gambit/lib/memory/root-origins.inc"; attribute :>> anchor="mark_execution_roots"; attribute :>> invariant="Detached cell is traced through the blocked sender frame; mailbox graph through target thread root; returned payload through receiver frame. Whole physical writer stop remains a prerequisite"; attribute :>> retires="No GC scanner path retired by fixing mutator publication"; attribute :>> added="Native blocked-cell GC witness and generated-frame root refinement; no additional collector lock"; }
  part scan:Responsibility { attribute :>> id="scan"; attribute :>> source="vendor/gambit/lib/memory/object-scanning.inc"; attribute :>> anchor="scan"; attribute :>> invariant="Unique object scan ownership is independent of mailbox mutation ownership; scanner never acquires mailbox permit, preventing stopped-owner wait cycles"; attribute :>> retires="No old scanner retired; duplicate mutation and duplicate scan are separate causal hypotheses"; attribute :>> added="Existing Tail/forwarding/scan protocol unchanged; broader independent-worker obligations remain open"; }
  part timeout:Responsibility { attribute :>> id="timeout"; attribute :>> source="vendor/gambit/lib/_thread.scm"; attribute :>> anchor="##thread-mailbox-next-or-receive"; attribute :>> invariant="First empty observation releases permit before timeout conversion; one absolute timeout reused across wake/relock; recheck prevents lost wakeup; timeout exception occurs after wait releases permit"; attribute :>> retires="Duplicated unlocked and locked receive implementations"; attribute :>> added="Empty initial path unlocks/relocks once for lazy conversion; no deadline reset"; }
  part def Obligation { attribute id:String; attribute method:String; attribute program:String; attribute criterion:String; }
  part counterexample:Obligation { attribute :>> id="source-interleave"; attribute :>> method="source-projection"; attribute :>> program="dev/modeling/tools/project-mailbox-witness.scm"; attribute :>> criterion="Read actual SMP receive AST; replace binding and insert exactly one handoff after next3 read. Old observes33, candidate excludes writer and drains64; GC delta zero in both"; }
  part orderedMessages:Obligation { attribute :>> id="ordered"; attribute :>> method="native-scheme"; attribute :>> program="vendor/gambit/tests/smp/scheduler/mailbox-publication.scm"; attribute :>> criterion="Real built-in receive/send,64 messages, sender and receiver GC; exact candidate runtime source hashes"; }
  part blocked:Obligation { attribute :>> id="blocked-cell"; attribute :>> method="native-scheme"; attribute :>> program="vendor/gambit/tests/smp/scheduler/mailbox-permit-roots.scm"; attribute :>> criterion="Observe sender waiting for exact mailbox mutex, complete GC while permit held, validate returned payload; selective cursor and timeout exception cleanup"; }
  part concurrent:Obligation { attribute :>> id="first-publishers"; attribute :>> method="native-scheme"; attribute :>> program="vendor/gambit/tests/smp/scheduler/mailbox-identity.scm"; attribute :>> criterion="Eight simultaneous first publishers,64 messages, per-origin ordering and original shared payload identity across completed collections"; }
  part baseline:Obligation { attribute :>> id="bounded-controls"; attribute :>> method="native-scheme-history"; attribute :>> program="vendor/gambit/tests/smp/scheduler/publication-evidence.scm"; attribute :>> criterion="Keep all72 historical trials, including original immutable executable and single-processor/no-GC/sender/receiver/both controls; green controls cannot establish historical cause"; }
  part def Transfer { ref part origin:Responsibility; ref part destination:Responsibility; attribute condition:String; }
  part initialized:Transfer { ref part :>> origin=cell; ref part :>> destination=queue; attribute :>> condition="Cell initialized and rooted before permit; two nonallocating stores publish it; no mailbox read/mutation outside permit"; }
  part stopped:Transfer { ref part :>> origin=queue; ref part :>> destination=roots; attribute :>> condition="GC physically stops writers; graph complete at poll/check; roots include blocked sender and target. No mailbox lock acquisition by collector"; }
  part repaired:Transfer { ref part :>> origin=roots; ref part :>> destination=scan; attribute :>> condition="RootTask claims root repair, object scan claims payload; sharing does not grant a second mutator or duplicate scan authority"; }
}
