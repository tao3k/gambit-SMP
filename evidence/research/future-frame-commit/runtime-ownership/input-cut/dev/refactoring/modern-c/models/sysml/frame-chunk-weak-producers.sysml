package GambitFrameChunkWeakProducers { private import ScalarValues::*;
part def Source { attribute key:String; attribute path:String; attribute needle:String; attribute obligation:String; }
part source0:Source { attribute :>> key="copy-header"; attribute :>> path="vendor/gambit/lib/mem.c"; attribute :>> needle="copy_header = alloc;\n          *alloc++ = ___MAKE_HD_WORDS(words, ___sFRAME);"; attribute :>> obligation="Actual frame start before header/RA/payload"; }
part source1:Source { attribute :>> key="copy-size"; attribute :>> path="vendor/gambit/lib/mem.c"; attribute :>> needle="words = fs + ___FRAME_EXTRA_SLOTS;"; attribute :>> obligation="Frame payload words include extra RA"; }
part source2:Source { attribute :>> key="copy-slot"; attribute :>> path="vendor/gambit/lib/mem.c"; attribute :>> needle="ptr = &___FP_STK(alloc,link+1);"; attribute :>> obligation="Copier slot is end minus link plus one"; }
part source3:Source { attribute :>> key="scanner-fp"; attribute :>> path="vendor/gambit/lib/mem.c"; attribute :>> needle="fp += descriptor.fs;"; attribute :>> obligation="Scanner fp uses body plus extra plus fs"; }
part source4:Source { attribute :>> key="scanner-link"; attribute :>> path="vendor/gambit/lib/mem.c"; attribute :>> needle="frame = ___FP_STK(fp,descriptor.link+1);"; attribute :>> obligation="Scanner reads same copied link slot"; }
part source5:Source { attribute :>> key="scanner-hide"; attribute :>> path="vendor/gambit/lib/mem.c"; attribute :>> needle="___FP_SET_STK(fp,descriptor.link+1,___FAL)"; attribute :>> obligation="Overlapping scanner write footprint"; }
part source6:Source { attribute :>> key="local-authority"; attribute :>> path="vendor/gambit/lib/mem.c"; attribute :>> needle="if (alloc_heap_chunk_start != work->local_scan_chunk_)"; attribute :>> obligation="Current explicit chunk ownership"; }
part source7:Source { attribute :>> key="terminator"; attribute :>> path="vendor/gambit/lib/mem.c"; attribute :>> needle="*work->context->mem.alloc_heap_ptr_++ = NULL_CHUNK_LINK;"; attribute :>> obligation="Closed chunk terminator position"; }
part source8:Source { attribute :>> key="chunk-address"; attribute :>> path="vendor/gambit/lib/mem.c"; attribute :>> needle="___WORD *new_tail = alloc_heap_chunk_start-1;"; attribute :>> obligation="Leading link is not object header"; }
part source9:Source { attribute :>> key="section-state"; attribute :>> path="vendor/gambit/lib/mem.c"; attribute :>> needle="___PTRDIFF_T pos = header-the_msections->sections[i]->base-tospace_offset;"; attribute :>> obligation="State identity includes section and tospace"; }
part source10:Source { attribute :>> key="packed-state"; attribute :>> path="vendor/gambit/lib/mem.c"; attribute :>> needle="int shift = 2*(pos % (___WORD_WIDTH/2));"; attribute :>> obligation="Two-bit state shares a machine word"; }
part source11:Source { attribute :>> key="early-ready"; attribute :>> path="vendor/gambit/lib/mem.c"; attribute :>> needle="publish_object_scan (work, copy_header);\n          work->copied_words += words+___SUBTYPED_BODY;"; attribute :>> obligation="Candidate must move frame READY after link seal"; }
part source12:Source { attribute :>> key="tail-owner"; attribute :>> path="vendor/gambit/lib/mem.c"; attribute :>> needle="if (cell != 0) goto again;"; attribute :>> obligation="Tail remains a producer after READY"; }
part source13:Source { attribute :>> key="still-scan"; attribute :>> path="vendor/gambit/lib/mem.c"; attribute :>> needle="scan (work, body, body[-1]);"; attribute :>> obligation="Still path does not claim movable bitmap"; }
part source14:Source { attribute :>> key="fresh-will"; attribute :>> path="vendor/gambit/lib/mem.c"; attribute :>> needle="mark_array (work, body+1, 2); /* scan action and testator */"; attribute :>> obligation="Newly reached weak will creates work"; }
part source15:Source { attribute :>> key="will-decide"; attribute :>> path="vendor/gambit/lib/mem.c"; attribute :>> needle="determine_will_executability (nonexecutable_wills);"; attribute :>> obligation="List classification still fused with retention"; }
part source16:Source { attribute :>> key="repair-exec"; attribute :>> path="vendor/gambit/lib/mem.c"; attribute :>> needle="mark_array (work, tail_exec+___WILL_TESTATOR, 1);"; attribute :>> obligation="Two executable branch occurrences"; }
part source17:Source { attribute :>> key="repair-nonexec"; attribute :>> path="vendor/gambit/lib/mem.c"; attribute :>> needle="mark_array (work, tail_nonexec+___WILL_TESTATOR, 1);"; attribute :>> obligation="Nonexecutable branch also repairs"; }
part source18:Source { attribute :>> key="weak-mode"; attribute :>> path="vendor/gambit/lib/mem.c"; attribute :>> needle="traverse_weak_refs = 1;"; attribute :>> obligation="Worker-local mode must not precede global permission"; }
part source19:Source { attribute :>> key="weak-closure"; attribute :>> path="vendor/gambit/lib/mem.c"; attribute :>> needle="mark_reachable_from_marked (work);\n\n  move_continuation (work);"; attribute :>> obligation="Weak scan drains before stack move"; }
part source20:Source { attribute :>> key="hash-cleanup"; attribute :>> path="vendor/gambit/lib/mem.c"; attribute :>> needle="process_gc_hash_tables (work);"; attribute :>> obligation="Post-weak weak-edge rewrite not new marking"; }
part source21:Source { attribute :>> key="foreign-cleanup"; attribute :>> path="vendor/gambit/lib/mem.c"; attribute :>> needle="___release_foreign\n              ("; attribute :>> obligation="External cleanup callback boundary"; }
part source22:Source { attribute :>> key="strong-roots"; attribute :>> path="vendor/gambit/lib/mem.c"; attribute :>> needle="mark_execution_roots (work,"; attribute :>> obligation="Root/RC production is strong-phase scoped"; }
part source23:Source { attribute :>> key="strong-marker"; attribute :>> path="vendor/gambit/lib/mem.c"; attribute :>> needle="___GC_STRONG_COMPLETE;"; attribute :>> obligation="Local phase label not global closed-work proof"; }
part source24:Source { attribute :>> key="slot-macro"; attribute :>> path="vendor/gambit/include/gambit.h.in"; attribute :>> needle="#define ___FP_STK(fp,fpo)fp[-(fpo)]"; attribute :>> obligation="Actual negative-offset indexing"; }
part source25:Source { attribute :>> key="frame-space"; attribute :>> path="vendor/gambit/include/gambit.h.in"; attribute :>> needle="#define ___FRAME_SPACE(n)___ROUND_TO_MULT((n)+___FRAME_RESERVE,___FRAME_ALIGN)"; attribute :>> obligation="Stack storage includes reserve/alignment"; }
part source26:Source { attribute :>> key="decoder"; attribute :>> path="vendor/gambit/include/gambit.h.in"; attribute :>> needle="frame.fs = internal ? ___RETI_CFS_TO_FS(frame.stored_fs) : frame.stored_fs;"; attribute :>> obligation="RETI stored size differs from physical fs"; }
part source27:Source { attribute :>> key="cas"; attribute :>> path="vendor/gambit/include/gambit.h.in"; attribute :>> needle="__sync_val_compare_and_swap(p,oldval,newval)"; attribute :>> obligation="Legacy GCC implementation branch; not C11 profile qualification"; }
part source28:Source { attribute :>> key="release-callback"; attribute :>> path="vendor/gambit/lib/c_intf.c"; attribute :>> needle="if ((e = release_fn (ptr)) != ___FIX(___NO_ERR))"; attribute :>> obligation="Callback body cannot be bounded from collector source"; }
part source29:Source { attribute :>> key="barrier-wrapper"; attribute :>> path="vendor/gambit/lib/setup.h"; attribute :>> needle="#define BARRIER() barrier_sync_noop (___PSPNC)"; attribute :>> obligation="Native collective selection"; }
part source30:Source { attribute :>> key="barrier-service"; attribute :>> path="vendor/gambit/lib/setup.c"; attribute :>> needle="barrier_sync_op (___PSP &sop);"; attribute :>> obligation="Collective uses sync operation protocol"; }
part def Mapping { attribute key:String; attribute formula:String; attribute premise:String; attribute gap:String; }
part mapping0:Mapping { attribute :>> key="object interval"; attribute :>> formula="H header; body H+1; past H+fs+2"; attribute :>> premise="Extra=1 body=1; positive fs; same allocation"; attribute :>> gap="Pointer provenance/overflow not proved"; }
part mapping1:Mapping { attribute :>> key="copier link"; attribute :>> formula="past-(link+1)"; attribute :>> premise="0<=link<fs; copied stack fs slots"; attribute :>> gap="Descriptor/module lifetime required"; }
part mapping2:Mapping { attribute :>> key="scanner link"; attribute :>> formula="(H+1+1+fs)-(link+1)"; attribute :>> premise="Same physical descriptor; RETI normalized fs"; attribute :>> gap="Stored cfs cannot replace fs"; }
part mapping3:Mapping { attribute :>> key="mixed chunk"; attribute :>> formula="Tile from first header to terminator"; attribute :>> premise="Every ordinary/padding/frame header advances by 1+words"; attribute :>> gap="No unregistered hole or hidden object"; }
part mapping4:Mapping { attribute :>> key="leading marker"; attribute :>> formula="first header - 1"; attribute :>> premise="Not an object header; separate two-bit identity"; attribute :>> gap="State-word CAS still shares neighbouring bits"; }
part mapping5:Mapping { attribute :>> key="closed interval"; attribute :>> formula="[lo,term) objects; term marker; hi=term+1"; attribute :>> premise="All fields within grant; chunk half-open unique"; attribute :>> gap="Marker may not be claimed as object"; }
part mapping6:Mapping { attribute :>> key="local frontier"; attribute :>> formula="Per-object acquired READY before field access"; attribute :>> premise="Local ownership is not a seal receipt"; attribute :>> gap="Closed-chunk model alone does not prove local open frontier"; }
part mapping7:Mapping { attribute :>> key="writer footprint"; attribute :>> formula="Copier link overlaps scanner hide/restore"; attribute :>> premise="All overlapping writes must precede READY"; attribute :>> gap="Tail first field is separately owned and skipped by generic scan"; }
part def Producer { attribute key:String; attribute caller:String; attribute callee:String; attribute family:String; attribute phase:String; attribute gate:String; attribute custody:String; }
part producer0:Producer { attribute :>> key="list-cell"; attribute :>> caller="process_wills"; attribute :>> callee="mark_array"; attribute :>> family="0"; attribute :>> phase="weak"; attribute :>> gate="global decision cut"; attribute :>> custody="Accepted list work retains debt"; }
part producer1:Producer { attribute :>> key="testator-repair"; attribute :>> caller="process_wills"; attribute :>> callee="mark_array"; attribute :>> family="1"; attribute :>> phase="weak"; attribute :>> gate="global decision cut"; attribute :>> custody="Three source branches; executable needle appears twice"; }
part producer2:Producer { attribute :>> key="new-will"; attribute :>> caller="scan"; attribute :>> callee="mark_array"; attribute :>> family="2"; attribute :>> phase="weak"; attribute :>> gate="inherited weak-task permit"; attribute :>> custody="Action/testator for fresh weak will"; }
part producer3:Producer { attribute :>> key="ordinary-and-table"; attribute :>> caller="scan"; attribute :>> callee="mark_array"; attribute :>> family="3"; attribute :>> phase="strong-or-weak"; attribute :>> gate="phase-specific task permit"; attribute :>> custody="Strong-policy hash fields and ordinary fields; weak entries not traced"; }
part producer4:Producer { attribute :>> key="continuation-root"; attribute :>> caller="scan"; attribute :>> callee="mark_captured_continuation"; attribute :>> family="4"; attribute :>> phase="strong-or-weak"; attribute :>> gate="phase-specific task permit"; attribute :>> custody="Frame copy may close/publish chunk"; }
part producer5:Producer { attribute :>> key="captured-existing"; attribute :>> caller="mark_captured_continuation"; attribute :>> callee="mark_array"; attribute :>> family="4"; attribute :>> phase="strong-or-weak"; attribute :>> gate="inherit caller phase"; attribute :>> custody="Heap-backed or END path"; }
part producer6:Producer { attribute :>> key="frame-fields"; attribute :>> caller="mark_frame"; attribute :>> callee="mark_array"; attribute :>> family="4"; attribute :>> phase="strong-or-weak"; attribute :>> gate="inherit scan/capture phase"; attribute :>> custody="Root runs and live RA produce work"; }
part producer7:Producer { attribute :>> key="tail"; attribute :>> caller="mark_array"; attribute :>> callee="goto again"; attribute :>> family="3"; attribute :>> phase="strong-or-weak"; attribute :>> gate="same accepted copy owner"; attribute :>> custody="Owns first field; queue drain does not settle Tail"; }
part producer8:Producer { attribute :>> key="still"; attribute :>> caller="scan_still_objs_to_scan"; attribute :>> callee="scan"; attribute :>> family="5"; attribute :>> phase="strong-or-weak"; attribute :>> gate="phase scan permit"; attribute :>> custody="Still work not covered by movable READY"; }
part producer9:Producer { attribute :>> key="local-chunk"; attribute :>> caller="scan_movable_objs_to_scan"; attribute :>> callee="scan_and_advance"; attribute :>> family="3"; attribute :>> phase="strong-or-weak"; attribute :>> gate="phase permit plus per-object READY"; attribute :>> custody="Local owned frontier still needs seal"; }
part producer10:Producer { attribute :>> key="queued-and-stolen"; attribute :>> caller="scan_complete_heap_chunk"; attribute :>> callee="scan_and_advance"; attribute :>> family="3"; attribute :>> phase="strong-or-weak"; attribute :>> gate="phase permit plus physical coverage"; attribute :>> custody="Origins local FIFO or thief share gate"; }
part producer11:Producer { attribute :>> key="roots-rc"; attribute :>> caller="mark_execution_roots"; attribute :>> callee="mark_rc"; attribute :>> family="excluded"; attribute :>> phase="strong-only"; attribute :>> gate="strong phase must close"; attribute :>> custody="All nonzero contexts and native root writers remain admission premise"; }
part producer12:Producer { attribute :>> key="stack-move"; attribute :>> caller="move_continuation"; attribute :>> callee="raw stack copy"; attribute :>> family="excluded"; attribute :>> phase="after weak closure"; attribute :>> gate="no new mark calls"; attribute :>> custody="Not a weak marking producer in current function"; }
part producer13:Producer { attribute :>> key="hash-resolution"; attribute :>> caller="process_gc_hash_tables"; attribute :>> callee="UNMARKED/forward/delete"; attribute :>> family="excluded"; attribute :>> phase="cleanup"; attribute :>> gate="weak closure barrier"; attribute :>> custody="No mark_array/capture/scan calls in current body"; }
part producer14:Producer { attribute :>> key="foreign-hook"; attribute :>> caller="free_unmarked_still_objs"; attribute :>> callee="___release_foreign"; attribute :>> family="unbounded"; attribute :>> phase="cleanup"; attribute :>> gate="separate external callback admission"; attribute :>> custody="Cannot certify arbitrary release_fn reentry or late work from this inventory"; }
part def Contract { attribute fromNode:String; attribute toNode:String; attribute custody:String; }
part contract0:Contract { attribute :>> fromNode="stack-descriptor"; attribute :>> toNode="copied-span"; attribute :>> custody="Normalize RETI; authenticate fs/link"; }
part contract1:Contract { attribute :>> fromNode="copied-span"; attribute :>> toNode="physical-tile"; attribute :>> custody="No holes; exact header walk including padding"; }
part contract2:Contract { attribute :>> fromNode="physical-tile"; attribute :>> toNode="chunk-seal"; attribute :>> custody="Every overlapping writer closed"; }
part contract3:Contract { attribute :>> fromNode="copier-fixup"; attribute :>> toNode="chunk-seal"; attribute :>> custody="Seal pending predecessor and terminal"; }
part contract4:Contract { attribute :>> fromNode="chunk-seal"; attribute :>> toNode="release-publish"; attribute :>> custody="Marker plus full coverage"; }
part contract5:Contract { attribute :>> fromNode="release-publish"; attribute :>> toNode="acquire-claim"; attribute :>> custody="Object and chunk authorities distinct"; }
part contract6:Contract { attribute :>> fromNode="acquire-claim"; attribute :>> toNode="scanner"; attribute :>> custody="Validate exact epoch and owned interval"; }
part contract7:Contract { attribute :>> fromNode="local-frontier"; attribute :>> toNode="scanner"; attribute :>> custody="Per-object seal also required"; }
part contract8:Contract { attribute :>> fromNode="strong-producers"; attribute :>> toNode="strong-closure"; attribute :>> custody="Private Tail copies roots queued still debt all settled"; }
part contract9:Contract { attribute :>> fromNode="strong-closure"; attribute :>> toNode="classify-all"; attribute :>> custody="Frozen context lists and roster"; }
part contract10:Contract { attribute :>> fromNode="classify-all"; attribute :>> toNode="decision-cut"; attribute :>> custody="All owners including empty acknowledge"; }
part contract11:Contract { attribute :>> fromNode="decision-cut"; attribute :>> toNode="weak-producers"; attribute :>> custody="All six route classes inherit permission"; }
part contract12:Contract { attribute :>> fromNode="weak-producers"; attribute :>> toNode="child-reservation"; attribute :>> custody="Reserve before parent final release"; }
part contract13:Contract { attribute :>> fromNode="child-reservation"; attribute :>> toNode="weak-closure"; attribute :>> custody="Unknown delivery retains existing task"; }
part contract14:Contract { attribute :>> fromNode="weak-closure"; attribute :>> toNode="cleanup"; attribute :>> custody="No new weak roots; external hooks separately admitted"; }
part def Obligation { attribute key:String; attribute status:String; attribute scope:String; attribute gap:String; }
part obligation0:Obligation { attribute :>> key="slot-coordinate"; attribute :>> status="proved-arithmetic"; attribute :>> scope="Copier and scanner same integer slot"; attribute :>> gap="Provenance fs/link and live metadata premises remain"; }
part obligation1:Obligation { attribute :>> key="mixed-interval"; attribute :>> status="proved-conditional"; attribute :>> scope="Arbitrary list of frame ordinary padding spans"; attribute :>> gap="Real header-to-model Tile witness not extracted"; }
part obligation2:Obligation { attribute :>> key="chunk-publication"; attribute :>> status="proved-in-model"; attribute :>> scope="Two frames same physical interval gate"; attribute :>> gap="Real chunk membership all writers local frontier open"; }
part obligation3:Obligation { attribute :>> key="producer-route"; attribute :>> status="source-inventory"; attribute :>> scope="Direct calls reviewed under exact source hash"; attribute :>> gap="Not a C preprocessor/callback whole-program proof"; }
part obligation4:Obligation { attribute :>> key="weak-gate"; attribute :>> status="proved-in-model"; attribute :>> scope="Six route classes and inherited children"; attribute :>> gap="All native route-to-permit mappings unimplemented"; }
part obligation5:Obligation { attribute :>> key="strong-close"; attribute :>> status="open"; attribute :>> scope="No residual private chunk Tail copy root or still work"; attribute :>> gap="Existing idle count is conditional; no full C11 proof"; }
part obligation6:Obligation { attribute :>> key="roster-cut"; attribute :>> status="open"; attribute :>> scope="Same frozen contexts and classification lists"; attribute :>> gap="Physical worker/context cardinality and barrier protocol refinement"; }
part obligation7:Obligation { attribute :>> key="C11"; attribute :>> status="open"; attribute :>> scope="Release/acquire plus metadata/storage lifetime"; attribute :>> gap="Packed bits fallback ordinary polling and epoch reset"; }
part obligation8:Obligation { attribute :>> key="external-hooks"; attribute :>> status="open"; attribute :>> scope="Foreign release callback reentry and FFI writes"; attribute :>> gap="Deny proof issuance unless closed contract supplied"; }
part obligation9:Obligation { attribute :>> key="native"; attribute :>> status="open"; attribute :>> scope="No runtime change or native tests"; attribute :>> gap="No speedup or capacity acceptance"; }
part def Gain { attribute key:String; attribute avoided:String; attribute added:String; attribute condition:String; }
part gain0:Gain { attribute :>> key="prefix overlap"; attribute :>> avoided="Avoid whole-chain scanner serialization"; attribute :>> added="Seal bookkeeping and delayed last chunk"; attribute :>> condition="Useful scan overlap H exceeds added publication A"; }
part gain1:Gain { attribute :>> key="mixed coverage"; attribute :>> avoided="One canonical identity for slots spans and chunk"; attribute :>> added="Coverage metadata or generated owner proof"; attribute :>> condition="Do not add a second runtime graph without benefit"; }
part gain2:Gain { attribute :>> key="will consistency"; attribute :>> avoided="Keep O(W) decisions and repair without strong graph rescan"; attribute :>> added="One decision rendezvous or immutable strong snapshot"; attribute :>> condition="All weak producers gated; not a measured speedup"; }
part gain3:Gain { attribute :>> key="producer ledger"; attribute :>> avoided="No separate publication counter when active owner spans reserve to settle"; attribute :>> added="Register inherited children before release"; attribute :>> condition="All queued/private/Tail/still work represented"; }
part gain4:Gain { attribute :>> key="retirement"; attribute :>> avoided="Retire early frame READY; ungated weak entry; allocation-derived ownership"; attribute :>> added="Seal-aware local frontier and split classify/retain APIs"; attribute :>> condition="All actual consumers migrated; legacy ownership already replaced is baseline"; }
part gain5:Gain { attribute :>> key="retention"; attribute :>> avoided="At most one delayed closed chunk per fit-admitted sequential copier"; attribute :>> added="Plus open chunk side metadata and old-stack/epoch pin"; attribute :>> condition="No unconditional byte bound for captured stale-threshold path"; }
part def Binding { attribute actionName:String; attribute lemma:String; attribute scope:String; }
part binding0:Binding { attribute :>> actionName="frame_chunk_coverage.initializeA"; attribute :>> lemma="ChunkCoverage.initializeAPreserves"; attribute :>> scope="Exact typed IR guard/update; native C mapping remains open"; }
part binding1:Binding { attribute :>> actionName="frame_chunk_coverage.initializeB"; attribute :>> lemma="ChunkCoverage.initializeBPreserves"; attribute :>> scope="Exact typed IR guard/update; native C mapping remains open"; }
part binding2:Binding { attribute :>> actionName="frame_chunk_coverage.registerA"; attribute :>> lemma="ChunkCoverage.registerAPreserves"; attribute :>> scope="Exact typed IR guard/update; native C mapping remains open"; }
part binding3:Binding { attribute :>> actionName="frame_chunk_coverage.registerB"; attribute :>> lemma="ChunkCoverage.registerBPreserves"; attribute :>> scope="Exact typed IR guard/update; native C mapping remains open"; }
part binding4:Binding { attribute :>> actionName="frame_chunk_coverage.sealA"; attribute :>> lemma="ChunkCoverage.sealAPreserves"; attribute :>> scope="Exact typed IR guard/update; native C mapping remains open"; }
part binding5:Binding { attribute :>> actionName="frame_chunk_coverage.sealB"; attribute :>> lemma="ChunkCoverage.sealBPreserves"; attribute :>> scope="Exact typed IR guard/update; native C mapping remains open"; }
part binding6:Binding { attribute :>> actionName="frame_chunk_coverage.closeChunk"; attribute :>> lemma="ChunkCoverage.closeChunkPreserves"; attribute :>> scope="Exact typed IR guard/update; native C mapping remains open"; }
part binding7:Binding { attribute :>> actionName="frame_chunk_coverage.deferClosed"; attribute :>> lemma="ChunkCoverage.deferClosedPreserves"; attribute :>> scope="Exact typed IR guard/update; native C mapping remains open"; }
part binding8:Binding { attribute :>> actionName="frame_chunk_coverage.closeAliases"; attribute :>> lemma="ChunkCoverage.closeAliasesPreserves"; attribute :>> scope="Exact typed IR guard/update; native C mapping remains open"; }
part binding9:Binding { attribute :>> actionName="frame_chunk_coverage.mutateA"; attribute :>> lemma="ChunkCoverage.mutateAPreserves"; attribute :>> scope="Exact typed IR guard/update; native C mapping remains open"; }
part binding10:Binding { attribute :>> actionName="frame_chunk_coverage.publishChunk"; attribute :>> lemma="ChunkCoverage.publishChunkPreserves"; attribute :>> scope="Exact typed IR guard/update; native C mapping remains open"; }
part binding11:Binding { attribute :>> actionName="frame_chunk_coverage.claim"; attribute :>> lemma="ChunkCoverage.claimPreserves"; attribute :>> scope="Exact typed IR guard/update; native C mapping remains open"; }
part binding12:Binding { attribute :>> actionName="frame_chunk_coverage.completeScan"; attribute :>> lemma="ChunkCoverage.completeScanPreserves"; attribute :>> scope="Exact typed IR guard/update; native C mapping remains open"; }
part binding13:Binding { attribute :>> actionName="weak_producer_admission.drainStrong"; attribute :>> lemma="WeakAdmission.drainStrongPreserves"; attribute :>> scope="Exact typed IR guard/update; native C mapping remains open"; }
part binding14:Binding { attribute :>> actionName="weak_producer_admission.freezeStrong"; attribute :>> lemma="WeakAdmission.freezeStrongPreserves"; attribute :>> scope="Exact typed IR guard/update; native C mapping remains open"; }
part binding15:Binding { attribute :>> actionName="weak_producer_admission.classifyA"; attribute :>> lemma="WeakAdmission.classifyAPreserves"; attribute :>> scope="Exact typed IR guard/update; native C mapping remains open"; }
part binding16:Binding { attribute :>> actionName="weak_producer_admission.classifyB"; attribute :>> lemma="WeakAdmission.classifyBPreserves"; attribute :>> scope="Exact typed IR guard/update; native C mapping remains open"; }
part binding17:Binding { attribute :>> actionName="weak_producer_admission.openWeak"; attribute :>> lemma="WeakAdmission.openWeakPreserves"; attribute :>> scope="Exact typed IR guard/update; native C mapping remains open"; }
part binding18:Binding { attribute :>> actionName="weak_producer_admission.listProducer"; attribute :>> lemma="WeakAdmission.listProducerPreserves"; attribute :>> scope="Exact typed IR guard/update; native C mapping remains open"; }
part binding19:Binding { attribute :>> actionName="weak_producer_admission.repairProducer"; attribute :>> lemma="WeakAdmission.repairProducerPreserves"; attribute :>> scope="Exact typed IR guard/update; native C mapping remains open"; }
part binding20:Binding { attribute :>> actionName="weak_producer_admission.freshWillProducer"; attribute :>> lemma="WeakAdmission.freshWillProducerPreserves"; attribute :>> scope="Exact typed IR guard/update; native C mapping remains open"; }
part binding21:Binding { attribute :>> actionName="weak_producer_admission.graphProducer"; attribute :>> lemma="WeakAdmission.graphProducerPreserves"; attribute :>> scope="Exact typed IR guard/update; native C mapping remains open"; }
part binding22:Binding { attribute :>> actionName="weak_producer_admission.continuationProducer"; attribute :>> lemma="WeakAdmission.continuationProducerPreserves"; attribute :>> scope="Exact typed IR guard/update; native C mapping remains open"; }
part binding23:Binding { attribute :>> actionName="weak_producer_admission.stillProducer"; attribute :>> lemma="WeakAdmission.stillProducerPreserves"; attribute :>> scope="Exact typed IR guard/update; native C mapping remains open"; }
part binding24:Binding { attribute :>> actionName="weak_producer_admission.deriveChild"; attribute :>> lemma="WeakAdmission.deriveChildPreserves"; attribute :>> scope="Exact typed IR guard/update; native C mapping remains open"; }
part binding25:Binding { attribute :>> actionName="weak_producer_admission.settleTask"; attribute :>> lemma="WeakAdmission.settleTaskPreserves"; attribute :>> scope="Exact typed IR guard/update; native C mapping remains open"; }
part binding26:Binding { attribute :>> actionName="weak_producer_admission.closeRoots"; attribute :>> lemma="WeakAdmission.closeRootsPreserves"; attribute :>> scope="Exact typed IR guard/update; native C mapping remains open"; }
part binding27:Binding { attribute :>> actionName="weak_producer_admission.finishWeak"; attribute :>> lemma="WeakAdmission.finishWeakPreserves"; attribute :>> scope="Exact typed IR guard/update; native C mapping remains open"; }
part binding28:Binding { attribute :>> actionName="weak_producer_admission.cleanup"; attribute :>> lemma="WeakAdmission.cleanupPreserves"; attribute :>> scope="Exact typed IR guard/update; native C mapping remains open"; }
part def Composition { attribute key:String; attribute lemma:String; attribute scope:String; }
part composition0:Composition { attribute :>> key="spatial-induction"; attribute :>> lemma="ChunkCoverage.reachableSafe"; attribute :>> scope="All physical gate steps"; }
part composition1:Composition { attribute :>> key="coordinates"; attribute :>> lemma="ChunkCoverage.copierScannerCoordinate"; attribute :>> scope="Normalized descriptor integer indices"; }
part composition2:Composition { attribute :>> key="root-map"; attribute :>> lemma="ChunkCoverage.rootSlotCoordinate"; attribute :>> scope="One-based root slots to copy slots"; }
part composition3:Composition { attribute :>> key="inside-frame"; attribute :>> lemma="ChunkCoverage.linkInsideFrame"; attribute :>> scope="Valid link bounds"; }
part composition4:Composition { attribute :>> key="mixed-tile"; attribute :>> lemma="ChunkCoverage.mixedChunkLinkCovered"; attribute :>> scope="Arbitrary mixed object list"; }
part composition5:Composition { attribute :>> key="unique-chunk"; attribute :>> lemma="ChunkCoverage.uniqueChunk"; attribute :>> scope="Disjoint half-open intervals"; }
part composition6:Composition { attribute :>> key="terminator"; attribute :>> lemma="ChunkCoverage.slotBeforeTerminator"; attribute :>> scope="Link cannot alias marker"; }
part composition7:Composition { attribute :>> key="padding"; attribute :>> lemma="ChunkCoverage.paddingThenFrame"; attribute :>> scope="Zero-word padding participates in header walk"; }
part composition8:Composition { attribute :>> key="weak-induction"; attribute :>> lemma="WeakAdmission.reachableSafe"; attribute :>> scope="All producer and closure steps"; }
part composition9:Composition { attribute :>> key="all-producers"; attribute :>> lemma="WeakAdmission.producerNeedsCut"; attribute :>> scope="Any accepted active work requires completed cut"; }
part composition10:Composition { attribute :>> key="no-debt"; attribute :>> lemma="WeakAdmission.completedNoDebt"; attribute :>> scope="Completion needs closed roots and zero debt"; }
part composition11:Composition { attribute :>> key="child-transfer"; attribute :>> lemma="WeakAdmission.childReservationBeforeRelease"; attribute :>> scope="Reserve child before parent settle"; }
part frameHistory:GambitAssuranceRouting::ModelNeed { ref part :>> owner=GambitAssuranceRelations::modelUse3; attribute :>> obligationId="PW-frameHistory"; attribute :>> kind="interleaving"; attribute :>> subjectPath="dev/refactoring/modern-c/models/quint/frame_chunk_coverage.qnt"; attribute :>> subjectScope="Two frames marker aliases and physical chunk handoff"; attribute :>> premise="Design and formal models only; no native qualification"; }
part weakHistory:GambitAssuranceRouting::ModelNeed { ref part :>> owner=GambitAssuranceRelations::modelUse3; attribute :>> obligationId="PW-weakHistory"; attribute :>> kind="interleaving"; attribute :>> subjectPath="dev/refactoring/modern-c/models/quint/weak_producer_admission.qnt"; attribute :>> subjectScope="Six routes inherited children closed roots unknown acknowledgment"; attribute :>> premise="Design and formal models only; no native qualification"; }
part frameInduction:GambitAssuranceRouting::ModelNeed { ref part :>> owner=GambitAssuranceRelations::modelUse3; attribute :>> obligationId="PW-frameInduction"; attribute :>> kind="induction"; attribute :>> subjectPath="dev/refactoring/modern-c/models/lean/ChunkCoverage.lean"; attribute :>> subjectScope="All projected steps and generic mixed-span arithmetic"; attribute :>> premise="Design and formal models only; no native qualification"; }
part weakInduction:GambitAssuranceRouting::ModelNeed { ref part :>> owner=GambitAssuranceRelations::modelUse3; attribute :>> obligationId="PW-weakInduction"; attribute :>> kind="induction"; attribute :>> subjectPath="dev/refactoring/modern-c/models/lean/WeakAdmission.lean"; attribute :>> subjectScope="All projected steps and gate/settlement properties"; attribute :>> premise="Design and formal models only; no native qualification"; }
part projection:GambitAssuranceRouting::ModelNeed { ref part :>> owner=GambitAssuranceRelations::modelUse3; attribute :>> obligationId="PW-projection"; attribute :>> kind="restricted-projection"; attribute :>> subjectPath="dev/refactoring/modern-c/models/lean/ChunkCoverageAst.lean"; attribute :>> subjectScope="Both typed IR guards updates exact rosters"; attribute :>> premise="Design and formal models only; no native qualification"; }
part source:GambitAssuranceRouting::ModelNeed { ref part :>> owner=GambitAssuranceRelations::modelUse3; attribute :>> obligationId="PW-source"; attribute :>> kind="source-refinement"; attribute :>> subjectPath="dev/refactoring/modern-c/frame-chunk-weak-producers-design.org"; attribute :>> subjectScope="Real allocation Tile and all native writer/producer closure open"; attribute :>> premise="Design and formal models only; no native qualification"; }
part platform:GambitAssuranceRouting::ModelNeed { ref part :>> owner=GambitAssuranceRelations::modelUse3; attribute :>> obligationId="PW-platform"; attribute :>> kind="native-memory-order"; attribute :>> subjectPath="dev/refactoring/modern-c/frame-chunk-weak-producers-design.org"; attribute :>> subjectScope="Pointer provenance and concrete C11 publication/phase/epoch open"; attribute :>> premise="Design and formal models only; no native qualification"; }
part def Seam { ref part producer:GambitRuntimeComposition::BlueprintModule; ref part consumer:GambitRuntimeComposition::BlueprintModule; attribute contract:String; attribute modelNeed:String; }
part seam0:Seam { ref part :>> producer=GambitRuntimeComposition::blueprintModule3; ref part :>> consumer=GambitRuntimeComposition::blueprintModule4; attribute :>> contract="Frame identity live descriptor and context roots"; attribute :>> modelNeed="PW-source"; }
part seam1:Seam { ref part :>> producer=GambitRuntimeComposition::blueprintModule4; ref part :>> consumer=GambitRuntimeComposition::blueprintModule4; attribute :>> contract="Physical span to sealed chunk to scanner"; attribute :>> modelNeed="PW-frameInduction"; }
part seam2:Seam { ref part :>> producer=GambitRuntimeComposition::blueprintModule4; ref part :>> consumer=GambitRuntimeComposition::blueprintModule5; attribute :>> contract="Frozen roster all-list decision cut"; attribute :>> modelNeed="PW-weakInduction"; }
part seam3:Seam { ref part :>> producer=GambitRuntimeComposition::blueprintModule4; ref part :>> consumer=GambitRuntimeComposition::blueprintModule1; attribute :>> contract="C11 slot READY queue and epoch lifetime"; attribute :>> modelNeed="PW-platform"; }

part producer15:Producer { attribute :>> key="mark_continuation-mark_frame"; attribute :>> caller="mark_continuation"; attribute :>> callee="mark_frame"; attribute :>> family="excluded"; attribute :>> phase="strong-only"; attribute :>> gate="frozen root phase"; attribute :>> custody="Must settle before global strong closure; late entry refused"; }
part producer16:Producer { attribute :>> key="mark_continuation-mark_captured_continuation"; attribute :>> caller="mark_continuation"; attribute :>> callee="mark_captured_continuation"; attribute :>> family="excluded"; attribute :>> phase="strong-only"; attribute :>> gate="frozen root phase"; attribute :>> custody="Must settle before global strong closure; late entry refused"; }
part producer17:Producer { attribute :>> key="mark_rc-mark_array"; attribute :>> caller="mark_rc"; attribute :>> callee="mark_array"; attribute :>> family="excluded"; attribute :>> phase="strong-only"; attribute :>> gate="frozen root phase"; attribute :>> custody="Must settle before global strong closure; late entry refused"; }
part producer18:Producer { attribute :>> key="mark_processor_scmobj-mark_array"; attribute :>> caller="mark_processor_scmobj"; attribute :>> callee="mark_array"; attribute :>> family="excluded"; attribute :>> phase="strong-only"; attribute :>> gate="frozen root phase"; attribute :>> custody="Must settle before global strong closure; late entry refused"; }
part producer19:Producer { attribute :>> key="mark_vm_scmobj-mark_array"; attribute :>> caller="mark_vm_scmobj"; attribute :>> callee="mark_array"; attribute :>> family="excluded"; attribute :>> phase="strong-only"; attribute :>> gate="frozen root phase"; attribute :>> custody="Must settle before global strong closure; late entry refused"; }
part producer20:Producer { attribute :>> key="mark_global_variables-mark_array"; attribute :>> caller="mark_global_variables"; attribute :>> callee="mark_array"; attribute :>> family="excluded"; attribute :>> phase="strong-only"; attribute :>> gate="frozen root phase"; attribute :>> custody="Must settle before global strong closure; late entry refused"; }
part producer21:Producer { attribute :>> key="mark_symkey_tables-mark_array"; attribute :>> caller="mark_symkey_tables"; attribute :>> callee="mark_array"; attribute :>> family="excluded"; attribute :>> phase="strong-only"; attribute :>> gate="frozen root phase"; attribute :>> custody="Must settle before global strong closure; late entry refused"; }
part producer22:Producer { attribute :>> key="mark_execution_roots-mark_array"; attribute :>> caller="mark_execution_roots"; attribute :>> callee="mark_array"; attribute :>> family="excluded"; attribute :>> phase="strong-only"; attribute :>> gate="frozen root phase"; attribute :>> custody="Must settle before global strong closure; late entry refused"; }

part source31:Source { attribute :>> key="fifo-gate"; attribute :>> path="vendor/gambit/lib/mem.c"; attribute :>> needle="while (___COMPARE_AND_SWAP_WORD(&owner->chunk_gate_,0,1) != 0)"; attribute :>> obligation="Current queue gate replaces historical volatile polling; no automatic C11 qualification"; }
part source32:Source { attribute :>> key="fifo-take"; attribute :>> path="vendor/gambit/lib/mem.c"; attribute :>> needle="___WORD *ptr = take_heap_chunk(work,victim);"; attribute :>> obligation="Stolen scans use current shared take path"; }

part producer23:Producer { attribute :>> key="frame-scan-dispatch"; attribute :>> caller="scan"; attribute :>> callee="mark_frame"; attribute :>> family="4"; attribute :>> phase="strong-or-weak"; attribute :>> gate="inherited phase plus frame seal"; attribute :>> custody="Explicit caller edge required by actual direct-call inventory"; }
part composition12:Composition { attribute :>> key="append"; attribute :>> lemma="ChunkCoverage.spanAppend"; attribute :>> scope="Real allocation append induction premise"; }
part composition13:Composition { attribute :>> key="sentinel-alias"; attribute :>> lemma="ChunkCoverage.nextLeadingAliasesTerm"; attribute :>> scope="Previous terminator equals next leading queue-link address"; }
part contract15:Contract { attribute :>> fromNode="chunk-seal"; attribute :>> toNode="producer-ledger"; attribute :>> custody="Retain delayed chunk as phase debt; source relation open"; }
part contract16:Contract { attribute :>> fromNode="weak-producers"; attribute :>> toNode="producer-ledger"; attribute :>> custody="Same epoch task identity"; }
part contract17:Contract { attribute :>> fromNode="producer-ledger"; attribute :>> toNode="weak-closure"; attribute :>> custody="Private queued Tail still child debt zero"; }
part obligation10:Obligation { attribute :>> key="shared-terminator"; attribute :>> status="open"; attribute :>> scope="Previous end marker is next leading queue-link storage"; attribute :>> gap="FIFO gate alone does not synchronize scanner raw marker read; input schedule and C11 proof open"; }

part contract18:Contract { attribute :>> fromNode="terminator"; attribute :>> toNode="queue-link-alias"; attribute :>> custody="Next leading link equals prior term"; }
part contract19:Contract { attribute :>> fromNode="queue-link-alias"; attribute :>> toNode="C11-obligation"; attribute :>> custody="Scanner reads need synchronized or immutable metadata"; }
part gain6:Gain { attribute :>> key="frontier accounting"; attribute :>> avoided="Avoid an extra O(K) header walk at each publication"; attribute :>> added="O(1) frontier update per committed allocation; generated slot map"; attribute :>> condition="Real allocation append proof and all rollback/pad cases closed"; }
part gain7:Gain { attribute :>> key="sentinel separation"; attribute :>> avoided="Remove shared marker read versus FIFO-link write overlap"; attribute :>> added="Atomic compatible storage/access or separate queue-link word and lifetime"; attribute :>> condition="Address alias proved; scheduling and concrete C11 composition unresolved"; }
}
