package GambitCleanupIngress { private import ScalarValues::*;
part def SourceRow { attribute key:String; attribute path:String; attribute needle:String; attribute limit:String; }
part source0:SourceRow { attribute :>> key="cleanup-entry"; attribute :>> path="vendor/gambit/lib/setup.c"; attribute :>> needle="if (___GSTATE->setup_state != 1)"; attribute :>> limit="plain setup lifecycle check; not atomic cross-thread admission/drain"; }
part source1:SourceRow { attribute :>> key="same-carrier"; attribute :>> path="vendor/gambit/lib/setup.c"; attribute :>> needle="same-carrier refusal, not general cross-VM shutdown admission"; attribute :>> limit="reject frozen owner before destruction; no general nested-call census"; }
part source2:SourceRow { attribute :>> key="public-table"; attribute :>> path="vendor/gambit/lib/setup.c"; attribute :>> needle="___GSTATE->___cleanup"; attribute :>> limit="native table also exports pstate/vmstate cleanup; no stable public close receipt"; }
part source3:SourceRow { attribute :>> key="call-unwind"; attribute :>> path="vendor/gambit/lib/setup.c"; attribute :>> needle="stack_marker != ___ps->context->fp[___FRAME_SPACE(2)-2]"; attribute :>> limit="call may throw past its own activation before normal return"; }
part source4:SourceRow { attribute :>> key="run-marker"; attribute :>> path="vendor/gambit/lib/setup.c"; attribute :>> needle="___kill_sfun_stack_marker (marker);"; attribute :>> limit="run catches then kills marker; not an all-nested-guards completion proof"; }
part source5:SourceRow { attribute :>> key="sfun-landing"; attribute :>> path="vendor/gambit/lib/c_intf.c"; attribute :>> needle="call_sfun_with_cleanup"; attribute :>> limit="throw versus returned error tracked by unwinding flag"; }
part source6:SourceRow { attribute :>> key="generated-end"; attribute :>> path="vendor/gambit/include/_gambit/foreign_conversion.h.in"; attribute :>> needle="#define ___END_SFUN }"; attribute :>> limit="end_sfun before propagate_error; source macro not current generated module qualification"; }
part source7:SourceRow { attribute :>> key="catcher"; attribute :>> path="vendor/gambit/include/_gambit/foreign_conversion.h.in"; attribute :>> needle="___ps->catcher = ___old_catcher"; attribute :>> limit="normal END_TRY restoration; arbitrary foreign longjmp may bypass"; }
part source8:SourceRow { attribute :>> key="tcl-callback"; attribute :>> path="vendor/gambit/examples/tcltk/tcltk.scm"; attribute :>> needle="char *result = tcltk_call"; attribute :>> limit="raw data_rc at callback entry needs prior source lifetime"; }
part source9:SourceRow { attribute :>> key="tcl-result"; attribute :>> path="vendor/gambit/examples/tcltk/tcltk.scm"; attribute :>> needle="___CAST(Tcl_FreeProc*,___EXT(___release_string))"; attribute :>> limit="Tcl owns delayed native string release; callback return is not debt completion"; }
part source10:SourceRow { attribute :>> key="embedding-client"; attribute :>> path="vendor/gambit/tests/client.c"; attribute :>> needle="___cleanup ();"; attribute :>> limit="sequential generated API calls then cleanup; example not universal admission contract"; }
part source11:SourceRow { attribute :>> key="pthread-client"; attribute :>> path="vendor/gambit/examples/pthread/pthread.c"; attribute :>> needle="pthread_join (tid[i], &results[i]);"; attribute :>> limit="external host joins before cleanup; serialized Scheme calls in this example"; }
part source12:SourceRow { attribute :>> key="main-cleanup"; attribute :>> path="vendor/gambit/lib/main.c"; attribute :>> needle="___cleanup ();"; attribute :>> limit="after successful setup return; main owns lifecycle"; }
part source13:SourceRow { attribute :>> key="exit-policy"; attribute :>> path="vendor/gambit/lib/setup.c"; attribute :>> needle="___exit_process (status);"; attribute :>> limit="cleanup_and_exit is process termination even if cleanup retained/refused"; }
part source14:SourceRow { attribute :>> key="parent-model"; attribute :>> path="dev/refactoring/modern-c/models/quint/cohort_retirement.qnt"; attribute :>> needle="action retireDomain="; attribute :>> limit="actual previous model; retain external reader and join duties"; }
part def ObligationRow { attribute key:String; attribute status:String; attribute condition:String; }
part obligation0:ObligationRow { attribute :>> key="ingress-safety"; attribute :>> status="conditional-model"; attribute :>> condition="close request preserves active scopes; settle after children and known landing"; }
part obligation1:ObligationRow { attribute :>> key="source-boundaries"; attribute :>> status="source-bound"; attribute :>> condition="actual cleanup call sites, SFUN landing/end and Tcl delayed result release"; }
part obligation2:ObligationRow { attribute :>> key="public-callers"; attribute :>> status="unresolved"; attribute :>> condition="all direct and indirect public APIs acquire stable outer authority before first raw pointer/TLS access"; }
part obligation3:ObligationRow { attribute :>> key="nested-grants"; attribute :>> status="unresolved"; attribute :>> condition="preauthorized callback/source identity and bounded grant must be explicit; arbitrary late callbacks refused"; }
part obligation4:ObligationRow { attribute :>> key="exception-closure"; attribute :>> status="unresolved"; attribute :>> condition="exact catcher/marker landing and one-time guard settlement; raw foreign longjmp/cancellation not covered"; }
part obligation5:ObligationRow { attribute :>> key="storage-completion"; attribute :>> status="unresolved"; attribute :>> condition="all delayed result, RC, still, descriptor and allocator-origin debts settled"; }
part obligation6:ObligationRow { attribute :>> key="c23-refinement"; attribute :>> status="unresolved"; attribute :>> condition="closed admission atomic linearization, release/acquire and effective native sync/join"; }
part def RouteRow { attribute actionName:String; attribute lemma:String; attribute source:String; attribute obligation:String; }
part route0:RouteRow { attribute :>> actionName="reserveChild"; attribute :>> lemma="CleanupIngress.reserveChildPreserves"; attribute :>> source="cleanup-entry"; attribute :>> obligation="ingress-safety"; }
part route1:RouteRow { attribute :>> actionName="enterChild"; attribute :>> lemma="CleanupIngress.enterChildPreserves"; attribute :>> source="cleanup-entry"; attribute :>> obligation="ingress-safety"; }
part route2:RouteRow { attribute :>> actionName="returnChild"; attribute :>> lemma="CleanupIngress.returnChildPreserves"; attribute :>> source="sfun-landing"; attribute :>> obligation="ingress-safety"; }
part route3:RouteRow { attribute :>> actionName="cancelPermit"; attribute :>> lemma="CleanupIngress.cancelPermitPreserves"; attribute :>> source="cleanup-entry"; attribute :>> obligation="ingress-safety"; }
part route4:RouteRow { attribute :>> actionName="requestClose"; attribute :>> lemma="CleanupIngress.requestClosePreserves"; attribute :>> source="cleanup-entry"; attribute :>> obligation="ingress-safety"; }
part route5:RouteRow { attribute :>> actionName="loseBoundary"; attribute :>> lemma="CleanupIngress.loseBoundaryPreserves"; attribute :>> source="sfun-landing"; attribute :>> obligation="ingress-safety"; }
part route6:RouteRow { attribute :>> actionName="recoverLanding"; attribute :>> lemma="CleanupIngress.recoverLandingPreserves"; attribute :>> source="sfun-landing"; attribute :>> obligation="ingress-safety"; }
part route7:RouteRow { attribute :>> actionName="exportResult"; attribute :>> lemma="CleanupIngress.exportResultPreserves"; attribute :>> source="tcl-result"; attribute :>> obligation="ingress-safety"; }
part route8:RouteRow { attribute :>> actionName="releaseResult"; attribute :>> lemma="CleanupIngress.releaseResultPreserves"; attribute :>> source="tcl-result"; attribute :>> obligation="ingress-safety"; }
part route9:RouteRow { attribute :>> actionName="finishOuter"; attribute :>> lemma="CleanupIngress.finishOuterPreserves"; attribute :>> source="sfun-landing"; attribute :>> obligation="ingress-safety"; }
part route10:RouteRow { attribute :>> actionName="drainCollective"; attribute :>> lemma="CleanupIngress.drainCollectivePreserves"; attribute :>> source="cleanup-entry"; attribute :>> obligation="ingress-safety"; }
part route11:RouteRow { attribute :>> actionName="joinUnknown"; attribute :>> lemma="CleanupIngress.joinUnknownPreserves"; attribute :>> source="cleanup-entry"; attribute :>> obligation="ingress-safety"; }
part route12:RouteRow { attribute :>> actionName="joinKnown"; attribute :>> lemma="CleanupIngress.joinKnownPreserves"; attribute :>> source="cleanup-entry"; attribute :>> obligation="ingress-safety"; }
part route13:RouteRow { attribute :>> actionName="retireDomain"; attribute :>> lemma="CleanupIngress.retireDomainPreserves"; attribute :>> source="cleanup-entry"; attribute :>> obligation="ingress-safety"; }
part def GainRow { attribute key:String; attribute saved:String; attribute added:String; attribute condition:String; attribute status:String; }
part gain0:GainRow { attribute :>> key="nested-shutdown"; attribute :>> saved="0 blocking self-drain waits in requestClose; no forced premature root release"; attribute :>> added="stable requested-close record and later owner finalization"; attribute :>> condition="request and final retirement are separate operations"; attribute :>> status="conditional-model"; }
part gain1:GainRow { attribute :>> key="known-SFUN-unwind"; attribute :>> saved="reuse existing throw-as-result cleanup route and marker retirement"; attribute :>> added="exact session identity and guard registration before collecting conversion"; attribute :>> condition="no raw foreign exit bypasses landing; generated code qualified"; attribute :>> status="source-bound/conditional"; }
part gain2:GainRow { attribute :>> key="shared-admission"; attribute :>> saved="0 mandatory duplicate gates for run and its internal call"; attribute :>> added="one outer authority plus scoped child grants; all raw bypasses refused or mediated"; attribute :>> condition="private delegated internal calls distinguished from fresh public calls"; attribute :>> status="design-only"; }
part gain3:GainRow { attribute :>> key="delayed-results"; attribute :>> saved="avoid treating callback return as all-storage drain"; attribute :>> added="O(R) origin holds for R outstanding native result releases"; attribute :>> condition="Tcl release callback and module/provider lifetime remain callable"; attribute :>> status="unresolved-native"; }
part gain4:GainRow { attribute :>> key="retirement"; attribute :>> saved="0 current runtime paths retired by formal checks"; attribute :>> added="typed request/await/result and cleanup adapter; retained unknown ledger"; attribute :>> condition="all native callers, exception and storage closure"; attribute :>> status="design-only"; }
part def IssuerRow { attribute key:String; attribute source:String; attribute signature:String; attribute gap:String; }
part issuer0:IssuerRow { attribute :>> key="embedding-owner"; attribute :>> source="public-table"; attribute :>> signature="stable entry authority closes fresh host calls; remains live after close"; attribute :>> gap="setup_state alone is not concurrent gate"; }
part issuer1:IssuerRow { attribute :>> key="parent-scope"; attribute :>> source="sfun-landing"; attribute :>> signature="preauthorized child/source grant and pending child debt"; attribute :>> gap="normal parent cannot settle while child or grant remains"; }
part issuer2:IssuerRow { attribute :>> key="landing-owner"; attribute :>> source="generated-end"; attribute :>> signature="exact activation marker/catcher plus cleanup-completed guard identity"; attribute :>> gap="no receipt from arbitrary longjmp or multishot stale completion"; }
part issuer3:IssuerRow { attribute :>> key="result-owner"; attribute :>> source="tcl-result"; attribute :>> signature="one-time native result release with origin/module hold"; attribute :>> gap="delayed Tcl disposal or unknown free may outlive callbacks"; }
part issuer4:IssuerRow { attribute :>> key="retirement-coordinator"; attribute :>> source="parent-model"; attribute :>> signature="combine ingress drain, physical cohort, worker join and storage closure"; attribute :>> gap="current void APIs do not expose authoritative final status"; }
part def ConsumerRow { attribute key:String; attribute source:String; attribute access:String; attribute lifetime:String; attribute limit:String; }
part consumer0:ConsumerRow { attribute :>> key="sequential-host"; attribute :>> source="embedding-client"; attribute :>> access="call generated Scheme API then release string then cleanup"; attribute :>> lifetime="host owns sequential lifecycle"; attribute :>> limit="does not prove concurrent external caller closure"; }
part consumer1:ConsumerRow { attribute :>> key="threaded-host"; attribute :>> source="pthread-client"; attribute :>> access="ON_THROW inside host mutex; external pthread joins before cleanup"; attribute :>> lifetime="all host worker threads joined by main in example"; attribute :>> limit="mutex serialization is example policy, not modern SMP design"; }
part consumer2:ConsumerRow { attribute :>> key="run-call"; attribute :>> source="run-marker"; attribute :>> access="run establishes marker; call may propagate past nested C frame"; attribute :>> lifetime="C stack marker/catcher and Scheme roots until exact landing"; attribute :>> limit="phase check does not grant storage lifetime before first dereference"; }
part consumer3:ConsumerRow { attribute :>> key="sfun-end"; attribute :>> source="generated-end"; attribute :>> access="end_sfun releases root bank before propagate_error"; attribute :>> lifetime="common generated cleanup landing"; attribute :>> limit="foreign jumps around macro cleanup remain outside closure"; }
part consumer4:ConsumerRow { attribute :>> key="tcl-command"; attribute :>> source="tcl-callback"; attribute :>> access="Tcl dispatch -> data_rc -> tcltk_call -> Scheme apply"; attribute :>> lifetime="command source lifetime plus nested scope"; attribute :>> limit="Tcl command deletion/late dispatch require source-owner agreement"; }
part consumer5:ConsumerRow { attribute :>> key="tcl-release"; attribute :>> source="tcl-result"; attribute :>> access="Tcl_SetResult installs runtime release_string callback"; attribute :>> lifetime="result allocation and runtime code until disposal"; attribute :>> limit="not drained by join of an unrelated Scheme worker"; }
part consumer6:ConsumerRow { attribute :>> key="process-exit"; attribute :>> source="exit-policy"; attribute :>> access="cleanup then unconditional exit_process"; attribute :>> lifetime="process policy rather than reusable VM retirement"; attribute :>> limit="no recoverable retirement receipt inferred"; }
part def EdgeRow { attribute fromNode:String; attribute toNode:String; attribute contract:String; }
part edge0:EdgeRow { attribute :>> fromNode="Stable host authority"; attribute :>> toNode="Close request"; attribute :>> contract="stop fresh ingress; keep current scopes and their roots"; }
part edge1:EdgeRow { attribute :>> fromNode="Admitted parent"; attribute :>> toNode="Child grant"; attribute :>> contract="reserve before close; no late unbounded new work"; }
part edge2:EdgeRow { attribute :>> fromNode="Child grant"; attribute :>> toNode="Nested callback"; attribute :>> contract="consume exact grant; return or retained unknown"; }
part edge3:EdgeRow { attribute :>> fromNode="Nested callback"; attribute :>> toNode="Known cleanup landing"; attribute :>> contract="end_sfun and marker/root duties before parent settlement"; }
part edge4:EdgeRow { attribute :>> fromNode="Close request"; attribute :>> toNode="Deferred coordinator"; attribute :>> contract="never synchronously wait for requesting callback itself"; }
part edge5:EdgeRow { attribute :>> fromNode="Known cleanup landing"; attribute :>> toNode="Ingress drain"; attribute :>> contract="children and unused grants settled; guard only once"; }
part edge6:EdgeRow { attribute :>> fromNode="Ingress drain"; attribute :>> toNode="Collective and worker join"; attribute :>> contract="physical drain and termination remain independent"; }
part edge7:EdgeRow { attribute :>> fromNode="Tcl result owner"; attribute :>> toNode="Storage closure"; attribute :>> contract="release callback / origin holds can outlive execution"; }
part edge8:EdgeRow { attribute :>> fromNode="Collective and worker join"; attribute :>> toNode="Retirement receipt"; attribute :>> contract="also require storage closure; unknown retains custody"; }
}
