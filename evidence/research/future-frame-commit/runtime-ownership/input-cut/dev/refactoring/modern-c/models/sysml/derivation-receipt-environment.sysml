package GambitDerivationReceiptEnvironment { private import ScalarValues::*;
part def Route { attribute key:String; attribute sourcePath:String; attribute needle:String; attribute obligation:String; }
part route0:Route { attribute :>> key="chunk-producer"; attribute :>> sourcePath="vendor/gambit/lib/mem.c"; attribute :>> needle="___HIDDEN void end_heap_chunk"; attribute :>> obligation="Current synchronous link/barrier/tail/lock/signal path has no receipt transaction"; }
part route1:Route { attribute :>> key="chunk-claim"; attribute :>> sourcePath="vendor/gambit/lib/mem.c"; attribute :>> needle="heap_chunks_to_scan_head = ptr;"; attribute :>> obligation="Queue head moves before scan; dequeued work retains its own responsibility"; }
part route2:Route { attribute :>> key="scan-steal"; attribute :>> sourcePath="vendor/gambit/lib/mem.c"; attribute :>> needle="goto continue_local_scan;"; attribute :>> obligation="Steal scan can produce more local work before returning to termination loop"; }
part route3:Route { attribute :>> key="idle-completion"; attribute :>> sourcePath="vendor/gambit/lib/mem.c"; attribute :>> needle="if (--(*workers_count) == 0)"; attribute :>> obligation="Current worker-count termination must not become task-level retirement evidence without complete producer closure"; }
part route4:Route { attribute :>> key="lock-profile"; attribute :>> sourcePath="vendor/gambit/include/gambit.h.in"; attribute :>> needle="#define ___SPINLOCK_LOCK(lock) ___MUTEX_LOCK(lock)"; attribute :>> obligation="Actual backend selects no-op mutex or ticketlock branches; source macro name alone is not C11 proof"; }
part route5:Route { attribute :>> key="descriptor-reader"; attribute :>> sourcePath="vendor/gambit/lib/mem.c"; attribute :>> needle="descriptor = ___decode_frame_descriptor (___LABEL_DESCR_GET(actual_ra), 1);"; attribute :>> obligation="Decoder and trailing map reads need cohort authority through actual final use"; }
part route6:Route { attribute :>> key="exception-boundary"; attribute :>> sourcePath="vendor/gambit/include/gambit.h.in"; attribute :>> needle="___ps->catcher = ___old_catcher"; attribute :>> obligation="Failed native operation cannot discard a committed task or abandon candidate cleanup"; }
part route7:Route { attribute :>> key="os-retirement"; attribute :>> sourcePath="vendor/gambit/lib/os_dyn.c"; attribute :>> needle="dlclose (p->descr);"; attribute :>> obligation="No current per-task receipt ledger or per-cohort final-use closure is established"; }
part route8:Route { attribute :>> key="reference-producer"; attribute :>> sourcePath="/opt/homebrew/Cellar/quint/0.33.0/libexec/lib/node_modules/@informalsystems/quint/dist/src/names/resolver.js"; attribute :>> needle="this.table.set(id, def);"; attribute :>> obligation="Occurrence-ID lookup relation must be preserved in emitted finite witness rows"; }
part route9:Route { attribute :>> key="reference-consumer"; attribute :>> sourcePath="/opt/homebrew/Cellar/quint/0.33.0/libexec/lib/node_modules/@informalsystems/quint/dist/src/runtime/impl/builder.js"; attribute :>> needle="const def = builder.table.get(expr.id);"; attribute :>> obligation="Real resolution uses lookup table identity rather than spelling"; }
part route10:Route { attribute :>> key="witness-checker"; attribute :>> sourcePath="dev/modeling/tools/typed-binding-witness.py"; attribute :>> needle="refs.append(dict(occurrence=oid,target=target"; attribute :>> obligation="Existing research gate binds canonical declarations and inferred types; decoder remains trusted"; }
part route11:Route { attribute :>> key="frozen-json"; attribute :>> sourcePath="evidence/research/reti-ofd-semantics/typed-ir.json"; attribute :>> needle="\"typechecking\""; attribute :>> obligation="Actual pinned formal JSON has 91 selected name occurrences; not runtime source execution"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule4; ref part :>> counterpart=GambitRuntimeComposition::blueprintModule5; attribute :>> key="parent-authority"; attribute :>> owner="collector/control"; attribute :>> actionName="beginDerive beginFinish"; attribute :>> invariant="LIVE to DERIVING competes with LIVE to FINISHING on one canonical parent state"; attribute :>> gap="Real abandonment and reclamation of parent control records remain open"; }
part contract1:Contract { ref part :>> accountable=GambitRuntimeComposition::blueprintModule3; ref part :>> counterpart=GambitRuntimeComposition::blueprintModule7; attribute :>> key="ledger-commit"; attribute :>> owner="roots/release"; attribute :>> actionName="reserveChild publish"; attribute :>> invariant="Immutable snapshot CAS jointly commits ticket state count and receipt; queue hints carry no authority"; attribute :>> gap="Snapshot pinning allocation and weak-memory implementation unproved"; }
part contract2:Contract { ref part :>> accountable=GambitRuntimeComposition::blueprintModule7; ref part :>> counterpart=GambitRuntimeComposition::blueprintModule8; attribute :>> key="lost-ack-custody"; attribute :>> owner="release/build"; attribute :>> actionName="loseAck replay reconcile"; attribute :>> invariant="Publication registers pending delivery; exact-ID result clears it; late loss cannot resurrect it"; attribute :>> gap="Late observers require independent receipt lifetime and tombstones"; }
part contract3:Contract { ref part :>> accountable=GambitRuntimeComposition::blueprintModule7; ref part :>> counterpart=GambitRuntimeComposition::blueprintModule1; attribute :>> key="final-use"; attribute :>> owner="native/collector"; attribute :>> actionName="finishParent finishChild retire"; attribute :>> invariant="Debt released after final payload access; unknown outcome blocks retirement in reference model"; attribute :>> gap="Full users release sequence and loader final-use proof open"; }
part contract4:Contract { ref part :>> accountable=GambitRuntimeComposition::blueprintModule8; ref part :>> counterpart=GambitRuntimeComposition::blueprintModule0; attribute :>> key="finite-environment"; attribute :>> owner="modeling/build"; attribute :>> actionName="buildEnv tableCheck"; attribute :>> invariant="Every admitted witness row agrees with constructed lookup function"; attribute :>> gap="Rows must faithfully represent authenticated JSON used references"; }
part contract5:Contract { ref part :>> accountable=GambitRuntimeComposition::blueprintModule8; ref part :>> counterpart=GambitRuntimeComposition::blueprintModule0; attribute :>> key="typed-action-bridge"; attribute :>> owner="modeling/build"; attribute :>> actionName="reserveChild publish finishChild"; attribute :>> invariant="Generated guard/update expressions match maintained Lean Flat semantics for three selected actions"; attribute :>> gap="Emitter/parser trusted; remaining actions and full history simulation open"; }
part def Obligation { attribute key:String; attribute status:String; attribute scope:String; attribute counterexample:String; }
part obligation0:Obligation { attribute :>> key="authority-race"; attribute :>> status="bounded-checked"; attribute :>> scope="One parent one child one generation; deriving blocks finish and finishing blocks derive"; attribute :>> counterexample="Separate grant load and final decrement can overlap"; }
part obligation1:Obligation { attribute :>> key="receipt-order"; attribute :>> status="bounded-checked"; attribute :>> scope="Pending delivery is committed with READY; completion can precede observed receipt"; attribute :>> counterexample="Blind re-enqueue duplicates logical publication; ACK does not mean execution completion"; }
part obligation2:Obligation { attribute :>> key="three-step-refinement"; attribute :>> status="conditional-proved"; attribute :>> scope="Source State to Flat relation composes with generated guard/update certificates for reserve publish child completion"; attribute :>> counterexample="No theorem for all QNT actions or arbitrary histories"; }
part obligation3:Obligation { attribute :>> key="table-environment"; attribute :>> status="conditional-proved"; attribute :>> scope="Finite table check implies each witness row matches buildEnv; actual 91 rows certified"; attribute :>> counterexample="A consistently forged table still passes internal consistency"; }
part obligation4:Obligation { attribute :>> key="c11-execution"; attribute :>> status="open"; attribute :>> scope="Same LedgerHead acq_rel CAS chain with release-published initialized snapshots"; attribute :>> counterexample="Hazard/generation pin protocol and target C11 execution graph not proved"; }
part obligation5:Obligation { attribute :>> key="full-source"; attribute :>> status="open"; attribute :>> scope="Current FIFO idle rooted descriptors FFI exceptions and old module users"; attribute :>> counterexample="Current worker count is not the proposed task ledger"; }
part obligation6:Obligation { attribute :>> key="bytes-to-meaning"; attribute :>> status="open"; attribute :>> scope="JSON parsing canonical row projection and field-slot interpretation"; attribute :>> counterexample="Finite Lean certificate does not certify Python row extraction"; }
part def Gain { attribute key:String; attribute avoided:String; attribute added:String; attribute condition:String; }
part gain0:Gain { attribute :>> key="race-correctness"; attribute :>> avoided="Zero-debt gap between parent exit and child reservation"; attribute :>> added="Parent phase arbitration and atomic joint ledger commit"; attribute :>> condition="No production runtime benefit claim until actual refinements and all consumers migrate"; }
part gain1:Gain { attribute :>> key="unknown-recovery"; attribute :>> avoided="Blind publication retry and duplicate execution after lost ACK"; attribute :>> added="Stable TaskId input digest phase lookup and retained terminal receipt"; attribute :>> condition="Execution at most once is conditional on complete canonical claim; queue hints may duplicate"; }
part gain2:Gain { attribute :>> key="memory-order-audit"; attribute :>> avoided="Unproved fusion of independently written count state and receipt"; attribute :>> added="Reference protocol may allocate and copy a persistent snapshot path for each CAS attempt"; attribute :>> condition="A contended global head can regress throughput; batching/sharding need new proofs"; }
part gain3:Gain { attribute :>> key="environment-fidelity"; attribute :>> avoided="Manually supplied resolver function with no concrete table witness"; attribute :>> added="91 row consistency certificate plus JSON scope/type/digest admission"; attribute :>> condition="Correct rows and parser still premises; no whole-translator proof"; }
part gain4:Gain { attribute :>> key="retirement"; attribute :>> avoided="Blanket indefinite old-cohort retention when complete final-use evidence exists"; attribute :>> added="Execution debt and observer/tombstone lifetime must be accounted separately"; attribute :>> condition="Unknown observers conservatively block unload here; no finite retention bound"; }
part def Binding { attribute key:String; attribute qntAction:String; attribute leanLemma:String; attribute refinement:String; attribute guardLemma:String; attribute updateLemma:String; }
part binding0:Binding { attribute :>> key="reserve"; attribute :>> qntAction="reserveChild"; attribute :>> leanLemma="reserveRefines"; attribute :>> refinement="Successful immutable snapshot CAS must implement this atomic reserve relation"; attribute :>> guardLemma="reserveChildGuardMeaning"; attribute :>> updateLemma="reserveChildNextMeaning"; }
part binding1:Binding { attribute :>> key="publish"; attribute :>> qntAction="publish"; attribute :>> leanLemma="publishRefines"; attribute :>> refinement="Logical READY publication differs from physical queue hint enqueue"; attribute :>> guardLemma="publishGuardMeaning"; attribute :>> updateLemma="publishNextMeaning"; }
part binding2:Binding { attribute :>> key="completion"; attribute :>> qntAction="finishChild"; attribute :>> leanLemma="finishRefines"; attribute :>> refinement="Completion receipt and decrement commit together after all final reads"; attribute :>> guardLemma="finishChildGuardMeaning"; attribute :>> updateLemma="finishChildNextMeaning"; }
part def Flow { attribute fromNode:String; attribute toNode:String; attribute reason:String; }
part flow0:Flow { attribute :>> fromNode="c0"; attribute :>> toNode="c1"; attribute :>> reason="Grant remains live through joint child reservation"; }
part flow1:Flow { attribute :>> fromNode="c1"; attribute :>> toNode="c2"; attribute :>> reason="Canonical commit survives lost acknowledgement"; }
part flow2:Flow { attribute :>> fromNode="c2"; attribute :>> toNode="c3"; attribute :>> reason="Completion and observation settle different debts"; }
part flow3:Flow { attribute :>> fromNode="c0"; attribute :>> toNode="o0"; attribute :>> reason="Race histories"; }
part flow4:Flow { attribute :>> fromNode="c2"; attribute :>> toNode="o1"; attribute :>> reason="Lost ACK histories"; }
part flow5:Flow { attribute :>> fromNode="c5"; attribute :>> toNode="o2"; attribute :>> reason="Selected action certificates"; }
part flow6:Flow { attribute :>> fromNode="c4"; attribute :>> toNode="o3"; attribute :>> reason="Finite lookup construction theorem"; }
part flow7:Flow { attribute :>> fromNode="o3"; attribute :>> toNode="o6"; attribute :>> reason="Raw JSON projection remains trusted"; }
part flow8:Flow { attribute :>> fromNode="c1"; attribute :>> toNode="o4"; attribute :>> reason="C11 successful CAS refinement premise"; }
part flow9:Flow { attribute :>> fromNode="c3"; attribute :>> toNode="o5"; attribute :>> reason="All actual final users required"; }
part flow10:Flow { attribute :>> fromNode="o4"; attribute :>> toNode="o5"; attribute :>> reason="Memory order cannot establish source closure"; }
part flow11:Flow { attribute :>> fromNode="c4"; attribute :>> toNode="c5"; attribute :>> reason="Occurrence identity precedes AST meaning"; }
part history:GambitAssuranceRouting::ModelNeed { ref part :>> owner=GambitBuildAssurance::planner.component; attribute :>> obligationId="DR-H"; attribute :>> kind="interleaving"; attribute :>> subjectPath="dev/refactoring/modern-c/models/quint/derivation_receipt_environment.qnt"; attribute :>> subjectScope="Finite authority race and logical commit lost-ACK custody histories"; attribute :>> premise="Reference protocol and admitted formal AST; no native or whole-source qualification"; }
part induction:GambitAssuranceRouting::ModelNeed { ref part :>> owner=GambitBuildAssurance::planner.component; attribute :>> obligationId="DR-I"; attribute :>> kind="induction"; attribute :>> subjectPath="dev/refactoring/modern-c/models/lean/DerivationReceiptEnvironment.lean"; attribute :>> subjectScope="Three source-to-Flat transitions and generic finite-table environment meaning"; attribute :>> premise="Reference protocol and admitted formal AST; no native or whole-source qualification"; }
part expression:GambitAssuranceRouting::ModelNeed { ref part :>> owner=GambitBuildAssurance::planner.component; attribute :>> obligationId="DR-X"; attribute :>> kind="induction"; attribute :>> subjectPath="dev/refactoring/modern-c/models/lean/DerivationReceiptAst.lean"; attribute :>> subjectScope="Actual typed-IR guard/update certificates for three actions and 91-row environment witness"; attribute :>> premise="Reference protocol and admitted formal AST; no native or whole-source qualification"; }
part source:GambitAssuranceRouting::ModelNeed { ref part :>> owner=GambitBuildAssurance::planner.component; attribute :>> obligationId="DR-S"; attribute :>> kind="source-refinement"; attribute :>> subjectPath="dev/refactoring/modern-c/derivation-receipt-environment-design.org"; attribute :>> subjectScope="Current Gambit producers aliases and actual JSON-to-model source refinement OPEN"; attribute :>> premise="Reference protocol and admitted formal AST; no native or whole-source qualification"; }
part platform:GambitAssuranceRouting::ModelNeed { ref part :>> owner=GambitBuildAssurance::planner.component; attribute :>> obligationId="DR-E"; attribute :>> kind="environment-refinement"; attribute :>> subjectPath="dev/refactoring/modern-c/derivation-receipt-environment-design.org"; attribute :>> subjectScope="LedgerHead snapshots C11 lifetime and actual target configuration OPEN"; attribute :>> premise="Reference protocol and admitted formal AST; no native or whole-source qualification"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitDarwinForceBinding::source; }
part dependency4:GambitAssuranceRouting::NeedDependency { ref part :>> dependent=source; ref part :>> prerequisite=expression; }
}
