package GambitExitDomainDrain { private import ScalarValues::*;
part def SourceRow { attribute key:String; attribute path:String; attribute needle:String; attribute limit:String; }
part source0:SourceRow { attribute :>> key="create-thread"; attribute :>> path="evidence/research/source-references/tcl/cbf86d62348d6b052e1961b4df995960fb21545f/generic/tclEvent.c"; attribute :>> needle="Tcl_CreateThreadExitHandler("; attribute :>> limit="every registration allocates an independent node; pair equality is not identity"; }
part source1:SourceRow { attribute :>> key="delete-thread"; attribute :>> path="evidence/research/source-references/tcl/cbf86d62348d6b052e1961b4df995960fb21545f/generic/tclEvent.c"; attribute :>> needle="Tcl_DeleteThreadExitHandler("; attribute :>> limit="creating TSD lookup; first matching queued registration only"; }
part source2:SourceRow { attribute :>> key="invoke"; attribute :>> path="evidence/research/source-references/tcl/cbf86d62348d6b052e1961b4df995960fb21545f/generic/tclEvent.c"; attribute :>> needle="InvokeExitHandlers(void)"; attribute :>> limit="process-global dispatcher unlocks exitMutex around callbacks; not the thread-local synchronization contract"; }
part source3:SourceRow { attribute :>> key="pop-thread"; attribute :>> path="evidence/research/source-references/tcl/cbf86d62348d6b052e1961b4df995960fb21545f/generic/tclEvent.c"; attribute :>> needle="tsdPtr->firstExitPtr = exitPtr->nextPtr;"; attribute :>> limit="thread dispatcher removes before call; queue absence does not mean no in-flight node"; }
part source4:SourceRow { attribute :>> key="callback-thread"; attribute :>> path="evidence/research/source-references/tcl/cbf86d62348d6b052e1961b4df995960fb21545f/generic/tclEvent.c"; attribute :>> needle="exitPtr->proc(exitPtr->clientData);"; attribute :>> limit="void callback return alone is not a resource result"; }
part source5:SourceRow { attribute :>> key="free-thread"; attribute :>> path="evidence/research/source-references/tcl/cbf86d62348d6b052e1961b4df995960fb21545f/generic/tclEvent.c"; attribute :>> needle="ckfree(exitPtr);"; attribute :>> limit="node release is a distinct last use after callback"; }
part source6:SourceRow { attribute :>> key="finalize-thread"; attribute :>> path="evidence/research/source-references/tcl/cbf86d62348d6b052e1961b4df995960fb21545f/generic/tclEvent.c"; attribute :>> needle="FinalizeThread("; attribute :>> limit="no nested-finalization guard is proved by this body alone"; }
part source7:SourceRow { attribute :>> key="tail-finalizers"; attribute :>> path="evidence/research/source-references/tcl/cbf86d62348d6b052e1961b4df995960fb21545f/generic/tclEvent.c"; attribute :>> needle="TclFinalizeIOSubsystem();"; attribute :>> limit="IO, notifier, async and object finalizers follow callback drain; their producer closure remains open"; }
part source8:SourceRow { attribute :>> key="all-threads"; attribute :>> path="evidence/research/source-references/tcl/cbf86d62348d6b052e1961b4df995960fb21545f/generic/tclEvent.c"; attribute :>> needle="TclFinalizeThreadData(quick);"; attribute :>> limit="TLS-only threads exist without interpreter membership"; }
part source9:SourceRow { attribute :>> key="pure-get"; attribute :>> path="evidence/research/source-references/tcl/cbf86d62348d6b052e1961b4df995960fb21545f/generic/tclThread.c"; attribute :>> needle="TclThreadDataKeyGet("; attribute :>> limit="noncreating accessor still borrows the global native key"; }
part source10:SourceRow { attribute :>> key="creating-get"; attribute :>> path="evidence/research/source-references/tcl/cbf86d62348d6b052e1961b4df995960fb21545f/generic/tclThread.c"; attribute :>> needle="result = ckalloc(size);"; attribute :>> limit="absent data lookup allocates and zeroes payload"; }
part source11:SourceRow { attribute :>> key="tsd-detach"; attribute :>> path="evidence/research/source-references/tcl/cbf86d62348d6b052e1961b4df995960fb21545f/generic/tclThreadStorage.c"; attribute :>> needle="TclpThreadSetGlobalTSD(tsdGlobal.key, NULL);"; attribute :>> limit="old order frees table before clearing slot; proposed stronger order needs platform success evidence"; }
part source12:SourceRow { attribute :>> key="tsd-free"; attribute :>> path="evidence/research/source-references/tcl/cbf86d62348d6b052e1961b4df995960fb21545f/generic/tclThreadStorage.c"; attribute :>> needle="TSDTableDelete(tsdTablePtr);"; attribute :>> limit="deletes each stored data block and table; not allocator-cache completion"; }
part source13:SourceRow { attribute :>> key="key-delete"; attribute :>> path="evidence/research/source-references/tcl/cbf86d62348d6b052e1961b4df995960fb21545f/generic/tclThreadStorage.c"; attribute :>> needle="TclpThreadDeleteKey(tsdGlobal.key);"; attribute :>> limit="all Tcl threads finalized is a precondition, not an observed roster"; }
part source14:SourceRow { attribute :>> key="lookup-table"; attribute :>> path="evidence/research/source-references/tcl/cbf86d62348d6b052e1961b4df995960fb21545f/generic/tclThreadStorage.c"; attribute :>> needle="TSDTable *tsdTablePtr = TclpThreadGetGlobalTSD(tsdGlobal.key);"; attribute :>> limit="a no-table reader may never register an allocator cache"; }
part source15:SourceRow { attribute :>> key="create-table"; attribute :>> path="evidence/research/source-references/tcl/cbf86d62348d6b052e1961b4df995960fb21545f/generic/tclThreadStorage.c"; attribute :>> needle="tsdTablePtr = TSDTableCreate();"; attribute :>> limit="first set can allocate table and initial slot array"; }
part source16:SourceRow { attribute :>> key="condition-producer"; attribute :>> path="evidence/research/source-references/tcl/cbf86d62348d6b052e1961b4df995960fb21545f/win/tclWinThrd.c"; attribute :>> needle="Tcl_CreateThreadExitHandler(FinalizeConditionEvent, tsdPtr);"; attribute :>> limit="real producer registers outside global lock because TSD initialization can reenter it"; }
part source17:SourceRow { attribute :>> key="condition-close"; attribute :>> path="evidence/research/source-references/tcl/cbf86d62348d6b052e1961b4df995960fb21545f/win/tclWinThrd.c"; attribute :>> needle="CloseHandle(tsdPtr->condEvent);"; attribute :>> limit="return status ignored; capture exact HANDLE or transfer a stable dependency-free duty"; }
part source18:SourceRow { attribute :>> key="prior"; attribute :>> path="dev/refactoring/modern-c/models/quint/runtime_tls_ready.qnt"; attribute :>> needle="action finishFinalizer"; attribute :>> limit="actual previous finalizer and key guards; scoped join, not product simulation"; }
part def ObligationRow { attribute key:String; attribute status:String; attribute condition:String; }
part obligation0:ObligationRow { attribute :>> key="model-safety"; attribute :>> status="conditional-model"; attribute :>> condition="typed IR projection and all guarded steps preserve Safe; bounded owner and two task identities"; }
part obligation1:ObligationRow { attribute :>> key="source-order"; attribute :>> status="source-bound"; attribute :>> condition="pinned source proves pop/call/free order and creating versus pure lookup"; }
part obligation2:ObligationRow { attribute :>> key="callback-legality"; attribute :>> status="unresolved"; attribute :>> condition="close external callback producers and establish legal reentrant finalize behavior; no reached native bug claimed"; }
part obligation3:ObligationRow { attribute :>> key="subsystem-producers"; attribute :>> status="unresolved"; attribute :>> condition="close all four tail finalizers and allocate child permits while their required services remain live"; }
part obligation4:ObligationRow { attribute :>> key="resource-result"; attribute :>> status="unresolved"; attribute :>> condition="void return and ignored CloseHandle status do not supply no-TSD-dependency receipt"; }
part obligation5:ObligationRow { attribute :>> key="key-borrowers"; attribute :>> status="unresolved"; attribute :>> condition="cover TLS-only and noncreating readers, native slot clear success and global owner roster"; }
part obligation6:ObligationRow { attribute :>> key="c23-order"; attribute :>> status="unresolved"; attribute :>> condition="same-epoch release/acquire and no-abandon native tail; sequential model is not a C23 weak-memory proof"; }
part obligation7:ObligationRow { attribute :>> key="full-refinement"; attribute :>> status="unresolved"; attribute :>> condition="unbounded tasks, source allocator hooks, escape behavior and full previous-model product remain open"; }
part def RouteRow { attribute actionName:String; attribute lemma:String; attribute source:String; attribute obligation:String; }
part route0:RouteRow { attribute :>> actionName="seedRegistrationA"; attribute :>> lemma="ExitDomainDrain.seedRegistrationAPreserves"; attribute :>> source="create-thread"; attribute :>> obligation="model-safety"; }
part route1:RouteRow { attribute :>> actionName="chooseDuplicatePair"; attribute :>> lemma="ExitDomainDrain.chooseDuplicatePairPreserves"; attribute :>> source="create-thread"; attribute :>> obligation="model-safety"; }
part route2:RouteRow { attribute :>> actionName="reserveExternalB"; attribute :>> lemma="ExitDomainDrain.reserveExternalBPreserves"; attribute :>> source="create-thread"; attribute :>> obligation="model-safety"; }
part route3:RouteRow { attribute :>> actionName="beginDrain"; attribute :>> lemma="ExitDomainDrain.beginDrainPreserves"; attribute :>> source="invoke"; attribute :>> obligation="model-safety"; }
part route4:RouteRow { attribute :>> actionName="reserveChildB"; attribute :>> lemma="ExitDomainDrain.reserveChildBPreserves"; attribute :>> source="create-thread"; attribute :>> obligation="model-safety"; }
part route5:RouteRow { attribute :>> actionName="reserveTailB"; attribute :>> lemma="ExitDomainDrain.reserveTailBPreserves"; attribute :>> source="condition-producer"; attribute :>> obligation="model-safety"; }
part route6:RouteRow { attribute :>> actionName="publishBKnown"; attribute :>> lemma="ExitDomainDrain.publishBKnownPreserves"; attribute :>> source="create-thread"; attribute :>> obligation="model-safety"; }
part route7:RouteRow { attribute :>> actionName="publishBUnknown"; attribute :>> lemma="ExitDomainDrain.publishBUnknownPreserves"; attribute :>> source="create-thread"; attribute :>> obligation="model-safety"; }
part route8:RouteRow { attribute :>> actionName="publicationAbsentUnknown"; attribute :>> lemma="ExitDomainDrain.publicationAbsentUnknownPreserves"; attribute :>> source="create-thread"; attribute :>> obligation="model-safety"; }
part route9:RouteRow { attribute :>> actionName="reconcileAcceptedB"; attribute :>> lemma="ExitDomainDrain.reconcileAcceptedBPreserves"; attribute :>> source="prior"; attribute :>> obligation="model-safety"; }
part route10:RouteRow { attribute :>> actionName="reconcileAbsentAndRolledBackB"; attribute :>> lemma="ExitDomainDrain.reconcileAbsentAndRolledBackBPreserves"; attribute :>> source="prior"; attribute :>> obligation="model-safety"; }
part route11:RouteRow { attribute :>> actionName="popA"; attribute :>> lemma="ExitDomainDrain.popAPreserves"; attribute :>> source="pop-thread"; attribute :>> obligation="model-safety"; }
part route12:RouteRow { attribute :>> actionName="popB"; attribute :>> lemma="ExitDomainDrain.popBPreserves"; attribute :>> source="pop-thread"; attribute :>> obligation="model-safety"; }
part route13:RouteRow { attribute :>> actionName="returnA"; attribute :>> lemma="ExitDomainDrain.returnAPreserves"; attribute :>> source="callback-thread"; attribute :>> obligation="model-safety"; }
part route14:RouteRow { attribute :>> actionName="returnB"; attribute :>> lemma="ExitDomainDrain.returnBPreserves"; attribute :>> source="callback-thread"; attribute :>> obligation="model-safety"; }
part route15:RouteRow { attribute :>> actionName="callbackUnknownA"; attribute :>> lemma="ExitDomainDrain.callbackUnknownAPreserves"; attribute :>> source="callback-thread"; attribute :>> obligation="model-safety"; }
part route16:RouteRow { attribute :>> actionName="freeNodeAKnown"; attribute :>> lemma="ExitDomainDrain.freeNodeAKnownPreserves"; attribute :>> source="free-thread"; attribute :>> obligation="model-safety"; }
part route17:RouteRow { attribute :>> actionName="freeNodeBKnown"; attribute :>> lemma="ExitDomainDrain.freeNodeBKnownPreserves"; attribute :>> source="free-thread"; attribute :>> obligation="model-safety"; }
part route18:RouteRow { attribute :>> actionName="freeNodeAUnknown"; attribute :>> lemma="ExitDomainDrain.freeNodeAUnknownPreserves"; attribute :>> source="free-thread"; attribute :>> obligation="model-safety"; }
part route19:RouteRow { attribute :>> actionName="freeNodeBUnknown"; attribute :>> lemma="ExitDomainDrain.freeNodeBUnknownPreserves"; attribute :>> source="free-thread"; attribute :>> obligation="model-safety"; }
part route20:RouteRow { attribute :>> actionName="cancelNewestDuplicateB"; attribute :>> lemma="ExitDomainDrain.cancelNewestDuplicateBPreserves"; attribute :>> source="delete-thread"; attribute :>> obligation="model-safety"; }
part route21:RouteRow { attribute :>> actionName="cancelQueuedA"; attribute :>> lemma="ExitDomainDrain.cancelQueuedAPreserves"; attribute :>> source="delete-thread"; attribute :>> obligation="model-safety"; }
part route22:RouteRow { attribute :>> actionName="reentrantFinalizeJoin"; attribute :>> lemma="ExitDomainDrain.reentrantFinalizeJoinPreserves"; attribute :>> source="finalize-thread"; attribute :>> obligation="model-safety"; }
part route23:RouteRow { attribute :>> actionName="beginSubsystemTail"; attribute :>> lemma="ExitDomainDrain.beginSubsystemTailPreserves"; attribute :>> source="tail-finalizers"; attribute :>> obligation="model-safety"; }
part route24:RouteRow { attribute :>> actionName="finishSubsystemTail"; attribute :>> lemma="ExitDomainDrain.finishSubsystemTailPreserves"; attribute :>> source="tail-finalizers"; attribute :>> obligation="model-safety"; }
part route25:RouteRow { attribute :>> actionName="closeProducers"; attribute :>> lemma="ExitDomainDrain.closeProducersPreserves"; attribute :>> source="tail-finalizers"; attribute :>> obligation="model-safety"; }
part route26:RouteRow { attribute :>> actionName="attestNoTsdDependencies"; attribute :>> lemma="ExitDomainDrain.attestNoTsdDependenciesPreserves"; attribute :>> source="condition-close"; attribute :>> obligation="model-safety"; }
part route27:RouteRow { attribute :>> actionName="acquireLookup"; attribute :>> lemma="ExitDomainDrain.acquireLookupPreserves"; attribute :>> source="pure-get"; attribute :>> obligation="model-safety"; }
part route28:RouteRow { attribute :>> actionName="lookupAbsent"; attribute :>> lemma="ExitDomainDrain.lookupAbsentPreserves"; attribute :>> source="pure-get"; attribute :>> obligation="model-safety"; }
part route29:RouteRow { attribute :>> actionName="releaseLookup"; attribute :>> lemma="ExitDomainDrain.releaseLookupPreserves"; attribute :>> source="pure-get"; attribute :>> obligation="model-safety"; }
part route30:RouteRow { attribute :>> actionName="detachTableSlot"; attribute :>> lemma="ExitDomainDrain.detachTableSlotPreserves"; attribute :>> source="tsd-detach"; attribute :>> obligation="model-safety"; }
part route31:RouteRow { attribute :>> actionName="freeTsdData"; attribute :>> lemma="ExitDomainDrain.freeTsdDataPreserves"; attribute :>> source="tsd-free"; attribute :>> obligation="model-safety"; }
part route32:RouteRow { attribute :>> actionName="issueDataDrainReceipt"; attribute :>> lemma="ExitDomainDrain.issueDataDrainReceiptPreserves"; attribute :>> source="tsd-free"; attribute :>> obligation="model-safety"; }
part route33:RouteRow { attribute :>> actionName="cancelAbsentFromReceipt"; attribute :>> lemma="ExitDomainDrain.cancelAbsentFromReceiptPreserves"; attribute :>> source="delete-thread"; attribute :>> obligation="model-safety"; }
part route34:RouteRow { attribute :>> actionName="attestCacheAndOwnerRoster"; attribute :>> lemma="ExitDomainDrain.attestCacheAndOwnerRosterPreserves"; attribute :>> source="all-threads"; attribute :>> obligation="model-safety"; }
part route35:RouteRow { attribute :>> actionName="deleteGenericKey"; attribute :>> lemma="ExitDomainDrain.deleteGenericKeyPreserves"; attribute :>> source="key-delete"; attribute :>> obligation="model-safety"; }
part def GainRow { attribute key:String; attribute saved:String; attribute added:String; attribute condition:String; attribute status:String; }
part gain0:GainRow { attribute :>> key="absent-delete"; attribute :>> saved="one data payload allocation plus memset; conditional two initial TSD table allocations and growth/bootstrap"; attribute :>> added="owner/key admission and stable absence receipt"; attribute :>> condition="no existing event data; managed noncreating path; table allocations only if table absent"; attribute :>> status="source-count conditional; no timing"; }
part gain1:GainRow { attribute :>> key="one-drain"; attribute :>> saved="avoidable TSD recreation and repeated teardown within admitted domain"; attribute :>> added="per-registration identity, pre-pop escrow, tail permits and reconciliation"; attribute :>> condition="all producers closed, unknown duties retained; no deletion retry by raw address"; attribute :>> status="architectural potential; no finite repeat bound proved"; }
part gain2:GainRow { attribute :>> key="native-resource"; attribute :>> saved="no speculative double close or premature TSD release"; attribute :>> added="resource-specific status or independent duty transfer"; attribute :>> condition="capture exact handle while TSD live; record must not retain retiring TSD"; attribute :>> status="correctness boundary; source status missing"; }
part gain3:GainRow { attribute :>> key="roster"; attribute :>> saved="no cache allocation merely to track a key-only reader"; attribute :>> added="transient key lease plus external all-owner receipt"; attribute :>> condition="cache and interpreter lists cannot stand in for key borrowers"; attribute :>> status="potential; caller closure unresolved"; }
part gain4:GainRow { attribute :>> key="language"; attribute :>> saved="zero demonstrated Zig-exclusive runtime obligations"; attribute :>> added="same C23 runtime contracts; optional Zig ABI/toolchain adds independent cost"; attribute :>> condition="compare same architecture; language cannot close callback or OS status gaps"; attribute :>> status="C23 mandatory; Zig benefit not established"; }
part def IssuerRow { attribute key:String; attribute source:String; attribute signature:String; attribute gap:String; }
part issuer0:IssuerRow { attribute :>> key="registration"; attribute :>> source="create-thread"; attribute :>> signature="owner assigns a serial per actual registration; delivery retry resolves same ticket"; attribute :>> gap="no pair-key dedup; no native serial exists yet"; }
part issuer1:IssuerRow { attribute :>> key="inflight"; attribute :>> source="pop-thread"; attribute :>> signature="stable pre-pop owner takes callback and node obligations before unlink"; attribute :>> gap="nonlocal exit must retain independent record"; }
part issuer2:IssuerRow { attribute :>> key="resource"; attribute :>> source="condition-close"; attribute :>> signature="resource owner proves closed or transfer without any retiring TSD dependency"; attribute :>> gap="ignored status cannot be promoted to success"; }
part issuer3:IssuerRow { attribute :>> key="data-drain"; attribute :>> source="tsd-free"; attribute :>> signature="owner closes producers, resolves operations, drains lookup pins, detaches slot then frees data"; attribute :>> gap="not a cache or global key receipt"; }
part issuer4:IssuerRow { attribute :>> key="global-key"; attribute :>> source="key-delete"; attribute :>> signature="runtime coordinator combines owner data drains, cache drains and transient key borrowers"; attribute :>> gap="global roster source precondition remains unproved"; }
part def ConsumerRow { attribute key:String; attribute source:String; attribute access:String; attribute lifetime:String; attribute limit:String; }
part consumer0:ConsumerRow { attribute :>> key="thread-dispatch"; attribute :>> source="finalize-thread"; attribute :>> access="owner-local list and callback data"; attribute :>> lifetime="through callback and node completion"; attribute :>> limit="no holding a service lock across arbitrary callback"; }
part consumer1:ConsumerRow { attribute :>> key="global-dispatch"; attribute :>> source="invoke"; attribute :>> access="global list under exitMutex; callbacks outside lock"; attribute :>> lifetime="independent process-global admission"; attribute :>> limit="not automatically covered by owner-local model"; }
part consumer2:ConsumerRow { attribute :>> key="windows-condition"; attribute :>> source="condition-producer"; attribute :>> access="ClientData points to Windows TSD; callback reads flags and condEvent"; attribute :>> lifetime="until exact resource duty is settled or transferred"; attribute :>> limit="callback is not proof of CloseHandle success"; }
part consumer3:ConsumerRow { attribute :>> key="key-only-reader"; attribute :>> source="lookup-table"; attribute :>> access="native key get without table/cache creation"; attribute :>> lifetime="lookup pin before metadata load until last use"; attribute :>> limit="requires roster outside cache list"; }
part consumer4:ConsumerRow { attribute :>> key="subsystem-tail"; attribute :>> source="tail-finalizers"; attribute :>> access="four native finalizers after initial callback loop"; attribute :>> lifetime="producer permits through spawned work"; attribute :>> limit="cannot reorder handlers behind destroyed services indiscriminately"; }
part def WriterRow { attribute key:String; attribute source:String; attribute access:String; attribute closure:String; attribute limit:String; }
part writer0:WriterRow { attribute :>> key="registration-push"; attribute :>> source="create-thread"; attribute :>> access="new nextPtr then head store"; attribute :>> closure="owner external gate plus admitted descendant permit"; attribute :>> limit="reentrant allocator hooks not closed"; }
part writer1:WriterRow { attribute :>> key="cancel-unlink"; attribute :>> source="delete-thread"; attribute :>> access="first matching queued node unlink then free"; attribute :>> closure="per-registration stable duty after unlink"; attribute :>> limit="pair can designate another queued duplicate"; }
part writer2:WriterRow { attribute :>> key="dispatch-pop"; attribute :>> source="pop-thread"; attribute :>> access="head moved before callback"; attribute :>> closure="stable in-flight owner"; attribute :>> limit="empty queue not complete"; }
part writer3:WriterRow { attribute :>> key="table-install"; attribute :>> source="create-table"; attribute :>> access="native TSD install, offset and table slot writes"; attribute :>> closure="key lease and owner phase"; attribute :>> limit="native void setter outcome unresolved"; }
part writer4:WriterRow { attribute :>> key="table-retire"; attribute :>> source="tsd-free"; attribute :>> access="free then clear in old code"; attribute :>> closure="proposed detach-before-free with no readers"; attribute :>> limit="must preserve provenance and resolve clear outcome"; }
part writer5:WriterRow { attribute :>> key="condition-event"; attribute :>> source="condition-close"; attribute :>> access="flags reset then CloseHandle without status check"; attribute :>> closure="resource-specific result not callback return"; attribute :>> limit="tail callbacks creating another event not shown reachable"; }
part def RefinementRow { attribute key:String; attribute lemma:String; attribute source:String; attribute premise:String; }
part refinement0:RefinementRow { attribute :>> key="no-inflight"; attribute :>> lemma="ExitDomainDrain.drainedHasNoInFlight"; attribute :>> source="pop-thread"; attribute :>> premise="faithful task/state mapping and external receipt authorities"; }
part refinement1:RefinementRow { attribute :>> key="unknown-duty"; attribute :>> lemma="ExitDomainDrain.unknownRetainsCustody"; attribute :>> source="free-thread"; attribute :>> premise="unknown is not retried or declared success"; }
part refinement2:RefinementRow { attribute :>> key="lookup-key"; attribute :>> lemma="ExitDomainDrain.liveLookupRetainsKey"; attribute :>> source="pure-get"; attribute :>> premise="every native key user admitted before metadata loads"; }
part refinement3:RefinementRow { attribute :>> key="local-receipt"; attribute :>> lemma="ExitDomainDrain.dataReceiptIsLocal"; attribute :>> source="tsd-free"; attribute :>> premise="local data does not imply all caches and owners complete"; }
part refinement4:RefinementRow { attribute :>> key="global-key"; attribute :>> lemma="ExitDomainDrain.keyRetiredRequiresRoster"; attribute :>> source="key-delete"; attribute :>> premise="external roster authority; model does not invent it"; }
part refinement5:RefinementRow { attribute :>> key="no-create"; attribute :>> lemma="ExitDomainDrain.absentLookupDoesNotAllocate"; attribute :>> source="pure-get"; attribute :>> premise="native getter itself bound; admission may add storage cost"; }
part refinement6:RefinementRow { attribute :>> key="duplicate"; attribute :>> lemma="ExitDomainDrain.duplicateCancelDoesNotFinishActive"; attribute :>> source="delete-thread"; attribute :>> premise="two distinct registrations may carry same pair"; }
part refinement7:RefinementRow { attribute :>> key="parent-join"; attribute :>> lemma="ExitDomainDrain.guardedPriorFinish"; attribute :>> source="prior"; attribute :>> premise="explicit same-epoch mirror and actual previous finishFinalizer guard"; }
part def EdgeRow { attribute fromNode:String; attribute toNode:String; attribute contract:String; }
part edge0:EdgeRow { attribute :>> fromNode="external gate"; attribute :>> toNode="registration serial"; attribute :>> contract="close admission; no pair dedup"; }
part edge1:EdgeRow { attribute :>> fromNode="registration serial"; attribute :>> toNode="in-flight escrow"; attribute :>> contract="retain operation ACK beyond node lifetime"; }
part edge2:EdgeRow { attribute :>> fromNode="in-flight escrow"; attribute :>> toNode="callback result"; attribute :>> contract="pop is not completion"; }
part edge3:EdgeRow { attribute :>> fromNode="callback result"; attribute :>> toNode="node free result"; attribute :>> contract="separate last uses"; }
part edge4:EdgeRow { attribute :>> fromNode="tail finalizers"; attribute :>> toNode="registration serial"; attribute :>> contract="descendant producer permit while services live"; }
part edge5:EdgeRow { attribute :>> fromNode="node free result"; attribute :>> toNode="producer closure"; attribute :>> contract="all known done; no unresolved publication"; }
part edge6:EdgeRow { attribute :>> fromNode="producer closure"; attribute :>> toNode="key reader drain"; attribute :>> contract="close key gate; wait admitted lookups"; }
part edge7:EdgeRow { attribute :>> fromNode="Windows resource duty"; attribute :>> toNode="TSD detach"; attribute :>> contract="no retiring-data dependency"; }
part edge8:EdgeRow { attribute :>> fromNode="key reader drain"; attribute :>> toNode="TSD detach"; attribute :>> contract="same epoch release/acquire"; }
part edge9:EdgeRow { attribute :>> fromNode="TSD detach"; attribute :>> toNode="local data receipt"; attribute :>> contract="clear known before free"; }
part edge10:EdgeRow { attribute :>> fromNode="local data receipt"; attribute :>> toNode="cache and owner roster"; attribute :>> contract="independent external authority"; }
part edge11:EdgeRow { attribute :>> fromNode="cache and owner roster"; attribute :>> toNode="generic key retirement"; attribute :>> contract="all TLS users including no-table readers"; }
}
