package GambitSnapshotObserverRefinement { private import ScalarValues::*;
part def Route { attribute key:String; attribute sourcePath:String; attribute needle:String; attribute obligation:String; }
part route0:Route { attribute :>> key="existing-local-queues"; attribute :>> sourcePath="vendor/gambit/lib/mem.c"; attribute :>> needle="heap_chunks_to_scan_tail = new_tail;"; attribute :>> obligation="Per-processor FIFO is already distributed; a new global ledger is not an existing runtime facility"; }
part route1:Route { attribute :>> key="claim-before-scan"; attribute :>> sourcePath="vendor/gambit/lib/mem.c"; attribute :>> needle="scan_complete_heap_chunk (___PSP ptr+1);"; attribute :>> obligation="Dequeued work still owns payload and may derive tasks"; }
part route2:Route { attribute :>> key="global-cut"; attribute :>> sourcePath="vendor/gambit/lib/mem.c"; attribute :>> needle="if (--(*workers_count) == 0)"; attribute :>> obligation="Mutex/worker termination is not a snapshot/observer grace period"; }
part route3:Route { attribute :>> key="descriptor-borrow"; attribute :>> sourcePath="vendor/gambit/lib/mem.c"; attribute :>> needle="descriptor = ___decode_frame_descriptor (___LABEL_DESCR_GET(actual_ra), 1);"; attribute :>> obligation="Trailing OFD map pointer remains borrowed after decoder returns"; }
part route4:Route { attribute :>> key="phase-gc-storage"; attribute :>> sourcePath="vendor/gambit/lib/mem.c"; attribute :>> needle="___HIDDEN void free_unmarked_still_objs"; attribute :>> obligation="Scheme collector ownership and native snapshot reclamation are distinct contracts"; }
part route5:Route { attribute :>> key="native-final-use"; attribute :>> sourcePath="vendor/gambit/lib/os_dyn.c"; attribute :>> needle="dlclose (p->descr);"; attribute :>> obligation="Global unload needs old activation/root/inspection/native closure; snapshot zero alone is insufficient"; }
part route6:Route { attribute :>> key="exception-cleanup"; attribute :>> sourcePath="vendor/gambit/include/gambit.h.in"; attribute :>> needle="___ps->catcher = ___old_catcher"; attribute :>> obligation="Snapshot pin cannot be lost through an exception or multi-shot callback"; }
part route7:Route { attribute :>> key="lookup-producer"; attribute :>> sourcePath="/opt/homebrew/Cellar/quint/0.33.0/libexec/lib/node_modules/@informalsystems/quint/dist/src/names/resolver.js"; attribute :>> needle="this.table.set(id, def);"; attribute :>> obligation="Occurrence-ID witness requires exact canonical declaration"; }
part route8:Route { attribute :>> key="lookup-consumer"; attribute :>> sourcePath="/opt/homebrew/Cellar/quint/0.33.0/libexec/lib/node_modules/@informalsystems/quint/dist/src/runtime/impl/builder.js"; attribute :>> needle="const def = builder.table.get(expr.id);"; attribute :>> obligation="Lookup function must have no fabricated bindings beyond selected witness rows"; }
part route9:Route { attribute :>> key="json-gate"; attribute :>> sourcePath="dev/modeling/tools/typed-binding-witness.py"; attribute :>> needle="refs.append(dict(occurrence=oid,target=target"; attribute :>> obligation="Pinned input gate is executable checking, not a verified parser"; }
part route10:Route { attribute :>> key="parent-environment"; attribute :>> sourcePath="dev/refactoring/modern-c/models/lean/DerivationReceiptEnvironment.lean"; attribute :>> needle="theorem checkedEnvironment"; attribute :>> obligation="Reuse existing row-to-function theorem, then prove converse finite-domain direction"; }
part route11:Route { attribute :>> key="frozen-input"; attribute :>> sourcePath="evidence/research/reti-ofd-semantics/typed-ir.json"; attribute :>> needle="\"typechecking\""; attribute :>> obligation="91 map witness rows remain a separate input from snapshot protocol IR"; }
part def Contract { ref part accountable:GambitRuntimeComposition::BlueprintModule; ref part counterpart:GambitRuntimeComposition::BlueprintModule; attribute key:String; attribute owner:String; attribute actionName:String; attribute invariant:String; attribute gap:String; }
part contract0:Contract { ref part :>> accountable=GambitRuntimeComposition::blueprintModule1; ref part :>> counterpart=GambitRuntimeComposition::blueprintModule3; attribute :>> key="snapshot-pin"; attribute :>> owner="native/roots"; attribute :>> actionName="publishPin validatePin scan freeSnapshot"; attribute :>> invariant="Publish pin then revalidate same generation; final dereference precedes pin clear"; attribute :>> gap="Reference SC order and stable slot roster must be refined to actual C11"; }
part contract1:Contract { ref part :>> accountable=GambitRuntimeComposition::blueprintModule7; ref part :>> counterpart=GambitRuntimeComposition::blueprintModule8; attribute :>> key="observer-lifetime"; attribute :>> owner="release/build"; attribute :>> actionName="beginObserver closeObservers freeReceipt"; attribute :>> invariant="Admission close prevents new readers; old readers and pending delivery drain separately"; attribute :>> gap="Receipt identity directory and terminal tombstones require real source users"; }
part contract2:Contract { ref part :>> accountable=GambitRuntimeComposition::blueprintModule7; ref part :>> counterpart=GambitRuntimeComposition::blueprintModule1; attribute :>> key="code-detachment"; attribute :>> owner="release/native"; attribute :>> actionName="certifyDetached freeCode"; attribute :>> invariant="Data-only observer may outlive code only with a semantic detachment certificate"; attribute :>> gap="Idle execution or zero debt alone cannot sign certificate"; }
part contract3:Contract { ref part :>> accountable=GambitRuntimeComposition::blueprintModule4; ref part :>> counterpart=GambitRuntimeComposition::blueprintModule3; attribute :>> key="batch-refinement"; attribute :>> owner="collector/roots"; attribute :>> actionName="batch reserveA reserveB"; attribute :>> invariant="Disjoint updates commute; batch serializes legal guarded per-ticket operations"; attribute :>> gap="Arbitrary batches effects failures and observer histories remain open"; }
part contract4:Contract { ref part :>> accountable=GambitRuntimeComposition::blueprintModule4; ref part :>> counterpart=GambitRuntimeComposition::blueprintModule5; attribute :>> key="shard-cut"; attribute :>> owner="collector/control"; attribute :>> actionName="reserveTarget releaseSource sealA sealB retire"; attribute :>> invariant="Target reservation overlaps source debt; closed target rejects transfer without dropping source"; attribute :>> gap="Split target/source atomic steps need TaskId receipts and unknown-response refinement; complete global cut open"; }
part contract5:Contract { ref part :>> accountable=GambitRuntimeComposition::blueprintModule8; ref part :>> counterpart=GambitRuntimeComposition::blueprintModule0; attribute :>> key="finite-domain"; attribute :>> owner="modeling/build"; attribute :>> actionName="buildEnv tableCheck"; attribute :>> invariant="Lookup result iff matching admitted row under tableCheck"; attribute :>> gap="Authentic JSON row construction and field-slot mapping remain trusted"; }
part def Obligation { attribute key:String; attribute status:String; attribute scope:String; attribute counterexample:String; }
part obligation0:Obligation { attribute :>> key="pin-order"; attribute :>> status="conditional-proved"; attribute :>> scope="SC event-order cycle impossible under stable slots no ABA and no early clear"; attribute :>> counterexample="Release/acquire alone on unrelated atomics does not establish the needed order"; }
part obligation1:Obligation { attribute :>> key="three-lifetimes"; attribute :>> status="bounded-checked"; attribute :>> scope="One old snapshot one observer one cohort; detached certificate is an explicit premise"; attribute :>> counterexample="Free receipt with an admitted observer or free code with an undetached observer"; }
part obligation2:Obligation { attribute :>> key="batch-algebra"; attribute :>> status="conditional-proved"; attribute :>> scope="Two disjoint debt updates commute and equal explicit batch update"; attribute :>> counterexample="Cross-task read/effect or partial failure invalidates this argument"; }
part obligation3:Obligation { attribute :>> key="transfer-overlap"; attribute :>> status="conditional-proved"; attribute :>> scope="Two-shard reservation overlap preserves logical ownership; finite transfer cases checked"; attribute :>> counterexample="Release source before reserve target loses ownership"; }
part obligation4:Obligation { attribute :>> key="actual-guards"; attribute :>> status="conditional-proved"; attribute :>> scope="Three actual snapshot QNT guard/update expressions match Lean PinFlat"; attribute :>> counterexample="Parser/emitter trusted; no whole protocol history proof"; }
part obligation5:Obligation { attribute :>> key="c11-source"; attribute :>> status="open"; attribute :>> scope="Hazard membership ABA native aliases root/FFI cleanup actual final use and target memory model"; attribute :>> counterexample="SC arithmetic theorem is not a C11 race-freedom proof"; }
part obligation6:Obligation { attribute :>> key="json-meaning"; attribute :>> status="partially-proved"; attribute :>> scope="91-row environment consistency plus exact finite-domain theorem"; attribute :>> counterexample="Consistently forged rows still require independent JSON witness validation"; }
part def Gain { attribute key:String; attribute avoided:String; attribute added:String; attribute condition:String; }
part gain0:Gain { attribute :>> key="pin-reclamation"; attribute :>> avoided="Permanent retention of every detached metadata snapshot"; attribute :>> added="Pin publication validation scan of stable slots retired lists and controlled free work"; attribute :>> condition="Unknown or stalled holders keep storage; no bounded memory claim"; }
part gain1:Gain { attribute :>> key="receipt-detachment"; attribute :>> avoided="Keeping old code solely for terminal data-only queries"; attribute :>> added="Separate observer leases and certificate that no old code Scheme value or OFD can be accessed"; attribute :>> condition="Certificate must cover future as well as active observers"; }
part gain2:Gain { attribute :>> key="batch-head-writes"; attribute :>> avoided="k*(D-ceil(D/b)) child-phase successful global commits may be removed"; attribute :>> added="Membership freeze per-ticket result vector waiting and reclaim-tail work"; attribute :>> condition="Only k legal batchable phases among four; no elapsed-time percentage"; }
part gain3:Gain { attribute :>> key="shard-contention"; attribute :>> avoided="One mandatory global head on every local operation"; attribute :>> added="Transfer overlap two reservations close/seal coordination and imbalance"; attribute :>> condition="Maximum shard load and global cut cost must beat centralized serialization"; }
part gain4:Gain { attribute :>> key="existing-reuse"; attribute :>> avoided="Replacing already distributed FIFO with a new contention point"; attribute :>> added="Preserve current local queue structure while changing ownership and cut contracts"; attribute :>> condition="No existing queue or counter retires until actual consumer refinement"; }
part def Binding { attribute key:String; attribute qntAction:String; attribute leanLemma:String; attribute refinement:String; attribute guardLemma:String; attribute updateLemma:String; }
part binding0:Binding { attribute :>> key="pin"; attribute :>> qntAction="publishPin"; attribute :>> leanLemma="pinOrderCannotMiss"; attribute :>> refinement="Generated guard/update relation checked; SC order premises remain external"; attribute :>> guardLemma="publishPinGuardMeaning"; attribute :>> updateLemma="publishPinNextMeaning"; }
part binding1:Binding { attribute :>> key="validation"; attribute :>> qntAction="validatePin"; attribute :>> leanLemma="pinOrderCannotMiss"; attribute :>> refinement="Actual revalidation guard checked; full C11 lifetime still open"; attribute :>> guardLemma="validatePinGuardMeaning"; attribute :>> updateLemma="validatePinNextMeaning"; }
part binding2:Binding { attribute :>> key="receipt"; attribute :>> qntAction="freeReceipt"; attribute :>> leanLemma="observerBlocksReceipt"; attribute :>> refinement="Current guard rejects admitted observer; source lease coverage still open"; attribute :>> guardLemma="freeReceiptGuardMeaning"; attribute :>> updateLemma="freeReceiptNextMeaning"; }
part def Flow { attribute fromNode:String; attribute toNode:String; attribute reason:String; }
part flow0:Flow { attribute :>> fromNode="c0"; attribute :>> toNode="o0"; attribute :>> reason="SC order obligation"; }
part flow1:Flow { attribute :>> fromNode="c0"; attribute :>> toNode="o4"; attribute :>> reason="Actual typed-IR guards"; }
part flow2:Flow { attribute :>> fromNode="c1"; attribute :>> toNode="o1"; attribute :>> reason="Admission and late-reader histories"; }
part flow3:Flow { attribute :>> fromNode="c2"; attribute :>> toNode="o1"; attribute :>> reason="Separate code and receipt lifetimes"; }
part flow4:Flow { attribute :>> fromNode="c2"; attribute :>> toNode="o5"; attribute :>> reason="Certificate needs source closure"; }
part flow5:Flow { attribute :>> fromNode="c3"; attribute :>> toNode="o2"; attribute :>> reason="Batch commutation proof"; }
part flow6:Flow { attribute :>> fromNode="c4"; attribute :>> toNode="o3"; attribute :>> reason="Transfer accounting proof"; }
part flow7:Flow { attribute :>> fromNode="c4"; attribute :>> toNode="o5"; attribute :>> reason="All shard producers must close"; }
part flow8:Flow { attribute :>> fromNode="c5"; attribute :>> toNode="o6"; attribute :>> reason="Exact finite-domain proof"; }
part flow9:Flow { attribute :>> fromNode="o4"; attribute :>> toNode="o5"; attribute :>> reason="Actual syntax certificate is not C11 proof"; }
part flow10:Flow { attribute :>> fromNode="o2"; attribute :>> toNode="c4"; attribute :>> reason="Sharding must preserve legal task histories"; }
part flow11:Flow { attribute :>> fromNode="c1"; attribute :>> toNode="c2"; attribute :>> reason="Observer admission controls possible future code access"; }
part history:GambitAssuranceRouting::ModelNeed { ref part :>> owner=GambitBuildAssurance::planner.component; attribute :>> obligationId="SO-H"; attribute :>> kind="interleaving"; attribute :>> subjectPath="dev/refactoring/modern-c/models/quint/snapshot_observer.qnt"; attribute :>> subjectScope="Finite SC pin and three-lifetime admission/retirement protocol"; attribute :>> premise="Bounded models and restricted algebra only; no runtime implementation or native acceptance"; }
part shards:GambitAssuranceRouting::ModelNeed { ref part :>> owner=GambitBuildAssurance::planner.component; attribute :>> obligationId="SO-B"; attribute :>> kind="interleaving"; attribute :>> subjectPath="dev/refactoring/modern-c/models/quint/shard_retirement_cut.qnt"; attribute :>> subjectScope="Two-shard overlap handoff closed-target rejection and final seal cut"; attribute :>> premise="Bounded models and restricted algebra only; no runtime implementation or native acceptance"; }
part induction:GambitAssuranceRouting::ModelNeed { ref part :>> owner=GambitBuildAssurance::planner.component; attribute :>> obligationId="SO-I"; attribute :>> kind="induction"; attribute :>> subjectPath="dev/refactoring/modern-c/models/lean/SnapshotObserverRefinement.lean"; attribute :>> subjectScope="SC order arithmetic batch/transfer algebra and exact finite-domain lookup"; attribute :>> premise="Bounded models and restricted algebra only; no runtime implementation or native acceptance"; }
part expression:GambitAssuranceRouting::ModelNeed { ref part :>> owner=GambitBuildAssurance::planner.component; attribute :>> obligationId="SO-X"; attribute :>> kind="induction"; attribute :>> subjectPath="dev/refactoring/modern-c/models/lean/SnapshotObserverAst.lean"; attribute :>> subjectScope="Actual three snapshot action guard/update certificates and 91-row witness"; attribute :>> premise="Bounded models and restricted algebra only; no runtime implementation or native acceptance"; }
part source:GambitAssuranceRouting::ModelNeed { ref part :>> owner=GambitBuildAssurance::planner.component; attribute :>> obligationId="SO-S"; attribute :>> kind="source-refinement"; attribute :>> subjectPath="dev/refactoring/modern-c/snapshot-observer-refinement-design.org"; attribute :>> subjectScope="All actual roots snapshots observers shard producers and JSON/source relation OPEN"; attribute :>> premise="Bounded models and restricted algebra only; no runtime implementation or native acceptance"; }
part platform:GambitAssuranceRouting::ModelNeed { ref part :>> owner=GambitBuildAssurance::planner.component; attribute :>> obligationId="SO-E"; attribute :>> kind="environment-refinement"; attribute :>> subjectPath="dev/refactoring/modern-c/snapshot-observer-refinement-design.org"; attribute :>> subjectScope="C11 hazard slot roster ABA directory and target/runtime evidence OPEN"; attribute :>> premise="Bounded models and restricted algebra only; no runtime implementation or native acceptance"; }
part dependency0:GambitAssuranceRouting::NeedDependency { ref part :>> dependent=source; ref part :>> prerequisite=history; }
part dependency1:GambitAssuranceRouting::NeedDependency { ref part :>> dependent=source; ref part :>> prerequisite=induction; }
part dependency2:GambitAssuranceRouting::NeedDependency { ref part :>> dependent=source; ref part :>> prerequisite=platform; }
part dependency3:GambitAssuranceRouting::NeedDependency { ref part :>> dependent=source; ref part :>> prerequisite=GambitDerivationReceiptEnvironment::source; }
part dependency4:GambitAssuranceRouting::NeedDependency { ref part :>> dependent=source; ref part :>> prerequisite=expression; }
part dependency5:GambitAssuranceRouting::NeedDependency { ref part :>> dependent=source; ref part :>> prerequisite=shards; }
}
