package GambitNativePrefixPermission { private import ScalarValues::*;
part def SourceRow { attribute key:String; attribute path:String; attribute needle:String; attribute limit:String; }
part source0:SourceRow { attribute :>> key="begin"; attribute :>> path="vendor/gambit/lib/c_intf.c"; attribute :>> needle="___EXP_FUNC(___SCMOBJ,___begin_sfun)"; attribute :>> limit="source borrow, bank allocation, reload and registration order"; }
part source1:SourceRow { attribute :>> key="raw-prefix"; attribute :>> path="vendor/gambit/include/_gambit/foreign_conversion.h.in"; attribute :>> needle="#define ___BEGIN_SFUN_ARG_SCMOBJ(i)"; attribute :>> limit="raw input publication before other representations"; }
part source2:SourceRow { attribute :>> key="sort"; attribute :>> path="vendor/gambit/gsc/_ptree2.scm"; attribute :>> needle="(append (keep scmobj-typ? numbered-param-typs)"; attribute :>> limit="resolved SCMOBJ types come first"; }
part source3:SourceRow { attribute :>> key="custom-converter"; attribute :>> path="vendor/gambit/gsc/_ptree2.scm"; attribute :>> needle="(vector-ref def 2)"; attribute :>> limit="registered C type converter emits arbitrary named C call"; }
part source4:SourceRow { attribute :>> key="rc-alloc"; attribute :>> path="vendor/gambit/lib/_mem/rc-allocation.inc"; attribute :>> needle="h = ___CAST(___rc_header*, ___ALLOC_MEM"; attribute :>> limit="native allocation before header initialization"; }
part source5:SourceRow { attribute :>> key="rc-bank"; attribute :>> path="vendor/gambit/lib/_mem/rc-allocation.inc"; attribute :>> needle="void *___alloc_rc_roots"; attribute :>> limit="FAL initialization and root_count publication under gate"; }
part source6:SourceRow { attribute :>> key="rc-borrow"; attribute :>> path="vendor/gambit/lib/_mem/rc-allocation.inc"; attribute :>> needle="___SCMOBJ *___borrow_rc_root"; attribute :>> limit="root-cell lifetime and same-context checks"; }
part source7:SourceRow { attribute :>> key="rc-return"; attribute :>> path="vendor/gambit/lib/_mem/rc-allocation.inc"; attribute :>> needle="void ___return_rc_root"; attribute :>> limit="valid return may reach free; invalid custody calls fatal path"; }
part source8:SourceRow { attribute :>> key="malloc"; attribute :>> path="vendor/gambit/lib/os_base.c"; attribute :>> needle="ptr = malloc (bytes);"; attribute :>> limit="ordinary allocator; libc effects outside captured source"; }
part source9:SourceRow { attribute :>> key="logger"; attribute :>> path="vendor/gambit/lib/os_base.c"; attribute :>> needle="result = vfprintf (stream, format, ap);"; attribute :>> limit="debug log also flushes stream; no direct Scheme dispatch in wrapper"; }
part source10:SourceRow { attribute :>> key="fatal"; attribute :>> path="vendor/gambit/lib/os_base.c"; attribute :>> needle="___GSTATE->setup_params.fatal_error (msgs);"; attribute :>> limit="explicit configurable callback; excluded from normal balance proof"; }
part source11:SourceRow { attribute :>> key="binding"; attribute :>> path="vendor/gambit/lib/setup.c"; attribute :>> needle="= ___alloc_mem;"; attribute :>> limit="setup installs function pointer; later raw writers not closed by this assignment"; }
part source12:SourceRow { attribute :>> key="ext-mode"; attribute :>> path="vendor/gambit/include/_gambit/module_generation.h.in"; attribute :>> needle="#define ___EXT(f)(___GSTATE->f)"; attribute :>> limit="late binding can go through mutable exported table"; }
part source13:SourceRow { attribute :>> key="alloc-macro"; attribute :>> path="vendor/gambit/include/_gambit/runtime_protocols.h.in"; attribute :>> needle="#define ___ALLOC_MEM(bytes)"; attribute :>> limit="normal/debug ABI variants"; }
part source14:SourceRow { attribute :>> key="lock"; attribute :>> path="vendor/gambit/include/_gambit/gvm_operations.h.in"; attribute :>> needle="#define ___SPINLOCK_LOCK(lock) ___MUTEX_LOCK(lock)"; attribute :>> limit="mutex/ticket variants; debug ticket path prints"; }
part source15:SourceRow { attribute :>> key="mutex"; attribute :>> path="vendor/gambit/include/_gambit/activity_log.h.in"; attribute :>> needle="#define ___MUTEX_LOCK(mut) (pthread_mutex_lock"; attribute :>> limit="POSIX external primitive, not Scheme code"; }
part source16:SourceRow { attribute :>> key="global-self"; attribute :>> path="vendor/gambit/lib/os_dyn.c"; attribute :>> needle="/* TODO: c_closure_self needs to be thread local */"; attribute :>> limit="shared identity channel; a root borrow cannot repair wrong identity"; }
part source17:SourceRow { attribute :>> key="closure-support"; attribute :>> path="vendor/gambit/lib/os_dyn.c"; attribute :>> needle="#ifndef C_CLOSURE_CODE_SIZE"; attribute :>> limit="unsupported trampoline path returns zero"; }
part source18:SourceRow { attribute :>> key="closure-selector"; attribute :>> path="vendor/gambit/lib/c_intf.c"; attribute :>> needle="if ((*x = ___make_c_closure (obj, converter)) == 0)"; attribute :>> limit="c-define static entry is distinct from dynamic closure"; }
part source19:SourceRow { attribute :>> key="tcl-entry"; attribute :>> path="vendor/gambit/examples/tcltk/tcltk.scm"; attribute :>> needle="char *result = tcltk_call"; attribute :>> limit="ClientData snapshot then generated SFUN"; }
part source20:SourceRow { attribute :>> key="tcl-type"; attribute :>> path="vendor/gambit/examples/tcltk/tcltk.scm"; attribute :>> needle="(scheme-object nonnull-char-string-list) char-string"; attribute :>> limit="one raw Scheme vector then string-list conversion"; }
part source21:SourceRow { attribute :>> key="string-list"; attribute :>> path="vendor/gambit/lib/c_intf.c"; attribute :>> needle="___EXP_FUNC(___SCMOBJ,___NONNULLSTRINGLIST_to_SCMOBJ)"; attribute :>> limit="list builder calls string conversion and make_pair"; }
part source22:SourceRow { attribute :>> key="collect"; attribute :>> path="vendor/gambit/lib/_mem/object-allocation.inc"; attribute :>> needle="if (___garbage_collect (___PSP words))"; attribute :>> limit="still allocation can collect; boundary is before converters/marker"; }
part source23:SourceRow { attribute :>> key="error-exit"; attribute :>> path="vendor/gambit/lib/setup.c"; attribute :>> needle="___EXP_FUNC(void,___propagate_error)"; attribute :>> limit="nonzero error throws via caller catcher"; }
part source24:SourceRow { attribute :>> key="config-snapshot"; attribute :>> path="vendor/gambit/include/config.h"; attribute :>> needle="/* #undef ___DEBUG_ALLOC_MEM */"; attribute :>> limit="textual generated snapshot, not effective binary qualification"; }
part source25:SourceRow { attribute :>> key="interrupt-default"; attribute :>> path="vendor/gambit/lib/os_setup.c"; attribute :>> needle="___raise_interrupt (___INTR_HEARTBEAT);"; attribute :>> limit="default posts interrupt, not direct Scheme callback; routing remains external closure input"; }
part def CallRow { attribute key:String; attribute source:String; attribute caller:String; attribute callee:String; attribute effect:String; attribute status:String; }
part call0:CallRow { attribute :>> key="tcl-to-entry"; attribute :>> source="tcl-entry"; attribute :>> caller="scheme_call_cmd"; attribute :>> callee="data_rc -> tcltk_call"; attribute :>> effect="raw snapshot; source owner and Tcl thread lifetime required"; attribute :>> status="bounded-source"; }
part call1:CallRow { attribute :>> key="generated-prefix"; attribute :>> source="sort"; attribute :>> caller="c-make-function"; attribute :>> callee="BEGIN_SFUN -> begin_sfun -> SCMOBJ argument prefix"; attribute :>> effect="generator enforces argument order; type aliases resolved"; attribute :>> status="bounded-source"; }
part call2:CallRow { attribute :>> key="begin-to-bank"; attribute :>> source="begin"; attribute :>> caller="begin_sfun"; attribute :>> callee="rc_entry_open / c_closure_self / borrow_rc_root / alloc_rc_roots"; attribute :>> effect="no direct Scheme call; locks and allocation dependencies remain"; attribute :>> status="bounded-source"; }
part call3:CallRow { attribute :>> key="bank-to-allocator"; attribute :>> source="rc-bank"; attribute :>> caller="alloc_rc_roots"; attribute :>> callee="alloc_rc -> alloc_rc_no_register -> ALLOC_MEM"; attribute :>> effect="private native allocation followed by registration and FAL initialization"; attribute :>> status="bounded-source"; }
part call4:CallRow { attribute :>> key="allocation-leaf"; attribute :>> source="malloc"; attribute :>> caller="alloc_mem"; attribute :>> callee="malloc or historical TempNewHandle branch"; attribute :>> effect="external allocator can only be sealed with selected target/effect profile"; attribute :>> status="external-unresolved"; }
part call5:CallRow { attribute :>> key="debug-leaf"; attribute :>> source="logger"; attribute :>> caller="alloc_mem/free_mem"; attribute :>> callee="printf wrapper -> vfprintf -> fflush"; attribute :>> effect="external I/O; no direct Gambit GC shown"; attribute :>> status="external-unresolved"; }
part call6:CallRow { attribute :>> key="binding-mode"; attribute :>> source="ext-mode"; attribute :>> caller="EXT wrapper"; attribute :>> callee="direct symbol or GSTATE function slot"; attribute :>> effect="all actual target writers must be excluded or version-leased"; attribute :>> status="external-unresolved"; }
part call7:CallRow { attribute :>> key="release-closure"; attribute :>> source="rc-return"; attribute :>> caller="return_rc_root/release_rc"; attribute :>> callee="gate -> release_rc_locked -> optional FREE_MEM"; attribute :>> effect="free/logging effects included; malformed custody calls fatal_error"; attribute :>> status="bounded-source"; }
part call8:CallRow { attribute :>> key="lock-leaf"; attribute :>> source="lock"; attribute :>> caller="RC gate operations"; attribute :>> callee="pthread mutex or ticket lock/CPU_RELAX"; attribute :>> effect="debug ticket variant reaches printf; no constant-time promise"; attribute :>> status="external-unresolved"; }
part call9:CallRow { attribute :>> key="fatal-callback"; attribute :>> source="fatal"; attribute :>> caller="rc_custody_error"; attribute :>> callee="fatal_error -> setup callback or display -> exit"; attribute :>> effect="normal fast proof requires well-formed custody; no callback is assumed harmless"; attribute :>> status="external-unresolved"; }
part call10:CallRow { attribute :>> key="closure-self"; attribute :>> source="global-self"; attribute :>> caller="dynamic trampoline -> begin_sfun"; attribute :>> callee="shared c_closure_self read after entry checks"; attribute :>> effect="identity must be captured reliably before borrow; supported architectures only"; attribute :>> status="source-limitation"; }
part call11:CallRow { attribute :>> key="static-tcl"; attribute :>> source="closure-selector"; attribute :>> caller="SCMOBJ_to_FUNCTION"; attribute :>> callee="static c-define entry or dynamic make_c_closure fallback"; attribute :>> effect="do not assign dynamic self hazard to Tcl static entry"; attribute :>> status="bounded-source"; }
part call12:CallRow { attribute :>> key="converter-boundary"; attribute :>> source="string-list"; attribute :>> caller="NONNULLCHARSTRINGLIST_to_SCMOBJ"; attribute :>> callee="NONNULLSTRING_to_SCMOBJ / make_pair -> alloc_scmobj"; attribute :>> effect="may collect after raw root prefix; current source includes GC slow path"; attribute :>> status="bounded-source"; }
part call13:CallRow { attribute :>> key="custom-c"; attribute :>> source="custom-converter"; attribute :>> caller="c-type-converter"; attribute :>> callee="user supplied C converter name"; attribute :>> effect="prefix sealing cannot whitelist arbitrary C callouts by filename"; attribute :>> status="external-unresolved"; }
part call14:CallRow { attribute :>> key="error-propagation"; attribute :>> source="error-exit"; attribute :>> caller="END_SFUN"; attribute :>> callee="end_sfun then propagate_error -> throw_error"; attribute :>> effect="C nonlocal exit after ordinary cleanup; abnormal prefix exits need stable custody"; attribute :>> status="bounded-source"; }
part call15:CallRow { attribute :>> key="default-signal"; attribute :>> source="interrupt-default"; attribute :>> caller="heartbeat_intr"; attribute :>> callee="raise_interrupt -> pending/trip/abort notification"; attribute :>> effect="ordinary default is deferred; custom signal/cancel paths need own admission"; attribute :>> status="bounded-source"; }
part def ProfileRow { attribute value:String; attribute key:String; attribute premise:String; attribute admission:String; attribute boundary:String; }
part profile0:ProfileRow { attribute :>> value="0"; attribute :>> key="plain-fast"; attribute :>> premise="closed no-GC/no-reentry/no-abandon prefix, valid source identity"; attribute :>> admission="fast conditional; durable not required"; attribute :>> boundary="libc, bindings, config and native thread lifetime remain unqualified"; }
part profile1:ProfileRow { attribute :>> value="1"; attribute :>> key="collecting-adapter"; attribute :>> premise="all movable raw inputs and procedure covered by registered source set"; attribute :>> admission="durable only"; attribute :>> boundary="reload canonical slots after collecting hook"; }
part profile2:ProfileRow { attribute :>> value="2"; attribute :>> key="reentrant-adapter"; attribute :>> premise="durable source set plus live or owned native inputs and explicit nested owner"; attribute :>> admission="durable only"; attribute :>> boundary="nested callback return does not refresh C locals"; }
part profile3:ProfileRow { attribute :>> value="3"; attribute :>> key="abandoning-adapter"; attribute :>> premise="stable allocation intent and complete lifetime custody before hook"; attribute :>> admission="durable only; unrecorded result retained"; attribute :>> boundary="rooting cannot recover an unrecorded pointer or preserve expired Tcl argv"; }
part profile4:ProfileRow { attribute :>> value="4"; attribute :>> key="opaque-callout"; attribute :>> premise="effect closure unavailable"; attribute :>> admission="reject"; attribute :>> boundary="persistent root is not an arbitrary-code safety proof"; }
part profile5:ProfileRow { attribute :>> value="5"; attribute :>> key="wrong-self"; attribute :>> premise="source identity cannot be established"; attribute :>> admission="reject both modes"; attribute :>> boundary="shared dynamic closure self is not fixed by RC refcount"; }
part profile6:ProfileRow { attribute :>> value="6"; attribute :>> key="debug-io-unqualified"; attribute :>> premise="stdio/logging dependencies not qualified"; attribute :>> admission="reject both modes until separately sealed"; attribute :>> boundary="DEBUG_LOG source wrapper has no direct Scheme call but is not a no-abandon certificate"; }
part def IssuerRow { attribute key:String; attribute source:String; attribute signature:String; attribute condition:String; attribute gap:String; }
part issuer0:IssuerRow { attribute :>> key="generated-prefix"; attribute :>> source="sort"; attribute :>> signature="PrefixId, raw-input shape, converter cut, source map"; attribute :>> condition="all SCMOBJ aliases resolved and raw prefix precedes collecting conversions"; attribute :>> gap="generated C/custom declarator closure not fully qualified"; }
part issuer1:IssuerRow { attribute :>> key="callee-lease"; attribute :>> source="ext-mode"; attribute :>> signature="callee graph hash, selected ABI/config, binding generation, effect vector"; attribute :>> condition="all selected direct/indirect targets immutable for grant lifetime"; attribute :>> gap="native binding writer closure and loaded libc not proved"; }
part issuer2:IssuerRow { attribute :>> key="source-owner"; attribute :>> source="rc-borrow"; attribute :>> signature="StorageId, root span of every movable input, provenance and owner lifetime"; attribute :>> condition="durable protects procedure plus raw inputs; fast needs complete no-safepoint interval"; attribute :>> gap="procedure-only root is insufficient for arbitrary SCMOBJ arguments"; }
part issuer3:IssuerRow { attribute :>> key="allocation-owner"; attribute :>> source="rc-alloc"; attribute :>> signature="OperationId, stable intent, private result or published bank custody"; attribute :>> condition="intent before native allocator; stable pointer capture before release"; attribute :>> gap="allocator-return capture and arbitrary cancellation native proof missing"; }
part issuer4:IssuerRow { attribute :>> key="entry-consumer"; attribute :>> source="begin"; attribute :>> signature="same bank storage and source lease handed to NativeEntry"; attribute :>> condition="rooted bank becomes actual source for NativeEntry.publishCarrier"; attribute :>> gap="physical handle transfer/scan admission still unresolved"; }
part def RouteRow { attribute actionName:String; attribute lemma:String; attribute source:String; attribute obligationId:String; }
part route0:RouteRow { attribute :>> actionName="selectPlain"; attribute :>> lemma="NativePrefix.selectPlainPreserves"; attribute :>> source="begin"; attribute :>> obligationId="prefix-safety"; }
part route1:RouteRow { attribute :>> actionName="selectCollecting"; attribute :>> lemma="NativePrefix.selectCollectingPreserves"; attribute :>> source="begin"; attribute :>> obligationId="prefix-safety"; }
part route2:RouteRow { attribute :>> actionName="selectReentrant"; attribute :>> lemma="NativePrefix.selectReentrantPreserves"; attribute :>> source="begin"; attribute :>> obligationId="prefix-safety"; }
part route3:RouteRow { attribute :>> actionName="selectAbandoning"; attribute :>> lemma="NativePrefix.selectAbandoningPreserves"; attribute :>> source="begin"; attribute :>> obligationId="prefix-safety"; }
part route4:RouteRow { attribute :>> actionName="selectOpaque"; attribute :>> lemma="NativePrefix.selectOpaquePreserves"; attribute :>> source="begin"; attribute :>> obligationId="prefix-safety"; }
part route5:RouteRow { attribute :>> actionName="selectWrongSelf"; attribute :>> lemma="NativePrefix.selectWrongSelfPreserves"; attribute :>> source="global-self"; attribute :>> obligationId="prefix-safety"; }
part route6:RouteRow { attribute :>> actionName="selectDebugIO"; attribute :>> lemma="NativePrefix.selectDebugIOPreserves"; attribute :>> source="logger"; attribute :>> obligationId="prefix-safety"; }
part route7:RouteRow { attribute :>> actionName="replaceBeforeGrant"; attribute :>> lemma="NativePrefix.replaceBeforeGrantPreserves"; attribute :>> source="ext-mode"; attribute :>> obligationId="prefix-safety"; }
part route8:RouteRow { attribute :>> actionName="grantFast"; attribute :>> lemma="NativePrefix.grantFastPreserves"; attribute :>> source="begin"; attribute :>> obligationId="prefix-safety"; }
part route9:RouteRow { attribute :>> actionName="grantDurable"; attribute :>> lemma="NativePrefix.grantDurablePreserves"; attribute :>> source="begin"; attribute :>> obligationId="prefix-safety"; }
part route10:RouteRow { attribute :>> actionName="denyProfile"; attribute :>> lemma="NativePrefix.denyProfilePreserves"; attribute :>> source="begin"; attribute :>> obligationId="prefix-safety"; }
part route11:RouteRow { attribute :>> actionName="closeAdmission"; attribute :>> lemma="NativePrefix.closeAdmissionPreserves"; attribute :>> source="begin"; attribute :>> obligationId="prefix-safety"; }
part route12:RouteRow { attribute :>> actionName="beginAllocation"; attribute :>> lemma="NativePrefix.beginAllocationPreserves"; attribute :>> source="rc-alloc"; attribute :>> obligationId="prefix-safety"; }
part route13:RouteRow { attribute :>> actionName="obtainNativeMemory"; attribute :>> lemma="NativePrefix.obtainNativeMemoryPreserves"; attribute :>> source="rc-alloc"; attribute :>> obligationId="prefix-safety"; }
part route14:RouteRow { attribute :>> actionName="enterHook"; attribute :>> lemma="NativePrefix.enterHookPreserves"; attribute :>> source="logger"; attribute :>> obligationId="prefix-safety"; }
part route15:RouteRow { attribute :>> actionName="returnHook"; attribute :>> lemma="NativePrefix.returnHookPreserves"; attribute :>> source="logger"; attribute :>> obligationId="prefix-safety"; }
part route16:RouteRow { attribute :>> actionName="gcRound"; attribute :>> lemma="NativePrefix.gcRoundPreserves"; attribute :>> source="collect"; attribute :>> obligationId="prefix-safety"; }
part route17:RouteRow { attribute :>> actionName="reloadRoot"; attribute :>> lemma="NativePrefix.reloadRootPreserves"; attribute :>> source="collect"; attribute :>> obligationId="prefix-safety"; }
part route18:RouteRow { attribute :>> actionName="captureOutcome"; attribute :>> lemma="NativePrefix.captureOutcomePreserves"; attribute :>> source="rc-alloc"; attribute :>> obligationId="prefix-safety"; }
part route19:RouteRow { attribute :>> actionName="publishInputs"; attribute :>> lemma="NativePrefix.publishInputsPreserves"; attribute :>> source="begin"; attribute :>> obligationId="prefix-safety"; }
part route20:RouteRow { attribute :>> actionName="abandonBeforeRecord"; attribute :>> lemma="NativePrefix.abandonBeforeRecordPreserves"; attribute :>> source="rc-alloc"; attribute :>> obligationId="prefix-safety"; }
part route21:RouteRow { attribute :>> actionName="loseRecordedResponse"; attribute :>> lemma="NativePrefix.loseRecordedResponsePreserves"; attribute :>> source="begin"; attribute :>> obligationId="prefix-safety"; }
part route22:RouteRow { attribute :>> actionName="recoverPrivateRecord"; attribute :>> lemma="NativePrefix.recoverPrivateRecordPreserves"; attribute :>> source="begin"; attribute :>> obligationId="prefix-safety"; }
part route23:RouteRow { attribute :>> actionName="recoverPublishedRecord"; attribute :>> lemma="NativePrefix.recoverPublishedRecordPreserves"; attribute :>> source="begin"; attribute :>> obligationId="prefix-safety"; }
part route24:RouteRow { attribute :>> actionName="releaseSource"; attribute :>> lemma="NativePrefix.releaseSourcePreserves"; attribute :>> source="begin"; attribute :>> obligationId="prefix-safety"; }
part route25:RouteRow { attribute :>> actionName="handoffBank"; attribute :>> lemma="NativePrefix.handoffBankPreserves"; attribute :>> source="begin"; attribute :>> obligationId="prefix-safety"; }
part route26:RouteRow { attribute :>> actionName="rollbackPlain"; attribute :>> lemma="NativePrefix.rollbackPlainPreserves"; attribute :>> source="begin"; attribute :>> obligationId="prefix-safety"; }
part def ComponentRow { attribute componentId:String; attribute actionSlice:String; attribute sharedContract:String; attribute proof:String; attribute source:String; }
part component0:ComponentRow { attribute :>> componentId="effect-closure"; attribute :>> actionSlice="selectPlain/selectOpaque/replaceBeforeGrant/grantFast"; attribute :>> sharedContract="callee-closure"; attribute :>> proof="NativePrefix.staleBindingCannotGrant"; attribute :>> source="ext-mode"; }
part component1:ComponentRow { attribute :>> componentId="source-identity"; attribute :>> actionSlice="selectWrongSelf/grantDurable"; attribute :>> sharedContract="source-set"; attribute :>> proof="NativePrefix.wrongSelfCannotBorrowItsWayIn"; attribute :>> source="global-self"; }
part component2:ComponentRow { attribute :>> componentId="root-preparation"; attribute :>> actionSlice="grantFast/grantDurable/gcRound/reloadRoot/publishInputs"; attribute :>> sharedContract="prefix-safety"; attribute :>> proof="NativePrefix.publishRequiresCurrentLocal"; attribute :>> source="raw-prefix"; }
part component3:ComponentRow { attribute :>> componentId="allocation-custody"; attribute :>> actionSlice="obtainNativeMemory/captureOutcome/abandonBeforeRecord/recoverPrivateRecord"; attribute :>> sharedContract="allocation-capture"; attribute :>> proof="NativePrefix.noRecordNoRecovery"; attribute :>> source="rc-alloc"; }
part component4:ComponentRow { attribute :>> componentId="entry-handoff"; attribute :>> actionSlice="publishInputs/releaseSource/handoffBank"; attribute :>> sharedContract="entry-join"; attribute :>> proof="NativePrefix.prefixToEntryStep"; attribute :>> source="begin"; }
part def JoinRow { attribute key:String; attribute lemma:String; attribute source:String; attribute premise:String; attribute status:String; }
part join0:JoinRow { attribute :>> key="fast-no-gc"; attribute :>> lemma="NativePrefix.fastExcludesGc"; attribute :>> source="begin"; attribute :>> premise="certified fast profile forbids GC before target roots; not a runtime detector"; attribute :>> status="conditional-lemma"; }
part join1:JoinRow { attribute :>> key="identity-before-root"; attribute :>> lemma="NativePrefix.wrongSelfCannotBorrowItsWayIn"; attribute :>> source="global-self"; attribute :>> premise="correct source identity precedes any rooting claim"; attribute :>> status="conditional-lemma"; }
part join2:JoinRow { attribute :>> key="reload-after-callback"; attribute :>> lemma="NativePrefix.callbackReturnIsNotReload"; attribute :>> source="logger"; attribute :>> premise="returned C local can be stale even when root slot is current"; attribute :>> status="conditional-lemma"; }
part join3:JoinRow { attribute :>> key="unknown-retained"; attribute :>> lemma="NativePrefix.unknownRetains"; attribute :>> source="rc-alloc"; attribute :>> premise="stable intent and owned source/native inputs already admitted"; attribute :>> status="conditional-lemma"; }
part join4:JoinRow { attribute :>> key="actual-entry-step"; attribute :>> lemma="NativePrefix.prefixToEntryStep"; attribute :>> source="begin"; attribute :>> premise="bank storage/source handoff and host facts are native premises"; attribute :>> status="conditional-lemma"; }
part join5:JoinRow { attribute :>> key="entry-preserves-close"; attribute :>> lemma="NativePrefix.preservesClosedIngress"; attribute :>> source="begin"; attribute :>> premise="root preparation cannot reopen closed execution ingress"; attribute :>> status="conditional-lemma"; }
part def ObligationRow { attribute key:String; attribute status:String; attribute condition:String; }
part obligation0:ObligationRow { attribute :>> key="prefix-safety"; attribute :>> status="conditional-model"; attribute :>> condition="27 actions preserve root/intent coverage and mode separation"; }
part obligation1:ObligationRow { attribute :>> key="entry-join"; attribute :>> status="conditional-model"; attribute :>> condition="actual publishCarrier Step and Safe consumer seed; scoped root handoff premise"; }
part obligation2:ObligationRow { attribute :>> key="callee-closure"; attribute :>> status="unresolved"; attribute :>> condition="all selected allocator/free/lock/logging/indirect binding targets sealed through grant lifetime"; }
part obligation3:ObligationRow { attribute :>> key="effective-profile"; attribute :>> status="unresolved"; attribute :>> condition="actual loaded C23 configuration, symbol binding and libc effects qualified without assuming source snapshot equals binary"; }
part obligation4:ObligationRow { attribute :>> key="source-set"; attribute :>> status="unresolved"; attribute :>> condition="every movable raw SCMOBJ input and source identity covered; Tcl native buffers have separate lifetime"; }
part obligation5:ObligationRow { attribute :>> key="allocation-capture"; attribute :>> status="unresolved"; attribute :>> condition="native allocation-return to stable capture cannot abandon or has same-operation reconciliation custody"; }
part obligation6:ObligationRow { attribute :>> key="nonlocal-exits"; attribute :>> status="unresolved"; attribute :>> condition="fatal callback, cancellation, longjmp and nested host exits retain stable preparation custody"; }
part obligation7:ObligationRow { attribute :>> key="dynamic-self"; attribute :>> status="unresolved"; attribute :>> condition="supported dynamic closure identity binding replaced or excluded; no arm64 trampoline claim"; }
part obligation8:ObligationRow { attribute :>> key="native-scan"; attribute :>> status="unresolved"; attribute :>> condition="persistent source slots and bank span enter actual GC roster; locals reloaded after updates"; }
part obligation9:ObligationRow { attribute :>> key="native-product"; attribute :>> status="unresolved"; attribute :>> condition="prefix ownership and NativeEntry/NativeScope histories coupled through real C23 cuts; no global proof"; }
part def GainRow { attribute key:String; attribute benefit:String; attribute overhead:String; attribute positive:String; attribute refutation:String; }
part gain0:GainRow { attribute :>> key="qualified-fast"; attribute :>> benefit="zero mandatory persistent source-root slots before publication"; attribute :>> overhead="one effect/binding lease plus stable allocation intent; native allocation can still block"; attribute :>> positive="closed no-GC/no-reentry/no-abandon prefix and stable identity"; attribute :>> refutation="no direct GC call is insufficient to sign fast permission"; }
part gain1:GainRow { attribute :>> key="durable"; attribute :>> benefit="GC/reentry can preserve raw inputs through canonical roots"; attribute :>> overhead="O(R) source slots/leases and post-GC reload for R movable roots"; attribute :>> positive="source set covers all inputs and native buffers remain valid"; attribute :>> refutation="rooting only procedure misses raw arguments; rooted storage does not fix wrong source identity"; }
part gain2:GainRow { attribute :>> key="bank-reuse"; attribute :>> benefit="one existing SFUN bank can feed NativeEntry; no mandatory duplicate bank"; attribute :>> overhead="registration/storage handoff receipt and overlap scanning"; attribute :>> positive="bank lifetime/source span belongs to acknowledged consumer"; attribute :>> refutation="pointer copy to registry is not a storage ownership transfer"; }
part gain3:GainRow { attribute :>> key="unknown"; attribute :>> benefit="zero blind allocation/call replay before stable result is known"; attribute :>> overhead="O(K) intent records for K pending operations; memory may remain unbounded"; attribute :>> positive="same operation owns record and reconciliation path"; attribute :>> refutation="unknown pointer can remain unrecoverable; retention is not progress"; }
part gain4:GainRow { attribute :>> key="static-tcl"; attribute :>> benefit="reuse static c-define and SCMOBJ-first vector prefix"; attribute :>> overhead="Tcl owner/argv lifetime proof plus sealed native allocation path"; attribute :>> positive="same interpreter thread and no unqualified prefix callbacks"; attribute :>> refutation="dynamic global self finding alone does not prove a Tcl static-entry bug"; }
part gain5:GainRow { attribute :>> key="modern-c"; attribute :>> benefit="C23 can centralize effect leases, entry manifests and allocation custody"; attribute :>> overhead="new checked adapters; all raw aliases and native ABI combinations must be qualified"; attribute :>> positive="retire managed-path ad hoc bootstrap only after complete caller migration"; attribute :>> refutation="Zig does not remove effects, identity or C lifetime obligations"; }
part def EdgeRow { attribute fromNode:String; attribute toNode:String; attribute contract:String; }
part edge0:EdgeRow { attribute :>> fromNode="SFUN_generator"; attribute :>> toNode="raw_input_manifest"; attribute :>> contract="resolved SCMOBJ prefix before collecting converter"; }
part edge1:EdgeRow { attribute :>> fromNode="raw_input_manifest"; attribute :>> toNode="callee_lease"; attribute :>> contract="allocator/free/lock/logger/direct-table target closure"; }
part edge2:EdgeRow { attribute :>> fromNode="callee_lease"; attribute :>> toNode="fast_grant"; attribute :>> contract="no GC, no reentry, no abandonment, correct source"; }
part edge3:EdgeRow { attribute :>> fromNode="callee_lease"; attribute :>> toNode="durable_grant"; attribute :>> contract="declared effects; all source/native lifetimes covered"; }
part edge4:EdgeRow { attribute :>> fromNode="global_closure_self"; attribute :>> toNode="reject_or_rebuild"; attribute :>> contract="source identity before rooting; static Tcl is separate"; }
part edge5:EdgeRow { attribute :>> fromNode="fast_grant"; attribute :>> toNode="allocation_intent"; attribute :>> contract="stable preparation custody before allocator"; }
part edge6:EdgeRow { attribute :>> fromNode="durable_grant"; attribute :>> toNode="allocation_intent"; attribute :>> contract="source root set survives admitted hooks"; }
part edge7:EdgeRow { attribute :>> fromNode="allocation_intent"; attribute :>> toNode="private_pointer"; attribute :>> contract="native result may precede stable capture"; }
part edge8:EdgeRow { attribute :>> fromNode="private_pointer"; attribute :>> toNode="unknown_custodian"; attribute :>> contract="uncaptured abandonment retains debt; no replay"; }
part edge9:EdgeRow { attribute :>> fromNode="private_pointer"; attribute :>> toNode="captured_result"; attribute :>> contract="known record before raw input publication"; }
part edge10:EdgeRow { attribute :>> fromNode="durable_grant"; attribute :>> toNode="GC_root_update"; attribute :>> contract="collector updates canonical slots"; }
part edge11:EdgeRow { attribute :>> fromNode="GC_root_update"; attribute :>> toNode="reload_local"; attribute :>> contract="callback return is not reload"; }
part edge12:EdgeRow { attribute :>> fromNode="captured_result"; attribute :>> toNode="SFUN_bank"; attribute :>> contract="publish current raw inputs; consume preparation grant"; }
part edge13:EdgeRow { attribute :>> fromNode="SFUN_bank"; attribute :>> toNode="NativeEntry"; attribute :>> contract="actual publishCarrier Step; preserve closed ingress"; }
part edge14:EdgeRow { attribute :>> fromNode="SysML"; attribute :>> toNode="ASCENT"; attribute :>> contract="source/callee/effect/profile/issuer contracts"; }
part edge15:EdgeRow { attribute :>> fromNode="SysML"; attribute :>> toNode="QNT"; attribute :>> contract="27 explicit state transitions"; }
part edge16:EdgeRow { attribute :>> fromNode="QNT"; attribute :>> toNode="Lean"; attribute :>> contract="typed binding faithful AST and reachable induction"; }
part edge17:EdgeRow { attribute :>> fromNode="Lean"; attribute :>> toNode="ASCENT"; attribute :>> contract="compiled lemmas and conditional joins; native gaps block admission"; }
}
