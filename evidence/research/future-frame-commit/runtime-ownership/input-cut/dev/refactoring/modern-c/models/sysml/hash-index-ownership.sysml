package GambitHashIndexOwnership {
  private import ScalarValues::*;
  ref part collectorRole = GambitRuntimeRoleRealization::cut0;
  attribute runtimeAdmitted : Boolean = false;
  part def Contract { attribute id:String; attribute route:String; attribute invariant:String; attribute benefit:String; attribute cost:String; }
  part construction:Contract {
    attribute :>> id="reconstruction-roots";
    attribute :>> route="_io.scm deserialize -> _system.scm implode-gc-hash-table; binary deserialize -> gc-hash-table-reconstruction-begin/commit! -> object-scanning.inc";
    attribute :>> invariant="Begin allocates an initialized shell with MEM_ALLOC_KEYS and strong values before any payload store. Every installed key/value remains scanned across construction safepoints. Commit is nonallocating and publishes final weak/index flags plus KEY_MOVED and NEED_REHASH together. Binary alloc! roots the shell before recursively decoding fields; unpublished failure retains normal Scheme root/exception custody.";
    attribute :>> benefit="Replace flags-zero construction windows in both real decoders; GC transports every installed reference before the final semantic index policy becomes visible";
    attribute :>> cost="One existing flags word, no new object field or allocation. Pending weak entries are retained strongly until commit or abandonment; partial construction adds key scanning proportional to installed/unused table extent. Native roundtrip and exception paths still require qualification.";
  }
  part creation:Contract { attribute :>> id="producer"; attribute :>> route="_system.scm make-table-aux checks-done -> table flags -> table-get-gcht/allocate"; attribute :>> invariant="test-fn=false selects C identity index; a Scheme test/hash selects persistent SCHEME_INDEX bit 128. Same existing flags word; never infer ownership from KEY_MOVED or weak-key bits."; attribute :>> benefit="Native layout records the semantic algorithm owner before collector sees a table"; attribute :>> cost="One constructor flag decision; no extra table field or root word"; }
  part repair:Contract { attribute :>> id="reference-repair"; attribute :>> route="mem.c scan -> process_gc_hash_tables -> repaired key/value references and owner dispatch"; attribute :>> invariant="Collector transports references. Scheme hashes must be stable for unchanged semantic keys across GC. Clear only address-driven KEY_MOVED for Scheme indexes; preserve pre-existing NEED_REHASH. Never call Scheme from GC or replace its index with the C address hash."; attribute :>> benefit="Eliminate wrong C rehash and its full-table traversal for Scheme-owned indexes; avoid adding a first-reader mutation after ordinary GC"; attribute :>> cost="One owner branch per reached GC table. Correctness depends on hash stability; arbitrary physical-address-dependent custom hashes are not qualified."; }
  part identity:Contract { attribute :>> id="native-index"; attribute :>> route="object-scanning.inc actual strong-key movement; weak-tables.inc reference repair; hash-table-api.inc pure lookup and writer-owned reconstruction"; attribute :>> invariant="GC never permutes slots. Actual native key movement records KEY_MOVED; pure reads with this debt linearly search current references without clearing debt or writing slots. Set, delete and path-compressing union/find rebuild before mutation. Deserialization NEED_REHASH stays distinct. No eager/lazy collector-count policy remains."; attribute :>> benefit="Stable suspended traversal and shared pure reads; permanent symbols no longer force a speculative whole-table rebuild on every GC"; attribute :>> cost="One before/after identity comparison per strong heap key; moving-key reads can cost O(n) until the next mutation. Writer rebuild remains O(n). No new table field, heap increase or callback to Scheme in GC. Concurrent/reentrant same-table mutation is not admitted"; }
  part traversal:Contract { attribute :>> id="physical-cursor"; attribute :>> route="_system.scm gc-hash-table-for-each/search/foldl -> visitor -> GC -> same physical cursor"; attribute :>> invariant="Reference relocation and weak removal preserve slot positions; a strong unchanged table visits each binding once despite visitor GC. Mutator layout writes require no active traversal. doc/gambit.txi table-for-each forbids same-table public access/mutation; this cut does not lift that public restriction. Private native read is separately read-only."; attribute :>> benefit="Remove GC-induced duplicate/missing visits without allocating a traversal snapshot or global reader lock"; attribute :>> cost="Requires caller exclusivity and rooted table/key/value state; weak removals may legitimately remove unreachable bindings. No guarantee for unowned raw pointers, concurrent writers or unknown-stop recovery"; }
  part scheme:Contract { attribute :>> id="scheme-index"; attribute :>> route="_system.scm table-access -> recorded test/hash -> existing resize/reinsert for explicit reconstruction debt"; attribute :>> invariant="Ordinary GC does not create Scheme rebuild debt for stable hashes. Deserialization NEED_REHASH still blocks direct indexed lookup until Scheme reconstructs. GC never executes user hash callbacks."; attribute :>> benefit="Semantic key/index agreement and no extra Scheme O(n) rebuild after every collection"; attribute :>> cost="Existing explicit rebuild may allocate/call user hash. Same-table mutating reentrancy and simultaneous reconstruction are not proved by this cut."; }
  part lifetime:Contract { attribute :>> id="owner-lifetime"; attribute :>> route="gc-hash-table-resize flag retention; table-copy -> make-table-aux; serialize/deserialize flags"; attribute :>> invariant="Ownership survives allocation, resize, copy and current-format roundtrip. Older serialized images without owner metadata and external raw flag writers remain unqualified."; attribute :>> benefit="Owner is a persistent native contract, not a GC-mode switch or an exception for GSC"; attribute :>> cost="Additional serialization/FFI producer inventory and native tests required; no compatibility inference"; }
  part witness:Contract { attribute :>> id="witness"; attribute :>> route="new target gsc default heap -> full two-pass bootstrap -> compiled map/multishot/GC and hash-index-owner controls"; attribute :>> invariant="Default profile, real new runtime, both Scheme and native indexes. Large-heap and flag-intervention diagnostics explain failure but cannot confer acceptance."; attribute :>> benefit="Check actual generator, runtime index ownership, collector and repeatable control consumers together"; attribute :>> cost="Full native and source-refinement gates; first target link is insufficient"; }
  part def Edge { ref part producer:Contract; ref part consumer:Contract; }
  part e0:Edge { ref part :>> producer=creation; ref part :>> consumer=repair; }
  part e1:Edge { ref part :>> producer=repair; ref part :>> consumer=identity; }
  part e2:Edge { ref part :>> producer=repair; ref part :>> consumer=scheme; }
  part e3:Edge { ref part :>> producer=creation; ref part :>> consumer=lifetime; }
  part e4:Edge { ref part :>> producer=lifetime; ref part :>> consumer=witness; }
  part e5:Edge { ref part :>> producer=scheme; ref part :>> consumer=witness; }
  part e6:Edge { ref part :>> producer=repair; ref part :>> consumer=traversal; }
  part e7:Edge { ref part :>> producer=traversal; ref part :>> consumer=witness; }
  part e8:Edge { ref part :>> producer=construction; ref part :>> consumer=repair; }
  part e9:Edge { ref part :>> producer=construction; ref part :>> consumer=scheme; }
  part e10:Edge { ref part :>> producer=construction; ref part :>> consumer=witness; }
  ref part constructionSchedule = qnt;
  ref part constructionTransportLaw = lean;
  part def Proof { ref part component:Contract; attribute id:String; attribute method:String; attribute artifact:String; attribute premise:String; }
  part qnt:Proof { ref part :>> component=traversal; attribute :>> id="HI-QNT"; attribute :>> method="quint"; attribute :>> artifact="dev/refactoring/modern-c/models/quint/hash_index_owner.qnt"; attribute :>> premise="One existing finite model: two semantic keys, one reader, two addresses/layouts, native address debt distinct from deserialize debt. Retain eager-reorder and unchanged-address reorder histories which duplicate a visited key despite valid hashing. The same QNT models one installed construction slot, GC relocation before commit and the flags-zero lost-reference counterexample; it assumes an externally retained key, not arbitrary weak reachability. Semantic hash stability and no concurrent writer are assumptions; not a C pointer or liveness proof"; }
  part lean:Proof { ref part :>> component=scheme; attribute :>> id="HI-LEAN"; attribute :>> method="lean"; attribute :>> artifact="dev/refactoring/modern-c/models/lean/HashIndexOwner.lean"; attribute :>> premise="Conditional semantic transport, native rebuild, incompatible-algorithm counter-law and debt guard; not a C pointer or complete hasher proof; construction reuses the existing reference-transport premise and adds no duplicate Lean schedule"; }
  part native:Proof { ref part :>> component=witness; attribute :>> id="HI-NATIVE"; attribute :>> method="native"; attribute :>> artifact="evidence/research/hash-layout/native-observations.json"; attribute :>> premise="Same Modern C source workspace and existing Bazel profile, retained generation, interpreted and compiled traversal with symbols/moving/retained-weak keys, map multi-shot, W<R and unknown join. Bind observed recipes, source locks and archived outcomes rather than treating a planned recipe as passed evidence. Earlier duplicate-key and compile failures remain retained. This incremental cohort is not a newly executed full bootstrap or remote CI"; }
  part ownership:Proof { ref part :>> component=lifetime; attribute :>> id="HI-REFINE"; attribute :>> method="source-refinement"; attribute :>> artifact="vendor/gambit/lib/_system.scm"; attribute :>> premise="Trace all active C-target constructors, copies, resizing, serialization and raw producers; old images, reentrant mutation and concurrent reconstruction remain open"; }
  part branchBootstrap:Proof {
    ref part :>> component=witness;
    attribute :>> id="HI-BRANCH-BOOTSTRAP";
    attribute :>> method="native-source-bound-candidate";
    attribute :>> artifact="evidence/refactoring/modern-c/bootstrap-index-owner.json";
    attribute :>> premise="Committed db7e3425 bootstrap failed; no independent twelve-requirement milestone credit exists. A separately hashed four-path candidate refines creation, repair and scheme only. Preserve the native eager policy: this candidate does not establish identity/traversal/construction/lifetime closure. Actual full from-scratch outcomes, causal controls and source identities must be read from the artifact. A diagnostic incremental link, model pass or candidate PASS never changes the committed-HEAD failure or grants SMP/commit admission.";
  }
}
