package GambitNestedDomainRootRetirement { private import ScalarValues::*;
part def Owner { attribute componentId:String; }
part controlOwner:Owner { attribute :>> componentId="control"; }
part rootsOwner:Owner { attribute :>> componentId="roots"; }
part codeOwner:Owner { attribute :>> componentId="code"; }
part def SourceRow { attribute key:String; attribute path:String; attribute needle:String; attribute obligation:String; }
part source0:SourceRow { attribute :>> key="return-owner"; attribute :>> path="vendor/gambit/lib/_kernel.scm"; attribute :>> needle="/* not the same processor that created frame */"; attribute :>> obligation="owner-affinity"; }
part source1:SourceRow { attribute :>> key="return-stale"; attribute :>> path="vendor/gambit/lib/_kernel.scm"; attribute :>> needle="/* not first return */"; attribute :>> obligation="one-native-return"; }
part source2:SourceRow { attribute :>> key="return-unwind"; attribute :>> path="vendor/gambit/lib/_kernel.scm"; attribute :>> needle="___throw_error (___PSP ___FIX(___UNWIND_C_STACK));"; attribute :>> obligation="live-catcher"; }
part source3:SourceRow { attribute :>> key="call-frame"; attribute :>> path="vendor/gambit/lib/setup.c"; attribute :>> needle="___fp[-2] = stack_marker;"; attribute :>> obligation="frame-marker-coordinate"; }
part source4:SourceRow { attribute :>> key="call-catcher"; attribute :>> path="vendor/gambit/lib/setup.c"; attribute :>> needle="stack_marker != ___ps->context->fp[___FRAME_SPACE(2)-2]"; attribute :>> obligation="unwind-destination"; }
part source5:SourceRow { attribute :>> key="marker-root"; attribute :>> path="vendor/gambit/lib/c_intf.c"; attribute :>> needle="proc_or_false = *proc_root; /* reload after allocating the marker */"; attribute :>> obligation="root-reload"; }
part source6:SourceRow { attribute :>> key="marker-kill"; attribute :>> path="vendor/gambit/lib/c_intf.c"; attribute :>> needle="___VECTORELEM(marker, 0) = ___FAL; /* invalidate the C stack frame */"; attribute :>> obligation="return-invalidation"; }
part source7:SourceRow { attribute :>> key="legacy-root"; attribute :>> path="vendor/gambit/lib/c_intf.c"; attribute :>> needle="wrapper. Managed startup uses the explicit rooted endpoint above."; attribute :>> obligation="legacy-not-rooted"; }
part source8:SourceRow { attribute :>> key="catcher-local"; attribute :>> path="vendor/gambit/include/_gambit/foreign_conversion.h.in"; attribute :>> needle="___jmpbuf_struct ___jbuf, *___old_catcher = ___ps->catcher;"; attribute :>> obligation="c-stack-dynamic-extent"; }
part source9:SourceRow { attribute :>> key="catcher-restore"; attribute :>> path="vendor/gambit/include/_gambit/foreign_conversion.h.in"; attribute :>> needle="#define ___END_TRY } ___ps->catcher = ___old_catcher; }"; attribute :>> obligation="nested-catcher-restore"; }
part source10:SourceRow { attribute :>> key="continuation-closure"; attribute :>> path="vendor/gambit/lib/_thread.scm"; attribute :>> needle="(##continuation-return-aux cont val1 val2 val3 others)"; attribute :>> obligation="multi-shot-logical-control"; }
part source11:SourceRow { attribute :>> key="wind-user"; attribute :>> path="vendor/gambit/lib/_thread.scm"; attribute :>> needle="((macro-dynwind-after src))"; attribute :>> obligation="reentrant-winding"; }
part source12:SourceRow { attribute :>> key="direct-no-winding"; attribute :>> path="vendor/gambit/lib/_thread.scm"; attribute :>> needle="(define-prim ##continuation-return-no-winding"; attribute :>> obligation="cannot-use-dynamic-wind-only"; }
part source13:SourceRow { attribute :>> key="saved-roots"; attribute :>> path="vendor/gambit/lib/_mem/root-origins.inc"; attribute :>> needle="mark_array (work, context->saved, sizeof(context->saved)/sizeof(*context->saved));"; attribute :>> obligation="saved-registers"; }
part source14:SourceRow { attribute :>> key="entry-root"; attribute :>> path="vendor/gambit/lib/_mem/root-origins.inc"; attribute :>> needle="mark_array (work, &context->entry_marker, 1);"; attribute :>> obligation="context-marker-root"; }
part source15:SourceRow { attribute :>> key="rc-root"; attribute :>> path="vendor/gambit/lib/_mem/rc-roots.inc"; attribute :>> needle="context->mem.rc_head_.next"; attribute :>> obligation="context-owned-rc"; }
part source16:SourceRow { attribute :>> key="tcl-reentry"; attribute :>> path="vendor/gambit/examples/tcltk/tcltk.scm"; attribute :>> needle="___EXT(___data_rc) (___CAST(void*,client_data))"; attribute :>> obligation="raw-before-guard"; }
part source17:SourceRow { attribute :>> key="tls-status"; attribute :>> path="vendor/gambit/lib/os_thread.c"; attribute :>> needle="pthread_setspecific (___thread_mod.tls_ptr_key, ptr); /* ignore error */"; attribute :>> obligation="checked-binding-required"; }
part source18:SourceRow { attribute :>> key="thread-id"; attribute :>> path="vendor/gambit/lib/os_thread.c"; attribute :>> needle="thread->thread_id = pthread_self ();"; attribute :>> obligation="native-thread-identity"; }
part source19:SourceRow { attribute :>> key="paper-fulltext"; attribute :>> path="evidence/research/guard-thread-admission/feeley-sfp-paper.txt"; attribute :>> needle="We have not yet implemented this approa h in Gambit-C."; attribute :>> obligation="historical-proposal-not-current"; }
part source20:SourceRow { attribute :>> key="sfun-empty-body"; attribute :>> path="vendor/gambit/include/_gambit/foreign_conversion.h.in"; attribute :>> needle="#define ___BEGIN_SFUN_BODY"; attribute :>> obligation="SFUN wrapper is not itself a catcher"; }
part source21:SourceRow { attribute :>> key="sfun-cleanup-after-call"; attribute :>> path="vendor/gambit/include/_gambit/foreign_conversion.h.in"; attribute :>> needle="#define ___END_SFUN } ___EXT(___kill_sfun_stack_marker) (___marker);"; attribute :>> obligation="sequential cleanup is not total under outer unwind"; }
part source22:SourceRow { attribute :>> key="sfun-generator"; attribute :>> path="vendor/gambit/gsc/_ptree2.scm"; attribute :>> needle="c-id-prefix \"BEGIN_SFUN_BODY\" nl-str"; attribute :>> obligation="actual generated SFUN body"; }
part source23:SourceRow { attribute :>> key="cfun-conditional-catcher"; attribute :>> path="vendor/gambit/gsc/_ptree2.scm"; attribute :>> needle="(if cleanup? \"BEGIN_CFUN_BODY_CLEANUP\" \"BEGIN_CFUN_BODY\")"; attribute :>> obligation="foreign catchers depend on conversion cleanup"; }
part source24:SourceRow { attribute :>> key="cfun-catcher-macro"; attribute :>> path="vendor/gambit/include/_gambit/foreign_conversion.h.in"; attribute :>> needle="#define ___BEGIN_CFUN_BODY_CLEANUP ___W_ALL_INL ___BEGIN_TRY"; attribute :>> obligation="intermediate catcher may intercept and propagate"; }
part source25:SourceRow { attribute :>> key="error-propagation"; attribute :>> path="vendor/gambit/lib/setup.c"; attribute :>> needle="___THROW (err);"; attribute :>> obligation="throw uses current catcher"; }
part source26:SourceRow { attribute :>> key="captured-frame-decode"; attribute :>> path="vendor/gambit/lib/_mem/object-scanning.inc"; attribute :>> needle="___decode_frame_descriptor (___LABEL_DESCR_GET(actual_ra), 1)"; attribute :>> obligation="captured RETI still consumes descriptor after native exit"; }
part source27:SourceRow { attribute :>> key="context-frame-decode"; attribute :>> path="vendor/gambit/lib/_mem/continuation-roots.inc"; attribute :>> needle="acquire_frame_access(work);"; attribute :>> obligation="maintenance scanner has separate descriptor lifetime"; }
part source28:SourceRow { attribute :>> key="captured-frame-copy"; attribute :>> path="vendor/gambit/lib/_mem/continuation-roots.inc"; attribute :>> needle="___RETI_GET_FS_LINK(actual_ra,fs,link)"; attribute :>> obligation="stack to heap copy reads label metadata"; }
part source29:SourceRow { attribute :>> key="native-unload"; attribute :>> path="vendor/gambit/lib/os_dyn.c"; attribute :>> needle="dlclose (p->descr);"; attribute :>> obligation="global loader cleanup is not per-domain retirement"; }
part source30:SourceRow { attribute :>> key="run-landing"; attribute :>> path="vendor/gambit/lib/setup.c"; attribute :>> needle="___VOLATILE ___SCMOBJ marker = ___FAL;"; attribute :>> obligation="run has an enclosing catcher and post-catch cleanup"; }
part source31:SourceRow { attribute :>> key="tcl-source-delete"; attribute :>> path="vendor/gambit/examples/tcltk/tcltk.scm"; attribute :>> needle="___EXT(___release_rc) (___CAST(void*,client_data));"; attribute :>> obligation="close source admission before native storage release"; }
part def IssuerRow { attribute key:String; attribute proposedIssuer:String; attribute actualSource:String; attribute status:String; attribute responsibility:String; }
part issuer0:IssuerRow { attribute :>> key="entry-root"; attribute :>> proposedIssuer="NativeEntryAdapter / VMRootRegistry"; attribute :>> actualSource="Tcl data_rc; marker-from-root; root-origins"; attribute :>> status="required new adapter, no qualified signer"; attribute :>> responsibility="both outer and inner source slots stay rooted until target acknowledgement"; }
part issuer1:IssuerRow { attribute :>> key="subtree"; attribute :>> proposedIssuer="NativeUnwindCoordinator"; attribute :>> actualSource="___call marker mismatch and SFUN continuation after call"; attribute :>> status="required new adapter, no qualified signer"; attribute :>> responsibility="close descendant admission, retain root/code leases and publish stable escrow before physical unwind"; }
part issuer2:IssuerRow { attribute :>> key="landing"; attribute :>> proposedIssuer="NativeLandingAdapter"; attribute :>> actualSource="___run BEGIN_TRY/END_TRY and conditional CFUN catcher"; attribute :>> status="required new adapter, no qualified signer"; attribute :>> responsibility="receipt names exact operation, thread incarnation, target frame and unwound subtree; unknown keeps custody"; }
part issuer3:IssuerRow { attribute :>> key="capture-close"; attribute :>> proposedIssuer="ContinuationHolderRegistry"; attribute :>> actualSource="_thread continuation closures and captured-frame scan"; attribute :>> status="required new adapter, no qualified signer"; attribute :>> responsibility="last holder includes FFI, scheduler and multi-shot in-flight resumptions"; }
part issuer4:IssuerRow { attribute :>> key="root-grace"; attribute :>> proposedIssuer="CollectorRootRegistry"; attribute :>> actualSource="mark_execution_roots and context RC traversal"; attribute :>> status="required new adapter, no qualified signer"; attribute :>> responsibility="close this bundle to future snapshots; drain all already admitted root readers"; }
part issuer5:IssuerRow { attribute :>> key="code-grace"; attribute :>> proposedIssuer="ImageLeaseCoordinator"; attribute :>> actualSource="captured-frame descriptors and loader dlclose"; attribute :>> status="required new adapter, no qualified signer"; attribute :>> responsibility="join frame holders, old scanner tasks, native return frames and other VM owners before image unload"; }
part def NeedRow { attribute key:String; attribute kind:String; attribute path:String; attribute scope:String; ref owner:Owner; }
part need0:NeedRow { attribute :>> key="Nested-formal"; attribute :>> kind="formal"; attribute :>> path="dev/refactoring/modern-c/models/quint/nested_domain_root_retirement.qnt"; attribute :>> scope="bounded-composition-safety"; ref :>> owner = controlOwner; }
part need1:NeedRow { attribute :>> key="Nested-bridge"; attribute :>> kind="bridge"; attribute :>> path="dev/refactoring/modern-c/models/lean/NestedDomain.lean"; attribute :>> scope="typed-ir-composition-bridge"; ref :>> owner = controlOwner; }
part need2:NeedRow { attribute :>> key="Nested-root-handoff"; attribute :>> kind="native"; attribute :>> path="vendor/gambit/lib/_mem/root-origins.inc"; attribute :>> scope="two-entry-root-registration-and-round-ack"; ref :>> owner = rootsOwner; }
part need3:NeedRow { attribute :>> key="Nested-unwind"; attribute :>> kind="native"; attribute :>> path="vendor/gambit/include/_gambit/foreign_conversion.h.in"; attribute :>> scope="subtree-escrow-before-catcher-transfer"; ref :>> owner = controlOwner; }
part need4:NeedRow { attribute :>> key="Nested-gc-retirement"; attribute :>> kind="native"; attribute :>> path="vendor/gambit/lib/_mem/continuation-roots.inc"; attribute :>> scope="root-snapshot-close-and-reader-drain"; ref :>> owner = rootsOwner; }
part need5:NeedRow { attribute :>> key="Nested-code-retirement"; attribute :>> kind="native"; attribute :>> path="vendor/gambit/lib/os_dyn.c"; attribute :>> scope="capture-scanner-native-image-lease-join"; ref :>> owner = codeOwner; }
part need6:NeedRow { attribute :>> key="Nested-c23"; attribute :>> kind="native"; attribute :>> path="vendor/gambit/lib/setup.c"; attribute :>> scope="owner-thread-unwind-and-memory-refinement"; ref :>> owner = controlOwner; }
part need7:NeedRow { attribute :>> key="Nested-entry-lowering"; attribute :>> kind="native"; attribute :>> path="vendor/gambit/gsc/_ptree2.scm"; attribute :>> scope="all-SFUN-CFUN-exit-adapter-coverage"; ref :>> owner = controlOwner; }
part def BindingRow { attribute actionName:String; attribute lemma:String; }
part binding0:BindingRow { attribute :>> actionName="nested_domain_root_retirement.publishRoots"; attribute :>> lemma="NestedDomain.publishRootsPreserves"; }
part binding1:BindingRow { attribute :>> actionName="nested_domain_root_retirement.publicationReplyLost"; attribute :>> lemma="NestedDomain.publicationReplyLostPreserves"; }
part binding2:BindingRow { attribute :>> actionName="nested_domain_root_retirement.publicationAbsentUnknown"; attribute :>> lemma="NestedDomain.publicationAbsentUnknownPreserves"; }
part binding3:BindingRow { attribute :>> actionName="nested_domain_root_retirement.resolvePublication"; attribute :>> lemma="NestedDomain.resolvePublicationPreserves"; }
part binding4:BindingRow { attribute :>> actionName="nested_domain_root_retirement.acknowledgeRoots"; attribute :>> lemma="NestedDomain.acknowledgeRootsPreserves"; }
part binding5:BindingRow { attribute :>> actionName="nested_domain_root_retirement.releaseSource"; attribute :>> lemma="NestedDomain.releaseSourcePreserves"; }
part binding6:BindingRow { attribute :>> actionName="nested_domain_root_retirement.enterOuter"; attribute :>> lemma="NestedDomain.enterOuterPreserves"; }
part binding7:BindingRow { attribute :>> actionName="nested_domain_root_retirement.reserveInnerOffer"; attribute :>> lemma="NestedDomain.reserveInnerOfferPreserves"; }
part binding8:BindingRow { attribute :>> actionName="nested_domain_root_retirement.publishInnerRoots"; attribute :>> lemma="NestedDomain.publishInnerRootsPreserves"; }
part binding9:BindingRow { attribute :>> actionName="nested_domain_root_retirement.acknowledgeInnerRoots"; attribute :>> lemma="NestedDomain.acknowledgeInnerRootsPreserves"; }
part binding10:BindingRow { attribute :>> actionName="nested_domain_root_retirement.releaseInnerSource"; attribute :>> lemma="NestedDomain.releaseInnerSourcePreserves"; }
part binding11:BindingRow { attribute :>> actionName="nested_domain_root_retirement.enterInner"; attribute :>> lemma="NestedDomain.enterInnerPreserves"; }
part binding12:BindingRow { attribute :>> actionName="nested_domain_root_retirement.captureInner"; attribute :>> lemma="NestedDomain.captureInnerPreserves"; }
part binding13:BindingRow { attribute :>> actionName="nested_domain_root_retirement.startGcReader"; attribute :>> lemma="NestedDomain.startGcReaderPreserves"; }
part binding14:BindingRow { attribute :>> actionName="nested_domain_root_retirement.finishGcReader"; attribute :>> lemma="NestedDomain.finishGcReaderPreserves"; }
part binding15:BindingRow { attribute :>> actionName="nested_domain_root_retirement.escrowOuterUnwind"; attribute :>> lemma="NestedDomain.escrowOuterUnwindPreserves"; }
part binding16:BindingRow { attribute :>> actionName="nested_domain_root_retirement.issueOuterUnwind"; attribute :>> lemma="NestedDomain.issueOuterUnwindPreserves"; }
part binding17:BindingRow { attribute :>> actionName="nested_domain_root_retirement.landingObserved"; attribute :>> lemma="NestedDomain.landingObservedPreserves"; }
part binding18:BindingRow { attribute :>> actionName="nested_domain_root_retirement.landingReplyLost"; attribute :>> lemma="NestedDomain.landingReplyLostPreserves"; }
part binding19:BindingRow { attribute :>> actionName="nested_domain_root_retirement.reconcileLanding"; attribute :>> lemma="NestedDomain.reconcileLandingPreserves"; }
part binding20:BindingRow { attribute :>> actionName="nested_domain_root_retirement.settleInnerGuard"; attribute :>> lemma="NestedDomain.settleInnerGuardPreserves"; }
part binding21:BindingRow { attribute :>> actionName="nested_domain_root_retirement.settleOuterGuard"; attribute :>> lemma="NestedDomain.settleOuterGuardPreserves"; }
part binding22:BindingRow { attribute :>> actionName="nested_domain_root_retirement.resumeCaptured"; attribute :>> lemma="NestedDomain.resumeCapturedPreserves"; }
part binding23:BindingRow { attribute :>> actionName="nested_domain_root_retirement.rejectInnerReturn"; attribute :>> lemma="NestedDomain.rejectInnerReturnPreserves"; }
part binding24:BindingRow { attribute :>> actionName="nested_domain_root_retirement.finishResumption"; attribute :>> lemma="NestedDomain.finishResumptionPreserves"; }
part binding25:BindingRow { attribute :>> actionName="nested_domain_root_retirement.closeCapturedHolders"; attribute :>> lemma="NestedDomain.closeCapturedHoldersPreserves"; }
part binding26:BindingRow { attribute :>> actionName="nested_domain_root_retirement.closeRootAdmission"; attribute :>> lemma="NestedDomain.closeRootAdmissionPreserves"; }
part binding27:BindingRow { attribute :>> actionName="nested_domain_root_retirement.closeCodeAdmission"; attribute :>> lemma="NestedDomain.closeCodeAdmissionPreserves"; }
part binding28:BindingRow { attribute :>> actionName="nested_domain_root_retirement.ackRootGrace"; attribute :>> lemma="NestedDomain.ackRootGracePreserves"; }
part binding29:BindingRow { attribute :>> actionName="nested_domain_root_retirement.retireRootSlots"; attribute :>> lemma="NestedDomain.retireRootSlotsPreserves"; }
part binding30:BindingRow { attribute :>> actionName="nested_domain_root_retirement.ackCodeGrace"; attribute :>> lemma="NestedDomain.ackCodeGracePreserves"; }
part binding31:BindingRow { attribute :>> actionName="nested_domain_root_retirement.retireDescriptor"; attribute :>> lemma="NestedDomain.retireDescriptorPreserves"; }
part binding32:BindingRow { attribute :>> actionName="nested_domain_root_retirement.detachNativeOwner"; attribute :>> lemma="NestedDomain.detachNativeOwnerPreserves"; }
part def RouteRow { attribute component:String; attribute actionName:String; attribute lemma:String; attribute producerAnchor:String; attribute obligationId:String; }
part route0:RouteRow { attribute :>> component="roots"; attribute :>> actionName="nested_domain_root_retirement.publishRoots"; attribute :>> lemma="NestedDomain.publishRootsPreserves"; attribute :>> producerAnchor="marker-root"; attribute :>> obligationId="Nested-root-handoff"; }
part route1:RouteRow { attribute :>> component="roots"; attribute :>> actionName="nested_domain_root_retirement.publicationReplyLost"; attribute :>> lemma="NestedDomain.publicationReplyLostPreserves"; attribute :>> producerAnchor="marker-root"; attribute :>> obligationId="Nested-root-handoff"; }
part route2:RouteRow { attribute :>> component="roots"; attribute :>> actionName="nested_domain_root_retirement.publicationAbsentUnknown"; attribute :>> lemma="NestedDomain.publicationAbsentUnknownPreserves"; attribute :>> producerAnchor="marker-root"; attribute :>> obligationId="Nested-root-handoff"; }
part route3:RouteRow { attribute :>> component="roots"; attribute :>> actionName="nested_domain_root_retirement.resolvePublication"; attribute :>> lemma="NestedDomain.resolvePublicationPreserves"; attribute :>> producerAnchor="marker-root"; attribute :>> obligationId="Nested-root-handoff"; }
part route4:RouteRow { attribute :>> component="roots"; attribute :>> actionName="nested_domain_root_retirement.acknowledgeRoots"; attribute :>> lemma="NestedDomain.acknowledgeRootsPreserves"; attribute :>> producerAnchor="marker-root"; attribute :>> obligationId="Nested-root-handoff"; }
part route5:RouteRow { attribute :>> component="roots"; attribute :>> actionName="nested_domain_root_retirement.releaseSource"; attribute :>> lemma="NestedDomain.releaseSourcePreserves"; attribute :>> producerAnchor="marker-root"; attribute :>> obligationId="Nested-root-handoff"; }
part route6:RouteRow { attribute :>> component="control"; attribute :>> actionName="nested_domain_root_retirement.enterOuter"; attribute :>> lemma="NestedDomain.enterOuterPreserves"; attribute :>> producerAnchor="sfun-generator"; attribute :>> obligationId="Nested-entry-lowering"; }
part route7:RouteRow { attribute :>> component="control"; attribute :>> actionName="nested_domain_root_retirement.reserveInnerOffer"; attribute :>> lemma="NestedDomain.reserveInnerOfferPreserves"; attribute :>> producerAnchor="sfun-generator"; attribute :>> obligationId="Nested-entry-lowering"; }
part route8:RouteRow { attribute :>> component="roots"; attribute :>> actionName="nested_domain_root_retirement.publishInnerRoots"; attribute :>> lemma="NestedDomain.publishInnerRootsPreserves"; attribute :>> producerAnchor="marker-root"; attribute :>> obligationId="Nested-root-handoff"; }
part route9:RouteRow { attribute :>> component="roots"; attribute :>> actionName="nested_domain_root_retirement.acknowledgeInnerRoots"; attribute :>> lemma="NestedDomain.acknowledgeInnerRootsPreserves"; attribute :>> producerAnchor="marker-root"; attribute :>> obligationId="Nested-root-handoff"; }
part route10:RouteRow { attribute :>> component="roots"; attribute :>> actionName="nested_domain_root_retirement.releaseInnerSource"; attribute :>> lemma="NestedDomain.releaseInnerSourcePreserves"; attribute :>> producerAnchor="marker-root"; attribute :>> obligationId="Nested-root-handoff"; }
part route11:RouteRow { attribute :>> component="control"; attribute :>> actionName="nested_domain_root_retirement.enterInner"; attribute :>> lemma="NestedDomain.enterInnerPreserves"; attribute :>> producerAnchor="sfun-generator"; attribute :>> obligationId="Nested-entry-lowering"; }
part route12:RouteRow { attribute :>> component="control"; attribute :>> actionName="nested_domain_root_retirement.captureInner"; attribute :>> lemma="NestedDomain.captureInnerPreserves"; attribute :>> producerAnchor="call-catcher"; attribute :>> obligationId="Nested-unwind"; }
part route13:RouteRow { attribute :>> component="roots"; attribute :>> actionName="nested_domain_root_retirement.startGcReader"; attribute :>> lemma="NestedDomain.startGcReaderPreserves"; attribute :>> producerAnchor="context-frame-decode"; attribute :>> obligationId="Nested-gc-retirement"; }
part route14:RouteRow { attribute :>> component="roots"; attribute :>> actionName="nested_domain_root_retirement.finishGcReader"; attribute :>> lemma="NestedDomain.finishGcReaderPreserves"; attribute :>> producerAnchor="context-frame-decode"; attribute :>> obligationId="Nested-gc-retirement"; }
part route15:RouteRow { attribute :>> component="control"; attribute :>> actionName="nested_domain_root_retirement.escrowOuterUnwind"; attribute :>> lemma="NestedDomain.escrowOuterUnwindPreserves"; attribute :>> producerAnchor="call-catcher"; attribute :>> obligationId="Nested-unwind"; }
part route16:RouteRow { attribute :>> component="control"; attribute :>> actionName="nested_domain_root_retirement.issueOuterUnwind"; attribute :>> lemma="NestedDomain.issueOuterUnwindPreserves"; attribute :>> producerAnchor="call-catcher"; attribute :>> obligationId="Nested-unwind"; }
part route17:RouteRow { attribute :>> component="control"; attribute :>> actionName="nested_domain_root_retirement.landingObserved"; attribute :>> lemma="NestedDomain.landingObservedPreserves"; attribute :>> producerAnchor="run-landing"; attribute :>> obligationId="Nested-c23"; }
part route18:RouteRow { attribute :>> component="control"; attribute :>> actionName="nested_domain_root_retirement.landingReplyLost"; attribute :>> lemma="NestedDomain.landingReplyLostPreserves"; attribute :>> producerAnchor="run-landing"; attribute :>> obligationId="Nested-c23"; }
part route19:RouteRow { attribute :>> component="control"; attribute :>> actionName="nested_domain_root_retirement.reconcileLanding"; attribute :>> lemma="NestedDomain.reconcileLandingPreserves"; attribute :>> producerAnchor="run-landing"; attribute :>> obligationId="Nested-c23"; }
part route20:RouteRow { attribute :>> component="control"; attribute :>> actionName="nested_domain_root_retirement.settleInnerGuard"; attribute :>> lemma="NestedDomain.settleInnerGuardPreserves"; attribute :>> producerAnchor="call-catcher"; attribute :>> obligationId="Nested-unwind"; }
part route21:RouteRow { attribute :>> component="control"; attribute :>> actionName="nested_domain_root_retirement.settleOuterGuard"; attribute :>> lemma="NestedDomain.settleOuterGuardPreserves"; attribute :>> producerAnchor="call-catcher"; attribute :>> obligationId="Nested-unwind"; }
part route22:RouteRow { attribute :>> component="control"; attribute :>> actionName="nested_domain_root_retirement.resumeCaptured"; attribute :>> lemma="NestedDomain.resumeCapturedPreserves"; attribute :>> producerAnchor="call-catcher"; attribute :>> obligationId="Nested-unwind"; }
part route23:RouteRow { attribute :>> component="control"; attribute :>> actionName="nested_domain_root_retirement.rejectInnerReturn"; attribute :>> lemma="NestedDomain.rejectInnerReturnPreserves"; attribute :>> producerAnchor="call-catcher"; attribute :>> obligationId="Nested-unwind"; }
part route24:RouteRow { attribute :>> component="control"; attribute :>> actionName="nested_domain_root_retirement.finishResumption"; attribute :>> lemma="NestedDomain.finishResumptionPreserves"; attribute :>> producerAnchor="call-catcher"; attribute :>> obligationId="Nested-unwind"; }
part route25:RouteRow { attribute :>> component="code"; attribute :>> actionName="nested_domain_root_retirement.closeCapturedHolders"; attribute :>> lemma="NestedDomain.closeCapturedHoldersPreserves"; attribute :>> producerAnchor="captured-frame-decode"; attribute :>> obligationId="Nested-code-retirement"; }
part route26:RouteRow { attribute :>> component="roots"; attribute :>> actionName="nested_domain_root_retirement.closeRootAdmission"; attribute :>> lemma="NestedDomain.closeRootAdmissionPreserves"; attribute :>> producerAnchor="context-frame-decode"; attribute :>> obligationId="Nested-gc-retirement"; }
part route27:RouteRow { attribute :>> component="code"; attribute :>> actionName="nested_domain_root_retirement.closeCodeAdmission"; attribute :>> lemma="NestedDomain.closeCodeAdmissionPreserves"; attribute :>> producerAnchor="captured-frame-decode"; attribute :>> obligationId="Nested-code-retirement"; }
part route28:RouteRow { attribute :>> component="roots"; attribute :>> actionName="nested_domain_root_retirement.ackRootGrace"; attribute :>> lemma="NestedDomain.ackRootGracePreserves"; attribute :>> producerAnchor="context-frame-decode"; attribute :>> obligationId="Nested-gc-retirement"; }
part route29:RouteRow { attribute :>> component="roots"; attribute :>> actionName="nested_domain_root_retirement.retireRootSlots"; attribute :>> lemma="NestedDomain.retireRootSlotsPreserves"; attribute :>> producerAnchor="context-frame-decode"; attribute :>> obligationId="Nested-gc-retirement"; }
part route30:RouteRow { attribute :>> component="code"; attribute :>> actionName="nested_domain_root_retirement.ackCodeGrace"; attribute :>> lemma="NestedDomain.ackCodeGracePreserves"; attribute :>> producerAnchor="captured-frame-decode"; attribute :>> obligationId="Nested-code-retirement"; }
part route31:RouteRow { attribute :>> component="code"; attribute :>> actionName="nested_domain_root_retirement.retireDescriptor"; attribute :>> lemma="NestedDomain.retireDescriptorPreserves"; attribute :>> producerAnchor="captured-frame-decode"; attribute :>> obligationId="Nested-code-retirement"; }
part route32:RouteRow { attribute :>> component="control"; attribute :>> actionName="nested_domain_root_retirement.detachNativeOwner"; attribute :>> lemma="NestedDomain.detachNativeOwnerPreserves"; attribute :>> producerAnchor="run-landing"; attribute :>> obligationId="Nested-c23"; }
part def ProofRow { attribute key:String; attribute lemma:String; }
part proof0:ProofRow { attribute :>> key="initialSafe"; attribute :>> lemma="NestedDomain.initialSafe"; }
part proof1:ProofRow { attribute :>> key="stepPreserves"; attribute :>> lemma="NestedDomain.stepPreserves"; }
part proof2:ProofRow { attribute :>> key="reachableSafe"; attribute :>> lemma="NestedDomain.reachableSafe"; }
part proof3:ProofRow { attribute :>> key="innerEntryHandoff"; attribute :>> lemma="NestedDomain.innerEntryHandoff"; }
part proof4:ProofRow { attribute :>> key="entryHandoff"; attribute :>> lemma="NestedDomain.entryHandoff"; }
part proof5:ProofRow { attribute :>> key="outerInvalidatesInner"; attribute :>> lemma="NestedDomain.outerInvalidatesInner"; }
part proof6:ProofRow { attribute :>> key="unknownKeepsCustody"; attribute :>> lemma="NestedDomain.unknownKeepsCustody"; }
part proof7:ProofRow { attribute :>> key="scannerPinsDescriptor"; attribute :>> lemma="NestedDomain.scannerPinsDescriptor"; }
part proof8:ProofRow { attribute :>> key="capturePinsDescriptor"; attribute :>> lemma="NestedDomain.capturePinsDescriptor"; }
part proof9:ProofRow { attribute :>> key="descriptorRetirementCut"; attribute :>> lemma="NestedDomain.descriptorRetirementCut"; }
part proof10:ProofRow { attribute :>> key="lateEntryClosed"; attribute :>> lemma="NestedDomain.lateEntryClosed"; }
part proof11:ProofRow { attribute :>> key="retiredRootsNoReader"; attribute :>> lemma="NestedDomain.retiredRootsNoReader"; }
part proof12:ProofRow { attribute :>> key="settledOuterNeedsSettledInner"; attribute :>> lemma="NestedDomain.settledOuterNeedsSettledInner"; }
part proof13:ProofRow { attribute :>> key="resumptionNoNativeRevival"; attribute :>> lemma="NestedDomain.resumptionNoNativeRevival"; }
part def PaperRow { attribute key:String; attribute title:String; attribute url:String; attribute section:String; attribute basis:String; attribute boundary:String; }
part paper0:PaperRow { attribute :>> key="gambit-pvm"; attribute :>> title="Feeley and Miller: A parallel virtual machine for efficient Scheme compilation"; attribute :>> url="https://www.iro.umontreal.ca/~feeley/papers/FeeleyMillerLFP90.pdf"; attribute :>> section="2"; attribute :>> basis="Front/back-end contract carries machine-specific facts"; attribute :>> boundary="Historical PVM is not a current C23 ABI proof"; }
part paper1:PaperRow { attribute :>> key="gambit-c-segments"; attribute :>> title="Feeley: Portable first-class continuations with C"; attribute :>> url="https://www.schemeworkshop.org/2000/feeley.ps"; attribute :>> section="1-5"; attribute :>> basis="Unlimited Scheme extent differs from dynamic C extent; independent native segments proposed"; attribute :>> boundary="Section 5 says not implemented then; preserve arbitrary C local state; no historical timings transferred"; }
part paper2:PaperRow { attribute :>> key="ocaml-effects"; attribute :>> title="Retrofitting Effect Handlers onto OCaml"; attribute :>> url="https://anil.recoil.org/papers/2021-pldi-retroeff.pdf"; attribute :>> section="3.1 and 5.3"; attribute :>> basis="Separate system/fiber stacks and explicit callback transitions"; attribute :>> boundary="One-shot effects do not cross C frames; neither restriction is silently applied to Gambit"; }
part paper3:PaperRow { attribute :>> key="c23-draft"; attribute :>> title="WG14 N3096 C23 working draft"; attribute :>> url="https://www.open-std.org/jtc1/sc22/wg14/www/docs/n3096.pdf"; attribute :>> section="5.1.2.4; 7.13.2.1"; attribute :>> basis="Release/acquire publication; longjmp requires same thread and live setjmp invocation"; attribute :>> boundary="Working draft, not purchased final ISO text; atomics do not extend C automatic lifetime"; }
part paper4:PaperRow { attribute :>> key="chez-stale-native"; attribute :>> title="Chez Scheme foreign interface"; attribute :>> url="https://cisco.github.io/ChezScheme/csug10.3.0/foreign.html"; attribute :>> section="4.4 and callback registration example"; attribute :>> basis="Nested foreign contexts become stale on return below them; callback code needs explicit retention"; attribute :>> boundary="Comparative mechanism only; not a Gambit implementation proof"; }
part def GroundingRow { attribute component:String; attribute producerAnchor:String; attribute paperKey:String; attribute obligationId:String; }
part grounding0:GroundingRow { attribute :>> component="control"; attribute :>> producerAnchor="call-catcher"; attribute :>> paperKey="gambit-c-segments"; attribute :>> obligationId="Nested-unwind"; }
part grounding1:GroundingRow { attribute :>> component="control"; attribute :>> producerAnchor="sfun-generator"; attribute :>> paperKey="gambit-pvm"; attribute :>> obligationId="Nested-entry-lowering"; }
part grounding2:GroundingRow { attribute :>> component="roots"; attribute :>> producerAnchor="context-frame-decode"; attribute :>> paperKey="ocaml-effects"; attribute :>> obligationId="Nested-gc-retirement"; }
part grounding3:GroundingRow { attribute :>> component="control"; attribute :>> producerAnchor="catcher-local"; attribute :>> paperKey="c23-draft"; attribute :>> obligationId="Nested-c23"; }
part grounding4:GroundingRow { attribute :>> component="code"; attribute :>> producerAnchor="captured-frame-decode"; attribute :>> paperKey="chez-stale-native"; attribute :>> obligationId="Nested-code-retirement"; }
part def GainRow { attribute key:String; attribute avoided:String; attribute added:String; attribute condition:String; }
part gain0:GainRow { attribute :>> key="G1"; attribute :>> avoided="Capture/restoration remains Scheme control independent of native stack return"; attribute :>> added="One fresh execution guard and ticket for each managed resumption"; attribute :>> condition="Two modeled resumptions; no baseline OS-thread-count saving claimed"; }
part gain1:GainRow { attribute :>> key="G2"; attribute :>> avoided="Outer unwind cannot silently abandon admitted inner root/code custody"; attribute :>> added="O(d) descendant closure and lease transfer for d affected native domains"; attribute :>> condition="No claim that sequential END_SFUN cleanup already covers every unwind"; }
part gain2:GainRow { attribute :>> key="G3"; attribute :>> avoided="Retirement checks can reuse one subtree/root/code ledger"; attribute :>> added="Ledger publication, pinning and acknowledgement traffic"; attribute :>> condition="Only if it replaces duplicated adapter state; layering it over old ownership has no demonstrated work saving"; }
part gain3:GainRow { attribute :>> key="G4"; attribute :>> avoided="Known native frame expiry need not force retention of whole execution context"; attribute :>> added="Separate RootBundle, captured frames and image leases"; attribute :>> condition="Safe separation is conditional; object bytes and exact root/descriptor closure remain unresolved"; }
part gain4:GainRow { attribute :>> key="G5"; attribute :>> avoided="Independent compilation contexts can share the same explicit entry schema"; attribute :>> added="Native owner pin occupancy and per-context root registry support"; attribute :>> condition="Parallel gxi/gxc throughput is not proved by this lifetime model"; }
part gain5:GainRow { attribute :>> key="G6"; attribute :>> avoided="Roots may retire while descriptor lease still protects a captured frame or scanner in a general design"; attribute :>> added="This bounded conservative model waits for captures then root readers; descriptor release follows"; attribute :>> condition="No prompt-reclamation or reduced scan-count claim without a less conservative product proof"; }
part gain6:GainRow { attribute :>> key="G7"; attribute :>> avoided="C23 can express the whole contract; no extra language is required for it"; attribute :>> added="C23 ABI adapters, atomic publication and reader retirement remain necessary"; attribute :>> condition="Zig adds the same semantic work; incremental net benefit remains unproved"; }
part def MemoryRow { attribute key:String; attribute publication:String; attribute observation:String; attribute obligation:String; }
part memory0:MemoryRow { attribute :>> key="root-publication"; attribute :>> publication="Initialize bundle slots and descriptor leases before release publication"; attribute :>> observation="Acquire registry snapshot or registration lock, then pin actual slots"; attribute :>> obligation="Source release requires a qualifying root-round receipt; sampling reader count zero is not a receipt"; }
part memory1:MemoryRow { attribute :>> key="subtree-escrow"; attribute :>> publication="Fill stable operation record and retain descendant roots/code before release publishing escrow"; attribute :>> observation="Owning thread acquires/validates exact closed subtree before longjmp"; attribute :>> obligation="Atomic abstract escrow requires a native refinement; two separate guard stores are not an atomic transaction"; }
part memory2:MemoryRow { attribute :>> key="landing-reply"; attribute :>> publication="Release commit landing record after exact target catcher is reached"; attribute :>> observation="Acquire same operation identity; missing reply remains unknown"; attribute :>> obligation="No timeout can substitute for a landing or failure receipt"; }
part memory3:MemoryRow { attribute :>> key="root-retirement"; attribute :>> publication="Close bundle admission acq_rel and release last admitted scanner pin"; attribute :>> observation="Acquire observes closed admission and scanner grace"; attribute :>> obligation="GC must not wait on a guard that waits for that same GC; existing scanners finish while guards stay rooted"; }
part memory4:MemoryRow { attribute :>> key="image-retirement"; attribute :>> publication="Retain image/code leases for captured frames and admitted scanners"; attribute :>> observation="Acquire aggregate root/code/native-owner closure across all VMs"; attribute :>> obligation="Marker invalidation and frame_access gate release alone are not global unload permission"; }
part def ContractRow { attribute fromNode:String; attribute toNode:String; attribute custody:String; }
part contract0:ContractRow { attribute :>> fromNode="Admitted_Outer_Source"; attribute :>> toNode="Outer_Target_Roots"; attribute :>> custody="publish; collective scan admission ack; source release"; }
part contract1:ContractRow { attribute :>> fromNode="Outer_Target_Roots"; attribute :>> toNode="Outer_Guard"; attribute :>> custody="rooted entry and descriptor lease"; }
part contract2:ContractRow { attribute :>> fromNode="Outer_Guard"; attribute :>> toNode="Admitted_Inner_Source"; attribute :>> custody="source protected before callback payload read"; }
part contract3:ContractRow { attribute :>> fromNode="Admitted_Inner_Source"; attribute :>> toNode="Inner_Target_Roots"; attribute :>> custody="publish; separate ack; release source"; }
part contract4:ContractRow { attribute :>> fromNode="Inner_Target_Roots"; attribute :>> toNode="Inner_Guard"; attribute :>> custody="fresh activation and native return domain"; }
part contract5:ContractRow { attribute :>> fromNode="Inner_Guard"; attribute :>> toNode="Captured_Scheme_Frames"; attribute :>> custody="multi-shot frames retain descriptor dependency"; }
part contract6:ContractRow { attribute :>> fromNode="Inner_Guard"; attribute :>> toNode="Stable_Subtree_Escrow"; attribute :>> custody="outer unwind closes descendants and transfers custody"; }
part contract7:ContractRow { attribute :>> fromNode="Stable_Subtree_Escrow"; attribute :>> toNode="Landing_Or_Unknown"; attribute :>> custody="invalidate native return rights; retain all leases"; }
part contract8:ContractRow { attribute :>> fromNode="Landing_Or_Unknown"; attribute :>> toNode="Known_Landing"; attribute :>> custody="only exact target/thread/operation receipt qualifies"; }
part contract9:ContractRow { attribute :>> fromNode="Landing_Or_Unknown"; attribute :>> toNode="Unknown_Custody"; attribute :>> custody="lost reply; no timeout-based freeing"; }
part contract10:ContractRow { attribute :>> fromNode="Known_Landing"; attribute :>> toNode="Postorder_Guard_Settlement"; attribute :>> custody="inner first; then outer"; }
part contract11:ContractRow { attribute :>> fromNode="Postorder_Guard_Settlement"; attribute :>> toNode="Root_Admission_Close"; attribute :>> custody="also require holders and fresh resumptions drained"; }
part contract12:ContractRow { attribute :>> fromNode="Root_Admission_Close"; attribute :>> toNode="Root_Grace"; attribute :>> custody="already admitted GC readers continue"; }
part contract13:ContractRow { attribute :>> fromNode="Root_Grace"; attribute :>> toNode="Root_Slots_Retired"; attribute :>> custody="source/target slots no longer borrowed"; }
part contract14:ContractRow { attribute :>> fromNode="Captured_Scheme_Frames"; attribute :>> toNode="Image_Lease_Join"; attribute :>> custody="logical native return stale; descriptor still live"; }
part contract15:ContractRow { attribute :>> fromNode="Root_Slots_Retired"; attribute :>> toNode="Image_Lease_Join"; attribute :>> custody="code-reader grace and known native exit"; }
part contract16:ContractRow { attribute :>> fromNode="Image_Lease_Join"; attribute :>> toNode="Local_Descriptor_Retired"; attribute :>> custody="other VM/image owners remain an external condition"; }
part def RoleRow { attribute key:String; attribute identity:String; attribute retirement:String; attribute boundary:String; }
part role0:RoleRow { attribute :>> key="IngressRootDelivery"; attribute :>> identity="Outer and inner source/target slots have separate acknowledgement"; attribute :>> retirement="Source storage ends after target root coverage is acknowledged"; attribute :>> boundary="Both source carriers are admitted premises; raw ClientData needs an earlier pin"; }
part role1:RoleRow { attribute :>> key="NestedNativeReturnDomain"; attribute :>> identity="Parent/child native extents and generation-bearing return authority"; attribute :>> retirement="Outer unwind invalidates affected descendant return targets"; attribute :>> boundary="Invalidation does not imply guard settlement or descriptor death"; }
part role2:RoleRow { attribute :>> key="StableUnwindEscrow"; attribute :>> identity="Stable operation identity, exact affected subtree, root/code custody"; attribute :>> retirement="Known landing plus per-activation settlement"; attribute :>> boundary="Unknown landing retains ownership; no retry of an arbitrary longjmp"; }
part role3:RoleRow { attribute :>> key="CollectorRootReader"; attribute :>> identity="Already admitted root snapshot and frame descriptor reader"; attribute :>> retirement="Finish scan and release root/code leases"; attribute :>> boundary="Closed external/native entry does not revoke admitted maintenance access"; }
part role4:RoleRow { attribute :>> key="DescriptorRetirement"; attribute :>> identity="Captured Scheme frames, scanners, native frames and other VM image owners"; attribute :>> retirement="All corresponding leases drained after admission closure"; attribute :>> boundary="This model is one local owner; global image unload remains a separate product"; }
part def CompositionRow { attribute key:String; attribute fromAction:String; attribute toAction:String; attribute lemma:String; attribute fromComponent:String; attribute toComponent:String; attribute sharedConstraint:String; }
part composition0:CompositionRow { attribute :>> key="entry-root-to-inner"; attribute :>> fromAction="nested_domain_root_retirement.releaseInnerSource"; attribute :>> toAction="nested_domain_root_retirement.enterInner"; attribute :>> lemma="NestedDomain.innerEntryHandoff"; attribute :>> fromComponent="roots"; attribute :>> toComponent="control"; attribute :>> sharedConstraint="Target registration and collective acknowledgement precede inner entry"; }
part composition1:CompositionRow { attribute :>> key="unwind-to-landing"; attribute :>> fromAction="nested_domain_root_retirement.escrowOuterUnwind"; attribute :>> toAction="nested_domain_root_retirement.landingObserved"; attribute :>> lemma="NestedDomain.outerInvalidatesInner"; attribute :>> fromComponent="control"; attribute :>> toComponent="control"; attribute :>> sharedConstraint="An outer unwind revokes both return rights; it does not free inner resources"; }
part composition2:CompositionRow { attribute :>> key="unknown-to-roots"; attribute :>> fromAction="nested_domain_root_retirement.landingReplyLost"; attribute :>> toAction="nested_domain_root_retirement.finishGcReader"; attribute :>> lemma="NestedDomain.unknownKeepsCustody"; attribute :>> fromComponent="control"; attribute :>> toComponent="roots"; attribute :>> sharedConstraint="Unknown native exit retains both guards and roots while GC can finish"; }
part composition3:CompositionRow { attribute :>> key="capture-to-code"; attribute :>> fromAction="nested_domain_root_retirement.resumeCaptured"; attribute :>> toAction="nested_domain_root_retirement.retireDescriptor"; attribute :>> lemma="NestedDomain.capturePinsDescriptor"; attribute :>> fromComponent="control"; attribute :>> toComponent="code"; attribute :>> sharedConstraint="Native frame expiry does not remove captured Scheme frame descriptor dependency"; }
part composition4:CompositionRow { attribute :>> key="scanner-to-code"; attribute :>> fromAction="nested_domain_root_retirement.startGcReader"; attribute :>> toAction="nested_domain_root_retirement.retireDescriptor"; attribute :>> lemma="NestedDomain.scannerPinsDescriptor"; attribute :>> fromComponent="roots"; attribute :>> toComponent="code"; attribute :>> sharedConstraint="Root scanner and code descriptor retirement share reader closure"; }
part composition5:CompositionRow { attribute :>> key="guard-to-root-close"; attribute :>> fromAction="nested_domain_root_retirement.settleOuterGuard"; attribute :>> toAction="nested_domain_root_retirement.closeRootAdmission"; attribute :>> lemma="NestedDomain.settledOuterNeedsSettledInner"; attribute :>> fromComponent="control"; attribute :>> toComponent="roots"; attribute :>> sharedConstraint="Inner settled first; captures and fresh execution guards must also drain"; }

part proof14:ProofRow { attribute :>> key="unwindCannotReviveInner"; attribute :>> lemma="NestedDomain.unwindCannotReviveInner"; }

part proof15:ProofRow { attribute :>> key="resumptionTicketIncrements"; attribute :>> lemma="NestedDomain.resumptionTicketIncrements"; }
}
