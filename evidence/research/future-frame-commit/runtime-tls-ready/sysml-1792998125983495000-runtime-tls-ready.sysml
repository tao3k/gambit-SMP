package GambitRuntimeTlsReady { private import ScalarValues::*;
part def SourceRow { attribute key:String; attribute path:String; attribute needle:String; attribute limit:String; }
part source0:SourceRow { attribute :>> key="global-init"; attribute :>> path="evidence/research/source-references/tcl/cbf86d62348d6b052e1961b4df995960fb21545f/generic/tclEvent.c"; attribute :>> needle="TclInitSubsystems(void)"; attribute :>> limit="generic subsystem flag is distinct from allocator tables/key publication"; }
part source1:SourceRow { attribute :>> key="static-bootstrap"; attribute :>> path="evidence/research/source-references/tcl/cbf86d62348d6b052e1961b4df995960fb21545f/unix/tclUnixThrd.c"; attribute :>> needle="static pthread_mutex_t allocLock = PTHREAD_MUTEX_INITIALIZER;"; attribute :>> limit="bootstrap allocator mutex uses no dynamic storage"; }
part source2:SourceRow { attribute :>> key="bucket-init"; attribute :>> path="evidence/research/source-references/tcl/cbf86d62348d6b052e1961b4df995960fb21545f/generic/tclThreadAlloc.c"; attribute :>> needle="bucketInfo[i].blockSize = MINALLOC << i;"; attribute :>> limit="listLockPtr already assigned before all table/objLock initialization"; }
part source3:SourceRow { attribute :>> key="generic-key"; attribute :>> path="evidence/research/source-references/tcl/cbf86d62348d6b052e1961b4df995960fb21545f/generic/tclThreadStorage.c"; attribute :>> needle="tsdGlobal.key = TclpThreadCreateKey();"; attribute :>> limit="generic TSD key distinct from allocator cache key"; }
part source4:SourceRow { attribute :>> key="unix-key"; attribute :>> path="evidence/research/source-references/tcl/cbf86d62348d6b052e1961b4df995960fb21545f/unix/tclUnixThrd.c"; attribute :>> needle="pthread_key_create(&key, NULL);"; attribute :>> limit="allocator key create status ignored; no allocator destructor registered"; }
part source5:SourceRow { attribute :>> key="unix-set"; attribute :>> path="evidence/research/source-references/tcl/cbf86d62348d6b052e1961b4df995960fb21545f/unix/tclUnixThrd.c"; attribute :>> needle="pthread_setspecific(key, arg);"; attribute :>> limit="allocator setter ignores return status"; }
part source6:SourceRow { attribute :>> key="checked-set"; attribute :>> path="evidence/research/source-references/tcl/cbf86d62348d6b052e1961b4df995960fb21545f/unix/tclUnixThrd.c"; attribute :>> needle="if (pthread_setspecific(*ptkeyPtr, ptr)) {"; attribute :>> limit="generic helper checks result, but requires its own key-storage lifecycle"; }
part source7:SourceRow { attribute :>> key="unix-clear"; attribute :>> path="evidence/research/source-references/tcl/cbf86d62348d6b052e1961b4df995960fb21545f/unix/tclUnixThrd.c"; attribute :>> needle="pthread_setspecific(key, NULL);"; attribute :>> limit="allocator clear status ignored and occurs after cache free"; }
part source8:SourceRow { attribute :>> key="unix-key-delete"; attribute :>> path="evidence/research/source-references/tcl/cbf86d62348d6b052e1961b4df995960fb21545f/unix/tclUnixThrd.c"; attribute :>> needle="pthread_key_delete(key);"; attribute :>> limit="allocator key delete status ignored"; }
part source9:SourceRow { attribute :>> key="free-before-clear"; attribute :>> path="evidence/research/source-references/tcl/cbf86d62348d6b052e1961b4df995960fb21545f/unix/tclUnixThrd.c"; attribute :>> needle="TclFreeAllocCache(ptr);"; attribute :>> limit="both platform alloc-cache cleanup bodies free before TLS clear"; }
part source10:SourceRow { attribute :>> key="windows-status"; attribute :>> path="evidence/research/source-references/tcl/cbf86d62348d6b052e1961b4df995960fb21545f/win/tclWinThrd.c"; attribute :>> needle="Tcl_Panic(\"TlsSetValue failed from TclpSetAllocCache\");"; attribute :>> limit="checked setter fails through panic; normal-return inference needs panic/provider qualification"; }
part source11:SourceRow { attribute :>> key="windows-key"; attribute :>> path="evidence/research/source-references/tcl/cbf86d62348d6b052e1961b4df995960fb21545f/win/tclWinThrd.c"; attribute :>> needle="tlsKey = TlsAlloc();"; attribute :>> limit="plain once flag and checked allocation failure; caller serialization still required"; }
part source12:SourceRow { attribute :>> key="plain-flags"; attribute :>> path="evidence/research/source-references/tcl/cbf86d62348d6b052e1961b4df995960fb21545f/unix/tclUnixThrd.c"; attribute :>> needle="static volatile int initialized = 0;"; attribute :>> limit="volatile is not a C23 same-epoch acquire witness"; }
part source13:SourceRow { attribute :>> key="fast-slot"; attribute :>> path="evidence/research/source-references/tcl/cbf86d62348d6b052e1961b4df995960fb21545f/generic/tclThreadAlloc.c"; attribute :>> needle="tcachePtr = GetCache();"; attribute :>> limit="fast TLS assignment; captured cleanup code never explicitly clears static tcachePtr"; }
part source14:SourceRow { attribute :>> key="thread-exit"; attribute :>> path="evidence/research/source-references/tcl/cbf86d62348d6b052e1961b4df995960fb21545f/generic/tclThread.c"; attribute :>> needle="TclFinalizeThreadAllocThread();"; attribute :>> limit="normal nonquick thread-data cleanup invokes allocator thread finalization"; }
part source15:SourceRow { attribute :>> key="exit-callback"; attribute :>> path="evidence/research/source-references/tcl/cbf86d62348d6b052e1961b4df995960fb21545f/generic/tclEvent.c"; attribute :>> needle="exitPtr->proc(exitPtr->clientData);"; attribute :>> limit="thread exit handlers are called before TSD/cache cleanup"; }
part source16:SourceRow { attribute :>> key="process-finalize"; attribute :>> path="evidence/research/source-references/tcl/cbf86d62348d6b052e1961b4df995960fb21545f/generic/tclEvent.c"; attribute :>> needle="TclFinalizeSynchronization();"; attribute :>> limit="generic synchronization cleanup before allocator-specific teardown"; }
part source17:SourceRow { attribute :>> key="tsd-recreate"; attribute :>> path="evidence/research/source-references/tcl/cbf86d62348d6b052e1961b4df995960fb21545f/generic/tclEvent.c"; attribute :>> needle="TclFinalizeThreadData(/* quick */ 0);"; attribute :>> limit="process finalization repeats cleanup because intermediate work can recreate TSD"; }
part source18:SourceRow { attribute :>> key="all-threads"; attribute :>> path="evidence/research/source-references/tcl/cbf86d62348d6b052e1961b4df995960fb21545f/generic/tclThreadStorage.c"; attribute :>> needle="IMPORTANT: All Tcl threads must be finalized before calling this!"; attribute :>> limit="source precondition is not an implemented all-owner receipt"; }
part source19:SourceRow { attribute :>> key="generic-key-delete"; attribute :>> path="evidence/research/source-references/tcl/cbf86d62348d6b052e1961b4df995960fb21545f/generic/tclThreadStorage.c"; attribute :>> needle="TclpThreadDeleteKey(tsdGlobal.key);"; attribute :>> limit="generic key deletion is separate from allocator key deletion"; }
part source20:SourceRow { attribute :>> key="allocator-finalize"; attribute :>> path="evidence/research/source-references/tcl/cbf86d62348d6b052e1961b4df995960fb21545f/generic/tclThreadAlloc.c"; attribute :>> needle="TclpFreeAllocCache(NULL);"; attribute :>> limit="allocator lock teardown then platform allocator-key retirement in legacy path"; }
part source21:SourceRow { attribute :>> key="prior"; attribute :>> path="dev/refactoring/modern-c/models/quint/cache_ready_publication.qnt"; attribute :>> needle="action installTlsKnown="; attribute :>> limit="actual parent install-receipt action; metadata mirror remains conditional"; }
part source22:SourceRow { attribute :>> key="helper-alloc"; attribute :>> path="evidence/research/source-references/tcl/cbf86d62348d6b052e1961b4df995960fb21545f/unix/tclUnixThrd.c"; attribute :>> needle="ptkeyPtr = (pthread_key_t *)TclpSysAlloc(sizeof(pthread_key_t), 0);"; attribute :>> limit="generic checked key helper allocates wrapper; not a zero-cost bootstrap substitute"; }
part source23:SourceRow { attribute :>> key="generic-set-status"; attribute :>> path="evidence/research/source-references/tcl/cbf86d62348d6b052e1961b4df995960fb21545f/unix/tclUnixThrd.c"; attribute :>> needle="if (pthread_key_delete(*ptkeyPtr)) {"; attribute :>> limit="checked generic delete contrasted with unchecked specialized allocator path"; }
part def ObligationRow { attribute key:String; attribute status:String; attribute condition:String; }
part obligation0:ObligationRow { attribute :>> key="service-safety"; attribute :>> status="conditional-model"; attribute :>> condition="one admitted owner, stable supervisor, epoch-stamped handles and authoritative key/install/clear outcomes"; }
part obligation1:ObligationRow { attribute :>> key="platform-source"; attribute :>> status="source-bound"; attribute :>> condition="five newly captured files match immutable tree blob/size; POSIX/Windows policies and call chains distinguished"; }
part obligation2:ObligationRow { attribute :>> key="bootstrap-reentry"; attribute :>> status="unresolved"; attribute :>> condition="all initialization callback targets, partial capability DAG and static-lock/direct allocator closure"; }
part obligation3:ObligationRow { attribute :>> key="status-provider"; attribute :>> status="unresolved"; attribute :>> condition="Unix statuses must be observed or qualified; Windows panic/nonreturn/SEH and exact operation outcomes"; }
part obligation4:ObligationRow { attribute :>> key="fast-thread-exit"; attribute :>> status="unresolved"; attribute :>> condition="all raw fast readers, explicit same-thread invalidation or verified OS-thread-death/join; returned finalization is not death"; }
part obligation5:ObligationRow { attribute :>> key="roster-cleanup"; attribute :>> status="unresolved"; attribute :>> condition="all admitted native owners and inherited finalization producers close; repeat TSD and every unknown result settled"; }
part obligation6:ObligationRow { attribute :>> key="c23-order"; attribute :>> status="unresolved"; attribute :>> condition="real matching release/acquire/reads-from at same runtime and cache epoch; legacy plain/volatile flags not proof"; }
part obligation7:ObligationRow { attribute :>> key="full-refinement"; attribute :>> status="unresolved"; attribute :>> condition="loaded platform profile, arbitrary owner count/epochs, native CFG and full parent product not established"; }
part def RouteRow { attribute actionName:String; attribute lemma:String; attribute source:String; attribute obligation:String; }
part route0:RouteRow { attribute :>> actionName="beginThreadClose"; attribute :>> lemma="RuntimeTlsReady.beginThreadClosePreserves"; attribute :>> source="thread-exit"; attribute :>> obligation="service-safety"; }
part route1:RouteRow { attribute :>> actionName="rebindCache"; attribute :>> lemma="RuntimeTlsReady.rebindCachePreserves"; attribute :>> source="fast-slot"; attribute :>> obligation="service-safety"; }
part route2:RouteRow { attribute :>> actionName="refreshHandle"; attribute :>> lemma="RuntimeTlsReady.refreshHandlePreserves"; attribute :>> source="fast-slot"; attribute :>> obligation="service-safety"; }
part route3:RouteRow { attribute :>> actionName="closeEmptyOwner"; attribute :>> lemma="RuntimeTlsReady.closeEmptyOwnerPreserves"; attribute :>> source="thread-exit"; attribute :>> obligation="service-safety"; }
part route4:RouteRow { attribute :>> actionName="reserveRuntime"; attribute :>> lemma="RuntimeTlsReady.reserveRuntimePreserves"; attribute :>> source="global-init"; attribute :>> obligation="service-safety"; }
part route5:RouteRow { attribute :>> actionName="initializeLocks"; attribute :>> lemma="RuntimeTlsReady.initializeLocksPreserves"; attribute :>> source="static-bootstrap"; attribute :>> obligation="service-safety"; }
part route6:RouteRow { attribute :>> actionName="initializeTables"; attribute :>> lemma="RuntimeTlsReady.initializeTablesPreserves"; attribute :>> source="bucket-init"; attribute :>> obligation="service-safety"; }
part route7:RouteRow { attribute :>> actionName="createGenericKey"; attribute :>> lemma="RuntimeTlsReady.createGenericKeyPreserves"; attribute :>> source="generic-key"; attribute :>> obligation="service-safety"; }
part route8:RouteRow { attribute :>> actionName="createAllocKeyKnown"; attribute :>> lemma="RuntimeTlsReady.createAllocKeyKnownPreserves"; attribute :>> source="unix-key"; attribute :>> obligation="service-safety"; }
part route9:RouteRow { attribute :>> actionName="createAllocKeyUnknown"; attribute :>> lemma="RuntimeTlsReady.createAllocKeyUnknownPreserves"; attribute :>> source="unix-key"; attribute :>> obligation="service-safety"; }
part route10:RouteRow { attribute :>> actionName="bootstrapBorrow"; attribute :>> lemma="RuntimeTlsReady.bootstrapBorrowPreserves"; attribute :>> source="init-reentry"; attribute :>> obligation="service-safety"; }
part route11:RouteRow { attribute :>> actionName="bootstrapReturn"; attribute :>> lemma="RuntimeTlsReady.bootstrapReturnPreserves"; attribute :>> source="init-reentry"; attribute :>> obligation="service-safety"; }
part route12:RouteRow { attribute :>> actionName="initializationReentry"; attribute :>> lemma="RuntimeTlsReady.initializationReentryPreserves"; attribute :>> source="init-reentry"; attribute :>> obligation="service-safety"; }
part route13:RouteRow { attribute :>> actionName="publishRuntime"; attribute :>> lemma="RuntimeTlsReady.publishRuntimePreserves"; attribute :>> source="global-init"; attribute :>> obligation="service-safety"; }
part route14:RouteRow { attribute :>> actionName="observeRuntime"; attribute :>> lemma="RuntimeTlsReady.observeRuntimePreserves"; attribute :>> source="plain-flags"; attribute :>> obligation="service-safety"; }
part route15:RouteRow { attribute :>> actionName="beginCacheInstall"; attribute :>> lemma="RuntimeTlsReady.beginCacheInstallPreserves"; attribute :>> source="unix-set"; attribute :>> obligation="service-safety"; }
part route16:RouteRow { attribute :>> actionName="rawSetterReturned"; attribute :>> lemma="RuntimeTlsReady.rawSetterReturnedPreserves"; attribute :>> source="unix-set"; attribute :>> obligation="service-safety"; }
part route17:RouteRow { attribute :>> actionName="recordKnownInstall"; attribute :>> lemma="RuntimeTlsReady.recordKnownInstallPreserves"; attribute :>> source="checked-set"; attribute :>> obligation="service-safety"; }
part route18:RouteRow { attribute :>> actionName="installUnknown"; attribute :>> lemma="RuntimeTlsReady.installUnknownPreserves"; attribute :>> source="unix-set"; attribute :>> obligation="service-safety"; }
part route19:RouteRow { attribute :>> actionName="publishCache"; attribute :>> lemma="RuntimeTlsReady.publishCachePreserves"; attribute :>> source="fast-slot"; attribute :>> obligation="service-safety"; }
part route20:RouteRow { attribute :>> actionName="publishFast"; attribute :>> lemma="RuntimeTlsReady.publishFastPreserves"; attribute :>> source="fast-slot"; attribute :>> obligation="service-safety"; }
part route21:RouteRow { attribute :>> actionName="acquireNormal"; attribute :>> lemma="RuntimeTlsReady.acquireNormalPreserves"; attribute :>> source="fast-slot"; attribute :>> obligation="service-safety"; }
part route22:RouteRow { attribute :>> actionName="releaseNormal"; attribute :>> lemma="RuntimeTlsReady.releaseNormalPreserves"; attribute :>> source="thread-exit"; attribute :>> obligation="service-safety"; }
part route23:RouteRow { attribute :>> actionName="admitFinalizer"; attribute :>> lemma="RuntimeTlsReady.admitFinalizerPreserves"; attribute :>> source="exit-callback"; attribute :>> obligation="service-safety"; }
part route24:RouteRow { attribute :>> actionName="beginGlobalClose"; attribute :>> lemma="RuntimeTlsReady.beginGlobalClosePreserves"; attribute :>> source="process-finalize"; attribute :>> obligation="service-safety"; }
part route25:RouteRow { attribute :>> actionName="deriveLateTsdWork"; attribute :>> lemma="RuntimeTlsReady.deriveLateTsdWorkPreserves"; attribute :>> source="tsd-recreate"; attribute :>> obligation="service-safety"; }
part route26:RouteRow { attribute :>> actionName="drainLateTsdWork"; attribute :>> lemma="RuntimeTlsReady.drainLateTsdWorkPreserves"; attribute :>> source="tsd-recreate"; attribute :>> obligation="service-safety"; }
part route27:RouteRow { attribute :>> actionName="finishFinalizer"; attribute :>> lemma="RuntimeTlsReady.finishFinalizerPreserves"; attribute :>> source="exit-callback"; attribute :>> obligation="service-safety"; }
part route28:RouteRow { attribute :>> actionName="closeCache"; attribute :>> lemma="RuntimeTlsReady.closeCachePreserves"; attribute :>> source="thread-exit"; attribute :>> obligation="service-safety"; }
part route29:RouteRow { attribute :>> actionName="clearFastKnown"; attribute :>> lemma="RuntimeTlsReady.clearFastKnownPreserves"; attribute :>> source="fast-slot"; attribute :>> obligation="service-safety"; }
part route30:RouteRow { attribute :>> actionName="clearTlsKnown"; attribute :>> lemma="RuntimeTlsReady.clearTlsKnownPreserves"; attribute :>> source="unix-clear"; attribute :>> obligation="service-safety"; }
part route31:RouteRow { attribute :>> actionName="clearTlsUnknown"; attribute :>> lemma="RuntimeTlsReady.clearTlsUnknownPreserves"; attribute :>> source="unix-clear"; attribute :>> obligation="service-safety"; }
part route32:RouteRow { attribute :>> actionName="freeCacheKnown"; attribute :>> lemma="RuntimeTlsReady.freeCacheKnownPreserves"; attribute :>> source="free-before-clear"; attribute :>> obligation="service-safety"; }
part route33:RouteRow { attribute :>> actionName="attestRosterClosed"; attribute :>> lemma="RuntimeTlsReady.attestRosterClosedPreserves"; attribute :>> source="all-threads"; attribute :>> obligation="service-safety"; }
part route34:RouteRow { attribute :>> actionName="deleteGenericKey"; attribute :>> lemma="RuntimeTlsReady.deleteGenericKeyPreserves"; attribute :>> source="generic-key-delete"; attribute :>> obligation="service-safety"; }
part route35:RouteRow { attribute :>> actionName="deleteAllocKeyKnown"; attribute :>> lemma="RuntimeTlsReady.deleteAllocKeyKnownPreserves"; attribute :>> source="unix-key-delete"; attribute :>> obligation="service-safety"; }
part route36:RouteRow { attribute :>> actionName="deleteAllocKeyUnknown"; attribute :>> lemma="RuntimeTlsReady.deleteAllocKeyUnknownPreserves"; attribute :>> source="unix-key-delete"; attribute :>> obligation="service-safety"; }
part route37:RouteRow { attribute :>> actionName="freeGlobalLocks"; attribute :>> lemma="RuntimeTlsReady.freeGlobalLocksPreserves"; attribute :>> source="allocator-finalize"; attribute :>> obligation="service-safety"; }
part route38:RouteRow { attribute :>> actionName="retireRuntime"; attribute :>> lemma="RuntimeTlsReady.retireRuntimePreserves"; attribute :>> source="allocator-finalize"; attribute :>> obligation="service-safety"; }
part def GainRow { attribute key:String; attribute saved:String; attribute added:String; attribute condition:String; attribute status:String; }
part gain0:GainRow { attribute :>> key="status-unification"; attribute :>> saved="can consolidate4 unchecked Unix allocator-key operation sites with checked native key policy"; attribute :>> added="status-normalized backend, key storage modes and operation/lifetime receipts"; attribute :>> condition="reuse checked policy not blindly malloc-backed helper in bootstrap; current paths retired0"; attribute :>> status="source-bound/conditional"; }
part gain1:GainRow { attribute :>> key="readiness"; attribute :>> saved="one runtime gate replaces using unrelated plain/volatile flags as complete service authority"; attribute :>> added="one release publication and matching cold-entry acquire/lifetime admission"; attribute :>> condition="all native readers migrate; no global atomic required on every object under held owner scope"; attribute :>> status="conditional-model"; }
part gain2:GainRow { attribute :>> key="fast-rebind"; attribute :>> saved="preserve fast TLS benefit while rejecting old cache epoch after thread-only cleanup/rebind"; attribute :>> added="fast-handle clear/epoch metadata and validated current handle refresh"; attribute :>> condition="same-thread raw fast access cannot bypass closing; finite1->2 witness only"; attribute :>> status="conditional-model"; }
part gain3:GainRow { attribute :>> key="late-work"; attribute :>> saved="can avoid early key/cache teardown followed by implicit TSD/cache recreation"; attribute :>> added="phase-limited finalizer permits and derived-work accounting; cannot delete legitimate callback work"; attribute :>> condition="real source repeat cleanup is known; whole callback DAG still incomplete"; attribute :>> status="conditional"; }
part gain4:GainRow { attribute :>> key="retirement"; attribute :>> saved="explicit cache then generic/allocator key and service retirement gates"; attribute :>> added="all-owner roster, unknown-operation custody and provider quiescence"; attribute :>> condition="no native liveness guarantee or measured speedup; source order must actually migrate"; attribute :>> status="unresolved"; }
part def IssuerRow { attribute key:String; attribute source:String; attribute signature:String; attribute gap:String; }
part issuer0:IssuerRow { attribute :>> key="bootstrap-owner"; attribute :>> source="static-bootstrap"; attribute :>> signature="pre-reserved native domain and permitted completed bootstrap services; no self-wait/full Ready escalation"; attribute :>> gap="source init comment notes callbacks, complete callees/recursive paths unqualified"; }
part issuer1:IssuerRow { attribute :>> key="key-owner"; attribute :>> source="unix-key"; attribute :>> signature="observed create/set/delete status tied to key/runtime/thread/cache incarnation"; attribute :>> gap="specialized Unix void return cannot certify success; ignored OS result must change"; }
part issuer2:IssuerRow { attribute :>> key="fast-owner"; attribute :>> source="fast-slot"; attribute :>> signature="same native thread clears/publishes fast handle at exact cache epoch; active scopes drain"; attribute :>> gap="static TLS not externally writable and source fast finalization reset not shown"; }
part issuer3:IssuerRow { attribute :>> key="shutdown-owner"; attribute :>> source="exit-callback"; attribute :>> signature="inherit cleanup capabilities before public close, settle children and all owners before keys/provider die"; attribute :>> gap="all-thread comments/second cleanup pass are not a completion receipt"; }
part issuer4:IssuerRow { attribute :>> key="memory-order-owner"; attribute :>> source="plain-flags"; attribute :>> signature="matching release/acquire edge and stable metadata handle, exact same publication epoch"; attribute :>> gap="volatile or unrelated mutex read cannot manufacture that edge"; }
part def ConsumerRow { attribute key:String; attribute source:String; attribute access:String; attribute lifetime:String; attribute limit:String; }
part consumer0:ConsumerRow { attribute :>> key="generic-vs-allocator"; attribute :>> source="generic-key"; attribute :>> access="two distinct key families and key-storage ownership conventions"; attribute :>> lifetime="generic TSD subsystem versus allocator cache service"; attribute :>> limit="generic checked helpers allocate key wrappers; recursion dependency must be preserved"; }
part consumer1:ConsumerRow { attribute :>> key="unix-allocator"; attribute :>> source="unix-set"; attribute :>> access="unchecked allocator pthread key/create/set/clear/delete sites"; attribute :>> lifetime="live key plus current OS thread and cache epoch"; attribute :>> limit="normal void return and NULL destructor do not supply cleanup receipts"; }
part consumer2:ConsumerRow { attribute :>> key="windows-allocator"; attribute :>> source="windows-status"; attribute :>> access="TlsAlloc/Get/Set/Free checks and panic paths; once flag controls creation"; attribute :>> lifetime="native loader/bootstrap, key and thread state"; attribute :>> limit="not proof of concurrent init, panic unwinding or loaded ABI"; }
part consumer3:ConsumerRow { attribute :>> key="fast-getter"; attribute :>> source="fast-slot"; attribute :>> access="native __thread pointer returned when nonnull in legacy macro"; attribute :>> lifetime="owner scope and matching runtime/cache epoch in replacement"; attribute :>> limit="Tcl_FinalizeThread returning does not retire OS TLS storage"; }
part consumer4:ConsumerRow { attribute :>> key="finalizer"; attribute :>> source="tsd-recreate"; attribute :>> access="exit callbacks and later cleanup can recreate TSD; limited authorized work continues after public close"; attribute :>> lifetime="parent cleanup permit and phase-valid services"; attribute :>> limit="no Tcl_Obj service after its own finalization; no blanket full Ready"; }
part consumer5:ConsumerRow { attribute :>> key="global-retire"; attribute :>> source="all-threads"; attribute :>> access="cache alias drain, complete roster, both key deletions and final provider teardown"; attribute :>> lifetime="stable runtime supervisor until all statuses known"; attribute :>> limit="model1 owner and at most2 cache epochs does not prove unbounded admission/ABA"; }
part def EdgeRow { attribute fromNode:String; attribute toNode:String; attribute contract:String; }
part edge0:EdgeRow { attribute :>> fromNode="Static bootstrap capabilities"; attribute :>> toNode="Native services initialization"; attribute :>> contract="generic TSD and allocator key are separate; keys and lock tables each complete"; }
part edge1:EdgeRow { attribute :>> fromNode="Native services initialization"; attribute :>> toNode="Runtime Ready(epoch)"; attribute :>> contract="one release after complete prerequisites; initialization callbacks get limited capabilities"; }
part edge2:EdgeRow { attribute :>> fromNode="Runtime Ready(epoch)"; attribute :>> toNode="Observe same-epoch Ready"; attribute :>> contract="matching acquire/reads-from and metadata lifetime required"; }
part edge3:EdgeRow { attribute :>> fromNode="Observe same-epoch Ready"; attribute :>> toNode="Known TLS install / cache Ready"; attribute :>> contract="raw Unix void return is not receipt"; }
part edge4:EdgeRow { attribute :>> fromNode="Known TLS install / cache Ready"; attribute :>> toNode="Fast handle(cache epoch)"; attribute :>> contract="owner scope can cache handle without global per-object pin"; }
part edge5:EdgeRow { attribute :>> fromNode="Fast handle(cache epoch)"; attribute :>> toNode="Thread close / clear / free"; attribute :>> contract="same-thread fast and platform aliases settled before managed free"; }
part edge6:EdgeRow { attribute :>> fromNode="Thread close / clear / free"; attribute :>> toNode="Rebind fresh cache epoch"; attribute :>> contract="global services/key stay alive; old request epoch rejected"; }
part edge7:EdgeRow { attribute :>> fromNode="Runtime Ready(epoch)"; attribute :>> toNode="Public close and cleanup permits"; attribute :>> contract="existing scopes drain; only phase-authorized inherited cleanup continues"; }
part edge8:EdgeRow { attribute :>> fromNode="Public close and cleanup permits"; attribute :>> toNode="Late TSD work drained"; attribute :>> contract="no producer resurrection after parent finish"; }
part edge9:EdgeRow { attribute :>> fromNode="Late TSD work drained"; attribute :>> toNode="All-owner completion"; attribute :>> contract="real cohort closure not comment or pointer test"; }
part edge10:EdgeRow { attribute :>> fromNode="All-owner completion"; attribute :>> toNode="Delete both key families"; attribute :>> contract="checked exact statuses; unknown deletion blocks provider retirement"; }
part edge11:EdgeRow { attribute :>> fromNode="Delete both key families"; attribute :>> toNode="Retire locks/tables/runtime"; attribute :>> contract="no client, finalizer, cache or key still borrows provider"; }
part def RefinementRow { attribute key:String; attribute lemma:String; attribute source:String; attribute premise:String; }
part refinement0:RefinementRow { attribute :>> key="global-ready"; attribute :>> lemma="RuntimeTlsReady.runtimeReadyHasServices"; attribute :>> source="global-init"; attribute :>> premise="native service subset only, not complete Tcl object/IO/language readiness"; }
part refinement1:RefinementRow { attribute :>> key="cache-protects-key"; attribute :>> lemma="RuntimeTlsReady.cacheRetainsServices"; attribute :>> source="unix-clear"; attribute :>> premise="pending/Ready/closing cache retains both key families and allocator tables"; }
part refinement2:RefinementRow { attribute :>> key="unknown-owner"; attribute :>> lemma="RuntimeTlsReady.unknownInstallRetainsOwner"; attribute :>> source="unix-set"; attribute :>> premise="unknown set/clear keeps native owner duty; no assumption of physical value"; }
part refinement3:RefinementRow { attribute :>> key="no-free-alias"; attribute :>> lemma="RuntimeTlsReady.freeHasNoAliases"; attribute :>> source="free-before-clear"; attribute :>> premise="managed order intentionally stronger than legacy free-before-clear"; }
part refinement4:RefinementRow { attribute :>> key="late-parent"; attribute :>> lemma="RuntimeTlsReady.lateWorkRetainsParent"; attribute :>> source="tsd-recreate"; attribute :>> premise="one modeled derived-work credit; full producer closure is external"; }
part refinement5:RefinementRow { attribute :>> key="ready-order"; attribute :>> lemma="RuntimeTlsReady.readyHappensBefore"; attribute :>> source="plain-flags"; attribute :>> premise="given matching release/acquire edge plus initialization/read program order; not inferred from volatile"; }
part refinement6:RefinementRow { attribute :>> key="retire"; attribute :>> lemma="RuntimeTlsReady.retiredHasNoServices"; attribute :>> source="all-threads"; attribute :>> premise="one-owner cohort witness, checked key delete and provider drain"; }
part refinement7:RefinementRow { attribute :>> key="parent-install"; attribute :>> lemma="RuntimeTlsReady.guardedPriorInstall"; attribute :>> source="prior"; attribute :>> premise="explicit install-receipt mirror into actual prior Guard/Step; full product not proved"; }
part def WriterRow { attribute key:String; attribute source:String; attribute access:String; attribute closure:String; attribute limit:String; }
part writer0:WriterRow { attribute :>> key="global-flags"; attribute :>> source="global-init"; attribute :>> access="subsystemsInitialized, listLockPtr and allocator table fields are different publication families"; attribute :>> closure="captured ordered stores"; attribute :>> limit="complete callers/launch serialization not proved"; }
part writer1:WriterRow { attribute :>> key="posix-status"; attribute :>> source="unix-key"; attribute :>> access="4 unchecked specialized pthread key create/set/clear/delete results"; attribute :>> closure="captured provider bodies"; attribute :>> limit="checked generic TLS helper semantics cannot be silently substituted"; }
part writer2:WriterRow { attribute :>> key="windows-status"; attribute :>> source="windows-status"; attribute :>> access="checked TlsSetValue/Free/Get/Alloc, panic exits and once flags"; attribute :>> closure="captured provider bodies"; attribute :>> limit="native error/panic/SEH and init concurrency unresolved"; }
part writer3:WriterRow { attribute :>> key="fast-tls"; attribute :>> source="fast-slot"; attribute :>> access="tcachePtr assignment in GETCACHE; no source reset in captured finalizers"; attribute :>> closure="captured macro and call chain"; attribute :>> limit="legal post-finalize reentry and all raw readers need qualification"; }
part writer4:WriterRow { attribute :>> key="exit-callbacks"; attribute :>> source="exit-callback"; attribute :>> access="handlers popped then called; cleanup afterwards and repeated TSD finalization"; attribute :>> closure="captured event/thread/TSD functions"; attribute :>> limit="all callback implementations and inherited task production unresolved"; }
part writer5:WriterRow { attribute :>> key="provider-free"; attribute :>> source="allocator-finalize"; attribute :>> access="legacy synchronization/key/cache/provider destruction order"; attribute :>> closure="captured direct calls"; attribute :>> limit="actual all-native-thread roster and every unknown operation not yet closed"; }
}
