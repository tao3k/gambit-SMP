package GambitSavedResultRetirement { private import ScalarValues::*;
part def SourceRow { attribute key:String; attribute path:String; attribute needle:String; attribute limit:String; }
part source0:SourceRow { attribute :>> key="legacy-layout"; attribute :>> path="evidence/research/source-references/tcl/cbf86d62348d6b052e1961b4df995960fb21545f/generic/tcl.h"; attribute :>> needle="typedef struct Tcl_SavedResult"; attribute :>> limit="typically stack allocated; raw fields are not an owner registry"; }
part source1:SourceRow { attribute :>> key="save"; attribute :>> path="evidence/research/source-references/tcl/cbf86d62348d6b052e1961b4df995960fb21545f/generic/tclResult.c"; attribute :>> needle="statePtr->freeProc = iPtr->freeProc;"; attribute :>> limit="legacy token moves native string/free hook out of interpreter"; }
part source2:SourceRow { attribute :>> key="restore"; attribute :>> path="evidence/research/source-references/tcl/cbf86d62348d6b052e1961b4df995960fb21545f/generic/tclResult.c"; attribute :>> needle="Tcl_ResetResult(interp);"; attribute :>> limit="legacy restore disposes current result BEFORE snapshot install"; }
part source3:SourceRow { attribute :>> key="discard"; attribute :>> path="evidence/research/source-references/tcl/cbf86d62348d6b052e1961b4df995960fb21545f/generic/tclResult.c"; attribute :>> needle="statePtr->freeProc(statePtr->result);"; attribute :>> limit="no interpreter argument; no settled-token bit after disposal"; }
part source4:SourceRow { attribute :>> key="set-result"; attribute :>> path="evidence/research/source-references/tcl/cbf86d62348d6b052e1961b4df995960fb21545f/generic/tclResult.c"; attribute :>> needle="oldFreeProc(oldResult);"; attribute :>> limit="SetResult publishes new result before old free hook callout"; }
part source5:SourceRow { attribute :>> key="modern-save"; attribute :>> path="evidence/research/source-references/tcl/cbf86d62348d6b052e1961b4df995960fb21545f/generic/tclResult.c"; attribute :>> needle="statePtr->objResult = Tcl_GetObjResult(interp);"; attribute :>> limit="modern opaque snapshot retains object state; can first dispose native string"; }
part source6:SourceRow { attribute :>> key="modern-restore"; attribute :>> path="evidence/research/source-references/tcl/cbf86d62348d6b052e1961b4df995960fb21545f/generic/tclResult.c"; attribute :>> needle="Tcl_SetObjResult(interp, statePtr->objResult);"; attribute :>> limit="object restore then discard state; arbitrary release callouts remain"; }
part source7:SourceRow { attribute :>> key="trace-holder"; attribute :>> path="evidence/research/source-references/tcl/cbf86d62348d6b052e1961b4df995960fb21545f/generic/tclBasic.c"; attribute :>> needle="state = Tcl_SaveInterpState((Tcl_Interp *) iPtr, TCL_OK);"; attribute :>> limit="local trace state spans user trace callback"; }
part source8:SourceRow { attribute :>> key="rewind-holder"; attribute :>> path="evidence/research/source-references/tcl/cbf86d62348d6b052e1961b4df995960fb21545f/generic/tclBasic.c"; attribute :>> needle="TclNRAddCallback(interp, RewindCoroutineCallback, state,"; attribute :>> limit="heap NR callback data[0] owns state until restore callback"; }
part source9:SourceRow { attribute :>> key="expr-holder"; attribute :>> path="evidence/research/source-references/tcl/cbf86d62348d6b052e1961b4df995960fb21545f/generic/tclExecute.c"; attribute :>> needle="Tcl_NRAddCallback(interp, ExprObjCallback, state, resultPtr,"; attribute :>> limit="NR callback data[0] branches Restore/Discard on result"; }
part source10:SourceRow { attribute :>> key="background-holder"; attribute :>> path="evidence/research/source-references/tcl/cbf86d62348d6b052e1961b4df995960fb21545f/generic/tclEvent.c"; attribute :>> needle="saved = Tcl_SaveInterpState(interp, code);"; attribute :>> limit="saved local spans bgerror evaluation and branch-dependent restore/discard"; }
part source11:SourceRow { attribute :>> key="legacy-abi"; attribute :>> path="evidence/research/source-references/tcl/cbf86d62348d6b052e1961b4df995960fb21545f/generic/tclDecls.h"; attribute :>> needle="Tcl_DiscardResult(Tcl_SavedResult *statePtr);"; attribute :>> limit="public and stubs entry; no actual legacy caller found in captured subset"; }
part source12:SourceRow { attribute :>> key="parent-model"; attribute :>> path="dev/refactoring/modern-c/models/quint/callback_producer.qnt"; attribute :>> needle="action retireDomain="; attribute :>> limit="actual preceding result/producer gate; new proof joins only at settled exit"; }
part source13:SourceRow { attribute :>> key="marker"; attribute :>> path="vendor/gambit/lib/c_intf.c"; attribute :>> needle="___still_obj_refcount_dec (marker);"; attribute :>> limit="irreversible cleanup does not become idempotent by deleting completion record"; }
part def ObligationRow { attribute key:String; attribute status:String; attribute condition:String; }
part obligation0:ObligationRow { attribute :>> key="custody-safety"; attribute :>> status="conditional-model"; attribute :>> condition="A held through B disposal; C cannot be overwritten without settlement; record readers/issuers drain"; }
part obligation1:ObligationRow { attribute :>> key="captured-holders"; attribute :>> status="source-bound"; attribute :>> condition="real modern local/NR callback state holders; legacy definitions/API only in captured subset"; }
part obligation2:ObligationRow { attribute :>> key="legacy-holder-closure"; attribute :>> status="unresolved"; attribute :>> condition="all external legacy snapshot callers, struct aliases and abandonment paths enumerated"; }
part obligation3:ObligationRow { attribute :>> key="reentrant-adapter"; attribute :>> status="unresolved"; attribute :>> condition="intercept raw result writes/free hooks or reject unsupported reentry; protected C is not current Tcl semantics proof"; }
part obligation4:ObligationRow { attribute :>> key="record-retirement"; attribute :>> status="unresolved"; attribute :>> condition="stable lookup anchor, closed ACK producers, drained observers and no raw TicketId pointer escape"; }
part obligation5:ObligationRow { attribute :>> key="native-completion"; attribute :>> status="unresolved"; attribute :>> condition="same-operation cleanup/free receipt; unknown cannot retry"; }
part obligation6:ObligationRow { attribute :>> key="c23-refinement"; attribute :>> status="unresolved"; attribute :>> condition="owner thread, loaded Tcl ABI, release/acquire and generation no-wrap"; }
part def RouteRow { attribute actionName:String; attribute lemma:String; attribute source:String; attribute obligation:String; }
part route0:RouteRow { attribute :>> actionName="saveA"; attribute :>> lemma="SavedResultRetirement.saveAPreserves"; attribute :>> source="set-result"; attribute :>> obligation="custody-safety"; }
part route1:RouteRow { attribute :>> actionName="installB"; attribute :>> lemma="SavedResultRetirement.installBPreserves"; attribute :>> source="set-result"; attribute :>> obligation="custody-safety"; }
part route2:RouteRow { attribute :>> actionName="beginRestore"; attribute :>> lemma="SavedResultRetirement.beginRestorePreserves"; attribute :>> source="restore"; attribute :>> obligation="custody-safety"; }
part route3:RouteRow { attribute :>> actionName="reenterPublishC"; attribute :>> lemma="SavedResultRetirement.reenterPublishCPreserves"; attribute :>> source="set-result"; attribute :>> obligation="custody-safety"; }
part route4:RouteRow { attribute :>> actionName="loseB"; attribute :>> lemma="SavedResultRetirement.loseBPreserves"; attribute :>> source="set-result"; attribute :>> obligation="custody-safety"; }
part route5:RouteRow { attribute :>> actionName="ackB"; attribute :>> lemma="SavedResultRetirement.ackBPreserves"; attribute :>> source="set-result"; attribute :>> obligation="custody-safety"; }
part route6:RouteRow { attribute :>> actionName="beginCRelease"; attribute :>> lemma="SavedResultRetirement.beginCReleasePreserves"; attribute :>> source="set-result"; attribute :>> obligation="custody-safety"; }
part route7:RouteRow { attribute :>> actionName="loseC"; attribute :>> lemma="SavedResultRetirement.loseCPreserves"; attribute :>> source="set-result"; attribute :>> obligation="custody-safety"; }
part route8:RouteRow { attribute :>> actionName="ackC"; attribute :>> lemma="SavedResultRetirement.ackCPreserves"; attribute :>> source="set-result"; attribute :>> obligation="custody-safety"; }
part route9:RouteRow { attribute :>> actionName="commitRestore"; attribute :>> lemma="SavedResultRetirement.commitRestorePreserves"; attribute :>> source="restore"; attribute :>> obligation="custody-safety"; }
part route10:RouteRow { attribute :>> actionName="beginDiscard"; attribute :>> lemma="SavedResultRetirement.beginDiscardPreserves"; attribute :>> source="discard"; attribute :>> obligation="custody-safety"; }
part route11:RouteRow { attribute :>> actionName="beginRestoredRelease"; attribute :>> lemma="SavedResultRetirement.beginRestoredReleasePreserves"; attribute :>> source="set-result"; attribute :>> obligation="custody-safety"; }
part route12:RouteRow { attribute :>> actionName="loseA"; attribute :>> lemma="SavedResultRetirement.loseAPreserves"; attribute :>> source="discard"; attribute :>> obligation="custody-safety"; }
part route13:RouteRow { attribute :>> actionName="ackA"; attribute :>> lemma="SavedResultRetirement.ackAPreserves"; attribute :>> source="discard"; attribute :>> obligation="custody-safety"; }
part route14:RouteRow { attribute :>> actionName="completeFirst"; attribute :>> lemma="SavedResultRetirement.completeFirstPreserves"; attribute :>> source="parent-model"; attribute :>> obligation="custody-safety"; }
part route15:RouteRow { attribute :>> actionName="completeSecond"; attribute :>> lemma="SavedResultRetirement.completeSecondPreserves"; attribute :>> source="parent-model"; attribute :>> obligation="custody-safety"; }
part route16:RouteRow { attribute :>> actionName="lookupRecord"; attribute :>> lemma="SavedResultRetirement.lookupRecordPreserves"; attribute :>> source="parent-model"; attribute :>> obligation="custody-safety"; }
part route17:RouteRow { attribute :>> actionName="returnRecord"; attribute :>> lemma="SavedResultRetirement.returnRecordPreserves"; attribute :>> source="parent-model"; attribute :>> obligation="custody-safety"; }
part route18:RouteRow { attribute :>> actionName="closeObserverGate"; attribute :>> lemma="SavedResultRetirement.closeObserverGatePreserves"; attribute :>> source="parent-model"; attribute :>> obligation="custody-safety"; }
part route19:RouteRow { attribute :>> actionName="closeIssuer"; attribute :>> lemma="SavedResultRetirement.closeIssuerPreserves"; attribute :>> source="parent-model"; attribute :>> obligation="custody-safety"; }
part route20:RouteRow { attribute :>> actionName="retireRecord"; attribute :>> lemma="SavedResultRetirement.retireRecordPreserves"; attribute :>> source="parent-model"; attribute :>> obligation="custody-safety"; }
part route21:RouteRow { attribute :>> actionName="reuseSlot"; attribute :>> lemma="SavedResultRetirement.reuseSlotPreserves"; attribute :>> source="parent-model"; attribute :>> obligation="custody-safety"; }
part def GainRow { attribute key:String; attribute saved:String; attribute added:String; attribute condition:String; attribute status:String; }
part gain0:GainRow { attribute :>> key="real-holder-classification"; attribute :>> saved="avoid treating all snapshots as native string/freeProc owners"; attribute :>> added="modern object state and legacy moved string tracked separately"; attribute :>> condition="native string conversion may free before modern save returns"; attribute :>> status="source-bound"; }
part gain1:GainRow { attribute :>> key="restore-escrow"; attribute :>> saved="0 admitted loss of saved A or overwrite of protected C while B release unknown"; attribute :>> added="simultaneous A/B/C custody and callout record"; attribute :>> condition="managed result interception or explicit refusal; raw Tcl not proven equivalent"; attribute :>> status="conditional-model"; }
part gain2:GainRow { attribute :>> key="completed-records"; attribute :>> saved="O(L) completed records after proven closed issuer/readers instead of keeping all history forever"; attribute :>> added="stable generation anchor plus retained records for live producers/readers/result debt"; attribute :>> condition="L counts all not-yet-qualified identities; can remain unbounded without closure"; attribute :>> status="conditional"; }
part gain3:GainRow { attribute :>> key="unknown-disposal"; attribute :>> saved="0 admitted blind retries or record retirement based solely on done"; attribute :>> added="opaque OperationId/result/provider holds retained indefinitely if needed"; attribute :>> condition="known backend receipt and remaining payload roots are separate"; attribute :>> status="conditional-model"; }
part gain4:GainRow { attribute :>> key="runtime-retirement"; attribute :>> saved="0 current runtime paths retired; no measured speedup"; attribute :>> added="snapshot adapters, observer/issuer lifecycle and native receipts"; attribute :>> condition="all native refinement gaps must close"; attribute :>> status="design-only"; }
part def IssuerRow { attribute key:String; attribute source:String; attribute signature:String; attribute gap:String; }
part issuer0:IssuerRow { attribute :>> key="snapshot-owner"; attribute :>> source="save"; attribute :>> signature="exclusive saved token and result identity across Restore/Discard"; attribute :>> gap="legacy struct can escape; no complete holder census"; }
part issuer1:IssuerRow { attribute :>> key="native-callback-owner"; attribute :>> source="rewind-holder"; attribute :>> signature="NR callback data[0] or local trace owner keeps modern state until normal endpoint"; attribute :>> gap="callback deletion/abandonment and whole coroutine product unresolved"; }
part issuer2:IssuerRow { attribute :>> key="result-owner"; attribute :>> source="restore"; attribute :>> signature="A snapshot escrow + B disposal identity + protected C owner"; attribute :>> gap="not implemented by raw Tcl_SetResult/ResetResult fields"; }
part issuer3:IssuerRow { attribute :>> key="completion-registry"; attribute :>> source="parent-model"; attribute :>> signature="settled InvocationId then close ACK producers and observer gate; drain prior readers"; attribute :>> gap="guard counts alone do not prove old raw aliases disappeared"; }
part issuer4:IssuerRow { attribute :>> key="generation-owner"; attribute :>> source="legacy-abi"; attribute :>> signature="stable lookup authority rejects old generation before accessing reused record"; attribute :>> gap="no safe first load from already reclaimed record; wrap/anchor retirement unresolved"; }
part def ConsumerRow { attribute key:String; attribute source:String; attribute access:String; attribute lifetime:String; attribute limit:String; }
part consumer0:ConsumerRow { attribute :>> key="legacy-token"; attribute :>> source="legacy-layout"; attribute :>> access="caller-supplied typically stack struct"; attribute :>> lifetime="caller must consume once via Restore or Discard"; attribute :>> limit="no actual caller in partial local capture; external/public ABI remains"; }
part consumer1:ConsumerRow { attribute :>> key="command-trace"; attribute :>> source="trace-holder"; attribute :>> access="local state spans traceProc then Restore before Tcl_Release"; attribute :>> lifetime="normal trace dynamic scope"; attribute :>> limit="foreign escape can bypass endpoint"; }
part consumer2:ConsumerRow { attribute :>> key="coroutine-rewind"; attribute :>> source="rewind-holder"; attribute :>> access="state copied into NR callback data[0], restored by RewindCoroutineCallback"; attribute :>> lifetime="NR callback lifetime, not just C stack"; attribute :>> limit="full deletion/rewind callback closure unresolved"; }
part consumer3:ConsumerRow { attribute :>> key="expression-NR"; attribute :>> source="expr-holder"; attribute :>> access="state in ExprObjCallback data[0]; success Restore, error Discard"; attribute :>> lifetime="callback until selected endpoint"; attribute :>> limit="not proof every callback completes under all exits"; }
part consumer4:ConsumerRow { attribute :>> key="background-error"; attribute :>> source="background-holder"; attribute :>> access="saved spans bgerror and fallback/output branches"; attribute :>> lifetime="selected Restore or Discard branch"; attribute :>> limit="selected captured source only, not all Tcl state owners"; }
part consumer5:ConsumerRow { attribute :>> key="legacy-restore"; attribute :>> source="restore"; attribute :>> access="Reset current result -> install saved freeProc/string -> replace object"; attribute :>> lifetime="A stays owned while B callout may run"; attribute :>> limit="raw reentrant mutation can invalidate ordering; requires admission"; }
part consumer6:ConsumerRow { attribute :>> key="legacy-discard"; attribute :>> source="discard"; attribute :>> access="object decrement then saved custom hook"; attribute :>> lifetime="caller token + native operation until authoritative completion"; attribute :>> limit="no automatic token invalidation or retry safety"; }
part def EdgeRow { attribute fromNode:String; attribute toNode:String; attribute contract:String; }
part edge0:EdgeRow { attribute :>> fromNode="Saved A"; attribute :>> toNode="Restore escrow"; attribute :>> contract="retain A while old-current B disposes"; }
part edge1:EdgeRow { attribute :>> fromNode="Old current B"; attribute :>> toNode="Reentrant new C"; attribute :>> contract="protected publication requires managed adapter; not raw equivalence"; }
part edge2:EdgeRow { attribute :>> fromNode="Restore escrow"; attribute :>> toNode="Interpreter A"; attribute :>> contract="commit only after known B and C settlement"; }
part edge3:EdgeRow { attribute :>> fromNode="Saved A"; attribute :>> toNode="Discard unknown"; attribute :>> contract="retain opaque operation and provider; do not retry hook"; }
part edge4:EdgeRow { attribute :>> fromNode="Invocation done"; attribute :>> toNode="Completion record retained"; attribute :>> contract="saved results, ACK producers and observers can still refer"; }
part edge5:EdgeRow { attribute :>> fromNode="Closed issuer and observer gate"; attribute :>> toNode="Prior reader drain"; attribute :>> contract="close is not a grace period"; }
part edge6:EdgeRow { attribute :>> fromNode="Prior reader drain"; attribute :>> toNode="Record retirement"; attribute :>> contract="result closure and completion evidence also required"; }
part edge7:EdgeRow { attribute :>> fromNode="Record retirement"; attribute :>> toNode="Generation slot reuse"; attribute :>> contract="stable anchor rejects old ACK before record access"; }
part source14:SourceRow { attribute :>> key="subst-holder"; attribute :>> path="evidence/research/source-references/tcl/cbf86d62348d6b052e1961b4df995960fb21545f/generic/tclCompCmdsSZ.c"; attribute :>> needle="TclSubstParse(interp, bytes, numBytes, flags, &parse, &state);"; attribute :>> limit="indirect state producer through out parameter; TclSubstParse definition not in captured subset"; }
part consumer7:ConsumerRow { attribute :>> key="subst-compiler"; attribute :>> source="subst-holder"; attribute :>> access="state out parameter then conditional Restore before syntax error emission"; attribute :>> lifetime="compiler local token across bytecode emission"; attribute :>> limit="producer implementation absent from captured files; alias closure remains unresolved"; }
}
