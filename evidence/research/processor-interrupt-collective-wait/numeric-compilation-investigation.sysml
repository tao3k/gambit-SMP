/* Current repair dossier. Method vocabulary is imported; no satisfaction claimed. */
package CurrentNumericCompilationInvestigation {
    private import GambitResearch::*;
    part numericCompilation : RepairInvestigation {
        attribute :>> investigationId = "NUMERIC-COMPILATION-MECHANISM";
        attribute :>> gateDefinition = "docs/current-repair-obligation-map.md";
        attribute :>> failureEvidence = "evidence/research/processor-interrupt-collective-wait/current-checkpoint-qualification-review.md";
        attribute :>> sourceMechanism = "src/gambit_smp/compiler_phase_primitives.py";
        attribute :>> competingHypotheses = "Actual points-to expansion; shared dispatcher and external-tail-call CFG/SSA representation; optimization configuration and later-pass cost; observer/resource interference. Structural concentration is observed, causal runtime attribution remains open";
        attribute :>> distinguishingObservation = "Original main has 101223 CFG blocks. Comparator-call candidate halves static eqv call sites but owned cc1 remains in parsing then gimplification and times out. True global grouping preserves all 1592 original forms in order with exception/definition barriers, yielding 7943 main CFG blocks; local outlining failed to create host boundaries. Detailed dumps time out with fflush-dominated own stacks; identical grouped input.i without tree dumps compiles at O1 under the unchanged 60-second cap. GCC wall report: tree PTA 1.06 seconds out of 45.05, not a measurement of original unresolved alias cost";
        attribute :>> sourceRefinementRequired = "Retained source driver creates 79 private global groups of at most 32 eligible assertions. Independent original reader verifies ordered coverage; unchanged interpreted reference and real compiled module execution both pass. Thirty-two closed ealias function solutions have maximum observed named set size four; remaining functions and later alias dump are unobserved, not empty. Full-tree output is an intrusive observer, not a production recipe default";
        attribute :>> acceptanceBoundary = "Diagnostic discrimination does not close full GC/FFI, lifecycle, Gerbil or release gates; original budgets and failed receipts retained";
        attribute :>> quintSource = "models/gambit/native_compiler_probe_correspondence.qnt";
        attribute :>> quintSymbol = "orderedFormPartition";
        attribute :>> leanSource = "models/gambit/lean/NumericCompilerExperiment.lean";
        attribute :>> leanSymbol = "partitionPreservesFormMembership";
        attribute :>> disposition = "original-C-SHA-preserved; global-group-source-refinement-executed; O1-module-and-original-numeric-assertions-pass; partial-ealias-observed; full-native-and-Gerbil-gates-open";
    }
}
