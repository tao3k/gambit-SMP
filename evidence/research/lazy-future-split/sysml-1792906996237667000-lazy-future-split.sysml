package GambitLazyFutureSplit { private import ScalarValues::*;
part def SourceRow { attribute key:String; attribute path:String; attribute needle:String; attribute obligation:String; }
part source0:SourceRow { attribute :>> key="feeley-paper"; attribute :>> path="evidence/research/source-references/feeley-pvm/ad1f9ca247f0c97835bda99bd387ca735767ab68ed4338897ade618ad769d2f1.txt"; attribute :>> needle="2.7 Parallelism in PVM"; attribute :>> obligation="paper TASK/WORK/DONE and lazy materialization, not current runtime proof"; }
part source1:SourceRow { attribute :>> key="paper-target"; attribute :>> path="evidence/research/source-references/feeley-pvm/ad1f9ca247f0c97835bda99bd387ca735767ab68ed4338897ade618ad769d2f1.txt"; attribute :>> needle="bidirectional communication"; attribute :>> obligation="semantic/compiler target feedback remains useful"; }
part source2:SourceRow { attribute :>> key="native-extent"; attribute :>> path="evidence/research/source-references/feeley-sfp/8bb2fae8ae4b54d3a86206596f90e9cf73da39846af0f39244a476074cf81ed4.txt"; attribute :>> needle="5       Pra"; attribute :>> obligation="historical native-stack proposal not an implemented source-split service"; }
part source3:SourceRow { attribute :>> key="future-parse"; attribute :>> path="vendor/gambit/gsc/_ptree1.scm"; attribute :>> needle="(define (pt-future source env use)"; attribute :>> obligation="future form produces a distinct parse-tree node"; }
part source4:SourceRow { attribute :>> key="future-tree"; attribute :>> path="vendor/gambit/gsc/_ptreeadt.scm"; attribute :>> needle="(define (make-fut"; attribute :>> obligation="future is not an ordinary opaque function call in this frontend"; }
part source5:SourceRow { attribute :>> key="future-dispatch"; attribute :>> path="vendor/gambit/gsc/_front.scm"; attribute :>> needle="((fut? node)"; attribute :>> obligation="semantic generator selects gen-fut"; }
part source6:SourceRow { attribute :>> key="future-generator"; attribute :>> path="vendor/gambit/gsc/_front.scm"; attribute :>> needle="(define (gen-fut node live reason)"; attribute :>> obligation="real compile-time future source producer"; }
part source7:SourceRow { attribute :>> key="future-save"; attribute :>> path="vendor/gambit/gsc/_front.scm"; attribute :>> needle="(save-regs-to-stk (live-regs live-after)"; attribute :>> obligation="save parent live registers before future"; }
part source8:SourceRow { attribute :>> key="future-cut"; attribute :>> path="vendor/gambit/gsc/_front.scm"; attribute :>> needle="1) ;; reserve space for a break frame"; attribute :>> obligation="frame alignment and break reservation precede task/return contexts"; }
part source9:SourceRow { attribute :>> key="task-context"; attribute :>> path="vendor/gambit/gsc/_front.scm"; attribute :>> needle="(make-context (- nb-slots frame-start)"; attribute :>> obligation="child task context and parent return context are already distinguished"; }
part source10:SourceRow { attribute :>> key="future-return"; attribute :>> path="vendor/gambit/gsc/_front.scm"; attribute :>> needle="(make-label-task-return"; attribute :>> obligation="result lives in proc-result before task-return label"; }
part source11:SourceRow { attribute :>> key="gvm-frame"; attribute :>> path="vendor/gambit/gsc/_gvm.scm"; attribute :>> needle="(define (make-frame size slots regs closed live)"; attribute :>> obligation="logical frame includes slots, registers, closed variables and liveness"; }
part source12:SourceRow { attribute :>> key="gvm-task-entry"; attribute :>> path="vendor/gambit/gsc/_gvm.scm"; attribute :>> needle="(define (make-label-task-entry"; attribute :>> obligation="task entry survives GVM representation"; }
part source13:SourceRow { attribute :>> key="gvm-task-return"; attribute :>> path="vendor/gambit/gsc/_gvm.scm"; attribute :>> needle="(define (make-label-task-return"; attribute :>> obligation="task return survives GVM representation"; }
part source14:SourceRow { attribute :>> key="emit-entry"; attribute :>> path="vendor/gambit/gsc/_t-c-2.scm"; attribute :>> needle="(targ-emit (list \"TASK_PUSH\" 0))"; attribute :>> obligation="C emitter emits task hook"; }
part source15:SourceRow { attribute :>> key="emit-return"; attribute :>> path="vendor/gambit/gsc/_t-c-2.scm"; attribute :>> needle="(targ-emit (list \"TASK_POP\""; attribute :>> obligation="C emitter emits task completion hook"; }
part source16:SourceRow { attribute :>> key="emit-live-map"; attribute :>> path="vendor/gambit/gsc/_t-c-2.scm"; attribute :>> needle="(targ-build-gc-map"; attribute :>> obligation="native return metadata derives from semantic liveness"; }
part source17:SourceRow { attribute :>> key="emit-task-spec"; attribute :>> path="vendor/gambit/gsc/_t-c-2.scm"; attribute :>> needle="(targ-make-frame-spec 'task fs link gc-map)"; attribute :>> obligation="task FrameSpec exists in current working tree; not split ownership metadata"; }
part source18:SourceRow { attribute :>> key="physical-frame"; attribute :>> path="vendor/gambit/gsc/_t-c-3.scm"; attribute :>> needle="(define (targ-make-frame-spec kind fs link gc-map)"; attribute :>> obligation="current physical validation does not establish parent/child ownership or sealing aliases"; }
part source19:SourceRow { attribute :>> key="task-push-empty"; attribute :>> path="vendor/gambit/include/_gambit/module_generation.h.in"; attribute :>> needle="#define ___TASK_PUSH(i)"; attribute :>> obligation="empty source macro; no runtime split logic here"; }
part source20:SourceRow { attribute :>> key="task-pop-empty"; attribute :>> path="vendor/gambit/include/_gambit/module_generation.h.in"; attribute :>> needle="#define ___TASK_POP(n)"; attribute :>> obligation="empty source macro; no placeholder/result handoff here"; }
part source21:SourceRow { attribute :>> key="frame-decode"; attribute :>> path="vendor/gambit/include/_gambit/module_generation.h.in"; attribute :>> needle="___FRAME_INLINE ___frame_descriptor ___decode_frame_descriptor"; attribute :>> obligation="inline/out-of-line and internal-return coordinates can be reused"; }
part source22:SourceRow { attribute :>> key="root-cursor"; attribute :>> path="vendor/gambit/include/_gambit/module_generation.h.in"; attribute :>> needle="Borrowed, nonallocating scan state."; attribute :>> obligation="cursor may not cross safepoints or descriptor lifetime"; }
part source23:SourceRow { attribute :>> key="force-hook"; attribute :>> path="vendor/gambit/include/_gambit/module_generation.h.in"; attribute :>> needle="#define ___FORCE1(n,src)"; attribute :>> obligation="promise forcing is not a proved cross-task future protocol"; }
part source24:SourceRow { attribute :>> key="capture-macro"; attribute :>> path="vendor/gambit/include/_gambit/gvm_operations.h.in"; attribute :>> needle="#define ___CONTINUATION_CAPTURE"; attribute :>> obligation="capture records frame and dynamic environment; source storage can remain stack-backed"; }
part source25:SourceRow { attribute :>> key="graft-macro"; attribute :>> path="vendor/gambit/include/_gambit/gvm_operations.h.in"; attribute :>> needle="#define ___CONTINUATION_GRAFT_NO_WINDING"; attribute :>> obligation="restores frame/denv/cache; not a task publication or exclusive run receipt"; }
part source26:SourceRow { attribute :>> key="live-context-roots"; attribute :>> path="vendor/gambit/lib/_mem/root-origins.inc"; attribute :>> needle="mark_array (work, context->saved"; attribute :>> obligation="running register/saved roots are already enumerated"; }
part source27:SourceRow { attribute :>> key="context-stack"; attribute :>> path="vendor/gambit/lib/_mem/root-origins.inc"; attribute :>> needle="mark_continuation (work, context);"; attribute :>> obligation="context stack and RC sources belong to a concrete root origin"; }
part source28:SourceRow { attribute :>> key="captured-copy"; attribute :>> path="vendor/gambit/lib/_mem/continuation-roots.inc"; attribute :>> needle="grant = reserve_copy(work,alloc,words,0);"; attribute :>> obligation="copying captured frames is GC work, not a scheduler steal transaction"; }
part source29:SourceRow { attribute :>> key="captured-link"; attribute :>> path="vendor/gambit/lib/_mem/continuation-roots.inc"; attribute :>> needle="/* leave a forwarding pointer */"; attribute :>> obligation="forwarding and structural link rewrites must be reconciled with split reader authority"; }
part source30:SourceRow { attribute :>> key="captured-publish"; attribute :>> path="vendor/gambit/lib/_mem/continuation-roots.inc"; attribute :>> needle="publish_object_scan (work, copy_header);"; attribute :>> obligation="existing copy/scan publication is not reused without its own qualification"; }
part source31:SourceRow { attribute :>> key="frame-scan"; attribute :>> path="vendor/gambit/lib/_mem/continuation-roots.inc"; attribute :>> needle="___frame_ordinary_root_begin (frame)"; attribute :>> obligation="ordinary roots and structural link are distinct coordinates"; }
part source32:SourceRow { attribute :>> key="heap-frame-scan"; attribute :>> path="vendor/gambit/lib/_mem/object-scanning.inc"; attribute :>> needle="case ___sFRAME:"; attribute :>> obligation="heap frame consumer validates descriptor/payload size and traverses link"; }
part source33:SourceRow { attribute :>> key="steal-queued"; attribute :>> path="vendor/gambit/lib/_thread.scm"; attribute :>> needle="There are no runnable threads locally, so try to steal"; attribute :>> obligation="current steal path chooses existing runnable threads"; }
part source34:SourceRow { attribute :>> key="steal-pin"; attribute :>> path="vendor/gambit/lib/_thread.scm"; attribute :>> needle="(macro-thread-pinned stolen-thread)"; attribute :>> obligation="native/explicit pin prevents that thread migration"; }
part source35:SourceRow { attribute :>> key="steal-remove"; attribute :>> path="vendor/gambit/lib/_thread.scm"; attribute :>> needle="(##btq-remove! stolen-thread)"; attribute :>> obligation="runnable-thread queue ownership change precedes restore"; }
part source36:SourceRow { attribute :>> key="steal-restore"; attribute :>> path="vendor/gambit/lib/_thread.scm"; attribute :>> needle="(macro-thread-restore!"; attribute :>> obligation="existing whole-thread restore is not a running parent stack split"; }
part source37:SourceRow { attribute :>> key="thread-resume"; attribute :>> path="vendor/gambit/lib/_thread.scm"; attribute :>> needle="(define-prim (##thread-resume-execution!)"; attribute :>> obligation="resume thunk/interrupt handling remains a scheduler consumer"; }
part source38:SourceRow { attribute :>> key="wind"; attribute :>> path="vendor/gambit/lib/_thread.scm"; attribute :>> needle="(define-prim (##continuation-unwind-wind src dst continue)"; attribute :>> obligation="dynamic wind is an observable control effect"; }
part source39:SourceRow { attribute :>> key="graft"; attribute :>> path="vendor/gambit/lib/_thread.scm"; attribute :>> needle="(define-prim (##continuation-graft-aux"; attribute :>> obligation="repeatable continuation is not a cached task value"; }
part source40:SourceRow { attribute :>> key="otp-steal"; attribute :>> path="vendor/erlang-otp/erts/emulator/beam/erl_process.c"; attribute :>> needle="try_steal_task_from_victim"; attribute :>> obligation="Erlang steals queued tasks/processes, not Gambit running frames"; }
part source41:SourceRow { attribute :>> key="otp-batch"; attribute :>> path="vendor/erlang-otp/erts/emulator/beam/erl_process.c"; attribute :>> needle="Don't steal too many tasks at once"; attribute :>> obligation="bounded steal batches trade critical section length for transfer work"; }
part source42:SourceRow { attribute :>> key="otp-message"; attribute :>> path="vendor/erlang-otp/erts/emulator/internal_doc/GarbageCollection.md"; attribute :>> needle="allocate a message container"; attribute :>> obligation="messages carry real allocation/copy costs; local shared split is a different contract"; }
part source43:SourceRow { attribute :>> key="otp-progress"; attribute :>> path="vendor/erlang-otp/erts/emulator/internal_doc/ThreadProgress.md"; attribute :>> needle="remove the possibility to look up"; attribute :>> obligation="retirement needs closed lookup and matching reader quiescence"; }
part source44:SourceRow { attribute :>> key="otp-native"; attribute :>> path="vendor/erlang-otp/erts/doc/references/erl_nif.md"; attribute :>> needle="a separate set of schedulers called dirty schedulers"; attribute :>> obligation="native work classification does not authorize moving thread-affine Tcl stacks"; }
part def ComponentRow { attribute componentId:String; attribute sharedContract:String; attribute role:String; }
part component0:ComponentRow { attribute :>> componentId="scheme-plan"; attribute :>> sharedContract="SplitSpec/TaskOccurrence/RootHomes/ReturnCohort"; attribute :>> role="future eligibility, liveness, alias/control and cut semantics"; }
part component1:ComponentRow { attribute :>> componentId="split-owner"; attribute :>> sharedContract="SplitSpec/TaskOccurrence/RootHomes/ReturnCohort"; attribute :>> role="exclusive claim, initialized copy, ready publication and source release"; }
part component2:ComponentRow { attribute :>> componentId="root-domain"; attribute :>> sharedContract="SplitSpec/TaskOccurrence/RootHomes/ReturnCohort"; attribute :>> role="source/copy/queue/restore/result/capture root coverage"; }
part component3:ComponentRow { attribute :>> componentId="scheduler"; attribute :>> sharedContract="SplitSpec/TaskOccurrence/RootHomes/ReturnCohort"; attribute :>> role="existing queues and whole-context restore; new split eligibility adapter"; }
part component4:ComponentRow { attribute :>> componentId="continuation"; attribute :>> sharedContract="SplitSpec/TaskOccurrence/RootHomes/ReturnCohort"; attribute :>> role="captured computation and per-occurrence task identity"; }
part component5:ComponentRow { attribute :>> componentId="payback"; attribute :>> sharedContract="SplitSpec/TaskOccurrence/RootHomes/ReturnCohort"; attribute :>> role="counts, aborted work and C23/migration admission"; }
part def LearningRow { attribute key:String; attribute source:String; attribute mechanism:String; attribute fact:String; attribute mismatch:String; attribute candidate:String; attribute status:String; }
part learning0:LearningRow { attribute :>> key="paper-lazy"; attribute :>> source="feeley-paper"; attribute :>> mechanism="lazy future task materialization"; attribute :>> fact="materialize suspended parent/placeholder when another processor resumes it"; attribute :>> mismatch="historical PVM is not current C backend execution"; attribute :>> candidate="use explicit split point and root/return contract"; attribute :>> status="PRIMARY-PAPER"; }
part learning1:LearningRow { attribute :>> key="current-hooks"; attribute :>> source="task-push-empty"; attribute :>> mechanism="task frontend with empty native hooks"; attribute :>> fact="GVM task labels and C hook emission exist; header hooks are empty"; attribute :>> mismatch="cannot claim current runtime already implements lazy task splitting"; attribute :>> candidate="reuse semantic seams; replace hook responsibility only after full admission"; attribute :>> status="CURRENT-LOCAL-SOURCE"; }
part learning2:LearningRow { attribute :>> key="frame-spec"; attribute :>> source="physical-frame"; attribute :>> mechanism="validated physical descriptor"; attribute :>> fact="kind, size, link and gc-map are represented in current local FrameSpec"; attribute :>> mismatch="physical metadata has no exclusive split, result or task-occurrence ownership"; attribute :>> candidate="extend Scheme-owned semantic split plan and reuse physical decoder"; attribute :>> status="CURRENT-WORKING-TREE"; }
part learning3:LearningRow { attribute :>> key="queued-steal"; attribute :>> source="steal-queued"; attribute :>> mechanism="steal runnable Scheme threads"; attribute :>> fact="pinned/locked queue thread is removed and restored on thief"; attribute :>> mismatch="not lazy materialization from a running child/parent stack"; attribute :>> candidate="reuse queue/restore consumer after a correct parent context is published"; attribute :>> status="CURRENT-LOCAL-SOURCE"; }
part learning4:LearningRow { attribute :>> key="gc-copy"; attribute :>> source="captured-copy"; attribute :>> mechanism="stack-to-heap continuation copying"; attribute :>> fact="collector already decodes and copies captured frames and forwards links"; attribute :>> mismatch="GC ownership does not itself grant a concurrent scheduler snapshot"; attribute :>> candidate="retain source roots; make copy/queue/restore root handoff explicit"; attribute :>> status="CURRENT-LOCAL-SOURCE"; }
part learning5:LearningRow { attribute :>> key="multi-shot"; attribute :>> source="graft"; attribute :>> mechanism="repeated continuation resumption"; attribute :>> fact="frame and denv identities plus wind effects are observable"; attribute :>> mismatch="one-shot task ownership cannot imply Scheme body memoization"; attribute :>> candidate="after-value resumption repeats suffix; before-spawn occurrence must be fresh"; attribute :>> status="GAMBIT-DERIVATION-OPEN"; }
part learning6:LearningRow { attribute :>> key="otp-scheduling"; attribute :>> source="otp-batch"; attribute :>> mechanism="queued scheduling and bounded batches"; attribute :>> fact="batching explicitly bounds queue critical-section work"; attribute :>> mismatch="no evidence for directly importing BEAM process state into Gambit"; attribute :>> candidate="evaluate batch ownership only after single-parent correctness"; attribute :>> status="PINNED-REFERENCE-SOURCE"; }
part learning7:LearningRow { attribute :>> key="otp-isolation"; attribute :>> source="otp-message"; attribute :>> mechanism="explicit message transfer costs"; attribute :>> fact="message copy/container work is not free"; attribute :>> mismatch="general Scheme aliases cannot be silently copied"; attribute :>> candidate="share heap referents under Scheme semantics; isolate actors only under separate profile"; attribute :>> status="PINNED-REFERENCE-SOURCE"; }
part def IssuerRow { attribute key:String; attribute source:String; attribute existing:String; attribute candidate:String; attribute gap:String; }
part issuer0:IssuerRow { attribute :>> key="split-plan"; attribute :>> source="future-generator"; attribute :>> existing="gen-fut computes parent live set and child closure variables"; attribute :>> candidate="Scheme semantic stage seals SplitSpec with control/alias/native restrictions"; attribute :>> gap="no full immutable identity/alias proof"; }
part issuer1:IssuerRow { attribute :>> key="frame-plan"; attribute :>> source="physical-frame"; attribute :>> existing="FrameSpec validates physical size/link/gc-map"; attribute :>> candidate="derive parent and child coordinates from one semantic cohort"; attribute :>> gap="return-task tag alone does not encode split ownership"; }
part issuer2:IssuerRow { attribute :>> key="claim"; attribute :>> source="steal-queued"; attribute :>> existing="current scheduler steals complete queued threads"; attribute :>> candidate="only one parent snapshot/split owner for one dynamic occurrence"; attribute :>> gap="new running-parent split operation absent in inspected C hooks"; }
part issuer3:IssuerRow { attribute :>> key="roots"; attribute :>> source="context-stack"; attribute :>> existing="current root origin scans stack, regs, saved, RC"; attribute :>> candidate="source, private copy, queue, restore and result homes share real GC enumeration"; attribute :>> gap="flag-level invariant does not prove native slots"; }
part issuer4:IssuerRow { attribute :>> key="resume"; attribute :>> source="graft"; attribute :>> existing="captured continuation restores frame and denv"; attribute :>> candidate="fresh occurrence before spawn; stable task reference after value; replay suffix effects"; attribute :>> gap="split-child escaping control semantics open"; }
part issuer5:IssuerRow { attribute :>> key="result"; attribute :>> source="task-pop-empty"; attribute :>> existing="TASK_POP source hook is empty"; attribute :>> candidate="explicit success/error/cancel result and rooted waiter handoff"; attribute :>> gap="normal value model does not implement result ABI"; }
part def ProfileRow { attribute key:String; attribute scope:String; attribute permission:String; attribute boundary:String; }
part profile0:ProfileRow { attribute :>> key="eligible-future"; attribute :>> scope="explicit admitted task occurrence"; attribute :>> permission="parallel split only when control/alias/native profile proves admissible"; attribute :>> boundary="unknowns use existing sequential path before any split effects"; }
part profile1:ProfileRow { attribute :>> key="general-scheme"; attribute :>> scope="general Scheme calls and continuation"; attribute :>> permission="retain current semantic behavior; no implicit parallel map or task memoization"; attribute :>> boundary="parallel eligibility failure does not reject the Scheme program"; }
part profile2:ProfileRow { attribute :>> key="after-value"; attribute :>> scope="continuation captured after future value is available"; attribute :>> permission="repeat suffix with same referenced result/task identity"; attribute :>> boundary="does not prove inside-child escaping continuation semantics"; }
part profile3:ProfileRow { attribute :>> key="current-c"; attribute :>> scope="inspected compiler/header source"; attribute :>> permission="task entry/return metadata and whole-thread queue stealing exist"; attribute :>> boundary="no native execution or loaded-cohort qualification"; }
part def PathRow { attribute key:String; attribute producer:String; attribute consumer:String; attribute classification:String; attribute missing:String; }
part path0:PathRow { attribute :>> key="future-c-chain"; attribute :>> producer="future-parse"; attribute :>> consumer="task-pop-empty"; attribute :>> classification="parse -> fut -> gen-fut -> GVM task labels -> C hooks -> empty macro"; attribute :>> missing="scheduler split/result implementation"; }
part path1:PathRow { attribute :>> key="frame-root-chain"; attribute :>> producer="emit-task-spec"; attribute :>> consumer="heap-frame-scan"; attribute :>> classification="physical FrameSpec -> descriptor -> frame scanning"; attribute :>> missing="split partition and partial-copy root mapping"; }
part path2:PathRow { attribute :>> key="thread-steal-chain"; attribute :>> producer="steal-remove"; attribute :>> consumer="thread-resume"; attribute :>> classification="queued complete thread -> restore -> resume thunk"; attribute :>> missing="running parent materialization"; }
part path3:PathRow { attribute :>> key="capture-restore"; attribute :>> producer="capture-macro"; attribute :>> consumer="graft-macro"; attribute :>> classification="frame/denv capture -> reconstruction"; attribute :>> missing="occurrence identity and escaping split-task semantics"; }
part path4:PathRow { attribute :>> key="paper-versus-native"; attribute :>> producer="feeley-paper"; attribute :>> consumer="task-push-empty"; attribute :>> classification="paper capability and current C stub are different facts"; attribute :>> missing="native/effective artifact linkage"; }
part def RouteRow { attribute component:String; attribute actionName:String; attribute lemma:String; attribute producerAnchor:String; attribute obligationId:String; }
part route0:RouteRow { attribute :>> component="scheme-plan"; attribute :>> actionName="lazy_future_split.denyParallelProfile"; attribute :>> lemma="LazySplit.denyParallelProfilePreserves"; attribute :>> producerAnchor="future-generator"; attribute :>> obligationId="split-safety"; }
part route1:RouteRow { attribute :>> component="split-owner"; attribute :>> actionName="lazy_future_split.claimSplit"; attribute :>> lemma="LazySplit.claimSplitPreserves"; attribute :>> producerAnchor="emit-entry"; attribute :>> obligationId="split-safety"; }
part route2:RouteRow { attribute :>> component="split-owner"; attribute :>> actionName="lazy_future_split.failedProbe"; attribute :>> lemma="LazySplit.failedProbePreserves"; attribute :>> producerAnchor="emit-entry"; attribute :>> obligationId="split-safety"; }
part route3:RouteRow { attribute :>> component="split-owner"; attribute :>> actionName="lazy_future_split.allocateCopy"; attribute :>> lemma="LazySplit.allocateCopyPreserves"; attribute :>> producerAnchor="emit-entry"; attribute :>> obligationId="split-safety"; }
part route4:RouteRow { attribute :>> component="split-owner"; attribute :>> actionName="lazy_future_split.initializeCopy"; attribute :>> lemma="LazySplit.initializeCopyPreserves"; attribute :>> producerAnchor="emit-entry"; attribute :>> obligationId="split-safety"; }
part route5:RouteRow { attribute :>> component="split-owner"; attribute :>> actionName="lazy_future_split.publishReady"; attribute :>> lemma="LazySplit.publishReadyPreserves"; attribute :>> producerAnchor="emit-entry"; attribute :>> obligationId="split-safety"; }
part route6:RouteRow { attribute :>> component="split-owner"; attribute :>> actionName="lazy_future_split.commitSplit"; attribute :>> lemma="LazySplit.commitSplitPreserves"; attribute :>> producerAnchor="emit-entry"; attribute :>> obligationId="split-safety"; }
part route7:RouteRow { attribute :>> component="split-owner"; attribute :>> actionName="lazy_future_split.abortPrivate"; attribute :>> lemma="LazySplit.abortPrivatePreserves"; attribute :>> producerAnchor="emit-entry"; attribute :>> obligationId="split-safety"; }
part route8:RouteRow { attribute :>> component="split-owner"; attribute :>> actionName="lazy_future_split.localChildDone"; attribute :>> lemma="LazySplit.localChildDonePreserves"; attribute :>> producerAnchor="emit-entry"; attribute :>> obligationId="split-safety"; }
part route9:RouteRow { attribute :>> component="split-owner"; attribute :>> actionName="lazy_future_split.localAfterAbortDone"; attribute :>> lemma="LazySplit.localAfterAbortDonePreserves"; attribute :>> producerAnchor="emit-entry"; attribute :>> obligationId="split-safety"; }
part route10:RouteRow { attribute :>> component="split-owner"; attribute :>> actionName="lazy_future_split.childDoneInSplit"; attribute :>> lemma="LazySplit.childDoneInSplitPreserves"; attribute :>> producerAnchor="emit-entry"; attribute :>> obligationId="split-safety"; }
part route11:RouteRow { attribute :>> component="scheduler"; attribute :>> actionName="lazy_future_split.dequeueParent"; attribute :>> lemma="LazySplit.dequeueParentPreserves"; attribute :>> producerAnchor="steal-restore"; attribute :>> obligationId="split-safety"; }
part route12:RouteRow { attribute :>> component="scheduler"; attribute :>> actionName="lazy_future_split.restoreParent"; attribute :>> lemma="LazySplit.restoreParentPreserves"; attribute :>> producerAnchor="steal-restore"; attribute :>> obligationId="split-safety"; }
part route13:RouteRow { attribute :>> component="split-owner"; attribute :>> actionName="lazy_future_split.publishResult"; attribute :>> lemma="LazySplit.publishResultPreserves"; attribute :>> producerAnchor="emit-entry"; attribute :>> obligationId="split-safety"; }
part route14:RouteRow { attribute :>> component="scheduler"; attribute :>> actionName="lazy_future_split.runParentPrefix"; attribute :>> lemma="LazySplit.runParentPrefixPreserves"; attribute :>> producerAnchor="steal-restore"; attribute :>> obligationId="split-safety"; }
part route15:RouteRow { attribute :>> component="scheduler"; attribute :>> actionName="lazy_future_split.consumeSplitResult"; attribute :>> lemma="LazySplit.consumeSplitResultPreserves"; attribute :>> producerAnchor="steal-restore"; attribute :>> obligationId="split-safety"; }
part route16:RouteRow { attribute :>> component="scheduler"; attribute :>> actionName="lazy_future_split.runLocalParent"; attribute :>> lemma="LazySplit.runLocalParentPreserves"; attribute :>> producerAnchor="steal-restore"; attribute :>> obligationId="split-safety"; }
part route17:RouteRow { attribute :>> component="continuation"; attribute :>> actionName="lazy_future_split.captureAfterValue"; attribute :>> lemma="LazySplit.captureAfterValuePreserves"; attribute :>> producerAnchor="graft"; attribute :>> obligationId="after-value-law"; }
part route18:RouteRow { attribute :>> component="continuation"; attribute :>> actionName="lazy_future_split.restoreAfterValue"; attribute :>> lemma="LazySplit.restoreAfterValuePreserves"; attribute :>> producerAnchor="graft"; attribute :>> obligationId="after-value-law"; }
part route19:RouteRow { attribute :>> component="continuation"; attribute :>> actionName="lazy_future_split.dropCaptured"; attribute :>> lemma="LazySplit.dropCapturedPreserves"; attribute :>> producerAnchor="graft"; attribute :>> obligationId="after-value-law"; }
part route20:RouteRow { attribute :>> component="continuation"; attribute :>> actionName="lazy_future_split.exitParent"; attribute :>> lemma="LazySplit.exitParentPreserves"; attribute :>> producerAnchor="graft"; attribute :>> obligationId="after-value-law"; }
part route21:RouteRow { attribute :>> component="root-domain"; attribute :>> actionName="lazy_future_split.retireTaskRoots"; attribute :>> lemma="LazySplit.retireTaskRootsPreserves"; attribute :>> producerAnchor="context-stack"; attribute :>> obligationId="split-safety"; }
part route22:RouteRow { attribute :>> component="root-domain"; attribute :>> actionName="lazy_future_split.retireDescriptor"; attribute :>> lemma="LazySplit.retireDescriptorPreserves"; attribute :>> producerAnchor="context-stack"; attribute :>> obligationId="split-safety"; }
part route23:RouteRow { attribute :>> component="root-domain"; attribute :>> actionName="lazy_future_split.closeGc"; attribute :>> lemma="LazySplit.closeGcPreserves"; attribute :>> producerAnchor="context-stack"; attribute :>> obligationId="split-safety"; }
part route24:RouteRow { attribute :>> component="root-domain"; attribute :>> actionName="lazy_future_split.freezeRoots"; attribute :>> lemma="LazySplit.freezeRootsPreserves"; attribute :>> producerAnchor="context-stack"; attribute :>> obligationId="split-safety"; }
part route25:RouteRow { attribute :>> component="root-domain"; attribute :>> actionName="lazy_future_split.beginScan"; attribute :>> lemma="LazySplit.beginScanPreserves"; attribute :>> producerAnchor="context-stack"; attribute :>> obligationId="split-safety"; }
part route26:RouteRow { attribute :>> component="root-domain"; attribute :>> actionName="lazy_future_split.endScan"; attribute :>> lemma="LazySplit.endScanPreserves"; attribute :>> producerAnchor="context-stack"; attribute :>> obligationId="split-safety"; }
part route27:RouteRow { attribute :>> component="root-domain"; attribute :>> actionName="lazy_future_split.resumeGc"; attribute :>> lemma="LazySplit.resumeGcPreserves"; attribute :>> producerAnchor="context-stack"; attribute :>> obligationId="split-safety"; }
part def CompositionRow { attribute key:String; attribute lemma:String; attribute source:String; attribute obligation:String; attribute boundary:String; }
part composition0:CompositionRow { attribute :>> key="root-home"; attribute :>> lemma="LazySplit.parentAlwaysRooted"; attribute :>> source="context-stack"; attribute :>> obligation="split-safety"; attribute :>> boundary="logical root flags; physical slot/relocation mapping open"; }
part composition1:CompositionRow { attribute :>> key="queue-initialization"; attribute :>> lemma="LazySplit.queuePublishedInitialized"; attribute :>> source="captured-publish"; attribute :>> obligation="split-safety"; attribute :>> boundary="one private snapshot and stable links; real GC publication needs independent qualification"; }
part composition2:CompositionRow { attribute :>> key="restore-occurrence"; attribute :>> lemma="LazySplit.restoreAfterValueKeepsChild"; attribute :>> source="graft"; attribute :>> obligation="after-value-law"; attribute :>> boundary="after-value capture only; no body memoization for arbitrary continuation"; }
part composition3:CompositionRow { attribute :>> key="net-threshold"; attribute :>> lemma="LazySplitCost.positiveIff"; attribute :>> source="feeley-paper"; attribute :>> obligation="payback-counts"; attribute :>> boundary="equal-unit cost equation against eager alternative; not current C runtime reduction"; }
part def MemoryRow { attribute key:String; attribute order:String; attribute premise:String; attribute obligation:String; }
part memory0:MemoryRow { attribute :>> key="claim"; attribute :>> order="compare-and-claim parent marker before copying; child completion uses same task state"; attribute :>> premise="one dynamic task occurrence; parent region not mutable/exposed by child"; attribute :>> obligation="c23-memory"; }
part memory1:MemoryRow { attribute :>> key="copy"; attribute :>> order="source root retained; initialized destination slots registered before GC-visible publication"; attribute :>> premise="no borrowed physical root cursor survives safepoint; restart from live descriptor cohort"; attribute :>> obligation="copy-forwarding"; }
part memory2:MemoryRow { attribute :>> key="ready"; attribute :>> order="initialize copy/result protocol then release-publish ready; acquire before claim/run"; attribute :>> premise="queue publication not equivalent to completed root transfer"; attribute :>> obligation="queue-result"; }
part memory3:MemoryRow { attribute :>> key="done"; attribute :>> order="child result rooted before release completion; strict waiter acquire before use"; attribute :>> premise="value/error/cancel result and actual wakeup protocol still need design"; attribute :>> obligation="queue-result"; }
part memory4:MemoryRow { attribute :>> key="restore"; attribute :>> order="queue root -> restore root -> private context root; captured aliases remain rooted"; attribute :>> premise="after-value resumption keeps occurrence identity; pre-spawn needs fresh identity"; attribute :>> obligation="before-spawn-freshness"; }
part memory5:MemoryRow { attribute :>> key="retire"; attribute :>> order="close all lookup/restore access; drain source/copy/queue/result/capture/descriptors"; attribute :>> premise="Erlang quiescence is not automatically a Gambit continuation checkpoint"; attribute :>> obligation="all-final-use"; }
part def GainRow { attribute key:String; attribute benefit:String; attribute cost:String; attribute condition:String; attribute refutation:String; }
part gain0:GainRow { attribute :>> key="materialization"; attribute :>> benefit="N-(S+A) dynamic calls avoid eager materialization when S split and A aborted-after-allocation"; attribute :>> cost="N marker/check work, S copy/handoff, A abandoned allocation and K failed probes"; attribute :>> condition="compare with a specified eager correct task baseline; S+A<=N"; attribute :>> refutation="aborted allocation counts even without successful split"; }
part gain1:GainRow { attribute :>> key="current-noop"; attribute :>> benefit="adds real parallel capability to a currently empty task-hook path"; attribute :>> cost="all marker/materialization/result machinery is additional versus current noop hooks"; attribute :>> condition="useful ready work and reduced span must pay for overhead"; attribute :>> refutation="cannot claim to remove N task allocations that current hooks do not perform"; }
part gain2:GainRow { attribute :>> key="no-steal-path"; attribute :>> benefit="an eligible unclaimed occurrence needs no separate parent/placeholder materialization in this model"; attribute :>> cost="existing GVM register saves/frame work plus new marker checks remain"; attribute :>> condition="no successful claim, no allocated aborted claim"; attribute :>> refutation="no-split alone does not imply no allocation"; }
part gain3:GainRow { attribute :>> key="root-reuse"; attribute :>> benefit="reuse precise frame decoders and context root enumeration"; attribute :>> cost="new private-copy/queue/restore/result homes and slot partition proof"; attribute :>> condition="descriptors and moving updates qualified across actual collector phases"; attribute :>> refutation="a second independent scanner or stale copied pointers erases correctness"; }
part gain4:GainRow { attribute :>> key="queue-reuse"; attribute :>> benefit="published parent can reuse runnable-context scheduler consumer"; attribute :>> cost="new materialization adapter and split-specific ready/grant states"; attribute :>> condition="existing thread identity, locks, pinning and denv restored correctly"; attribute :>> refutation="thread stealing alone cannot split active frames"; }
part gain5:GainRow { attribute :>> key="continuation"; attribute :>> benefit="after-value suffix can replay without creating a second child for the same admitted occurrence"; attribute :>> cost="per-shot execution/root/wind work remains; fresh pre-spawn creates real new work"; attribute :>> condition="capture point classified and semantics preserved"; attribute :>> refutation="memoizing an effectful suffix or banning legal continuation is not a benefit"; }
part gain6:GainRow { attribute :>> key="batching"; attribute :>> benefit="Erlang suggests amortized queued transfer and bounded lock hold time"; attribute :>> cost="batch root ownership and contention overhead"; attribute :>> condition="single-task proof composes to batches without duplicate grant"; attribute :>> refutation="no measured or proved batching benefit here"; }
part def ContractRow { attribute fromNode:String; attribute toNode:String; attribute custody:String; }
part contract0:ContractRow { attribute :>> fromNode="Feeley TASK/WORK/DONE"; attribute :>> toNode="Scheme future plan"; attribute :>> custody="paper fact; source-target boundary already represented"; }
part contract1:ContractRow { attribute :>> fromNode="Scheme future plan"; attribute :>> toNode="GVM task labels and FrameSpec"; attribute :>> custody="liveness, child closure inputs, parent return and physical coordinates"; }
part contract2:ContractRow { attribute :>> fromNode="GVM task labels and FrameSpec"; attribute :>> toNode="Current C hooks"; attribute :>> custody="TASK_PUSH/TASK_POP currently empty in inspected header"; }
part contract3:ContractRow { attribute :>> fromNode="Scheme future plan"; attribute :>> toNode="Eligible split plan"; attribute :>> custody="proposed control/alias/native and occurrence contract"; }
part contract4:ContractRow { attribute :>> fromNode="Eligible split plan"; attribute :>> toNode="One split owner"; attribute :>> custody="exclusive parent claim; child done may arrive meanwhile"; }
part contract5:ContractRow { attribute :>> fromNode="One split owner"; attribute :>> toNode="Private rooted copy"; attribute :>> custody="source retained; no partially initialized queue entry"; }
part contract6:ContractRow { attribute :>> fromNode="Private rooted copy"; attribute :>> toNode="Ready parent queue"; attribute :>> custody="release-ready, then source-root handoff"; }
part contract7:ContractRow { attribute :>> fromNode="Ready parent queue"; attribute :>> toNode="Existing scheduler restore"; attribute :>> custody="whole context consumer reused after split creates valid context"; }
part contract8:ContractRow { attribute :>> fromNode="Existing scheduler restore"; attribute :>> toNode="Parent context root"; attribute :>> custody="queue -> restore -> context handoff"; }
part contract9:ContractRow { attribute :>> fromNode="Child result root"; attribute :>> toNode="Strict future consumer"; attribute :>> custody="publish value before strict observation"; }
part contract10:ContractRow { attribute :>> fromNode="Parent context root"; attribute :>> toNode="Captured after-value continuation"; attribute :>> custody="same occurrence; repeat suffix, not child; general escaping child capture open"; }
part contract11:ContractRow { attribute :>> fromNode="FrameSpec GC consumers"; attribute :>> toNode="All root homes"; attribute :>> custody="source/copy/queue/restore/result/captured and descriptor cohort"; }
part contract12:ContractRow { attribute :>> fromNode="Erlang queue/progress lessons"; attribute :>> toNode="Retirement and batching"; attribute :>> custody="queued work and qualified quiescence; not Scheme heap copying"; }
part def NeedRow { attribute key:String; attribute status:String; attribute condition:String; }
part need0:NeedRow { attribute :>> key="split-safety"; attribute :>> status="formal"; attribute :>> condition="single accepted claim; initialized queue publication; source/destination root home throughout abstract protocol"; }
part need1:NeedRow { attribute :>> key="after-value-law"; attribute :>> status="formal"; attribute :>> condition="fixed task occurrence does not rerun child on after-value suffix restoration"; }
part need2:NeedRow { attribute :>> key="payback-counts"; attribute :>> status="formal"; attribute :>> condition="cost threshold conditional on N,S,A and declared equal-unit costs"; }
part need3:NeedRow { attribute :>> key="source-eligibility"; attribute :>> status="unresolved"; attribute :>> condition="explicit future contract or effect/control proof; native-affine/unknown/exposed frame cases fallback before split"; }
part need4:NeedRow { attribute :>> key="frame-partition"; attribute :>> status="unresolved"; attribute :>> condition="GVM slots/registers/closed vars/denv map to two precise root and structural-link descriptions"; }
part need5:NeedRow { attribute :>> key="copy-forwarding"; attribute :>> status="unresolved"; attribute :>> condition="real GC relocation and captured-link mutation refine a stable parent copy protocol"; }
part need6:NeedRow { attribute :>> key="queue-result"; attribute :>> status="unresolved"; attribute :>> condition="existing run queues accept published parent context and exact result/cancel/exception delivery"; }
part need7:NeedRow { attribute :>> key="multishot-inside-task"; attribute :>> status="unresolved"; attribute :>> condition="escape/capture inside an already split child needs full semantics; profile must exclude it until proved"; }
part need8:NeedRow { attribute :>> key="before-spawn-freshness"; attribute :>> status="unresolved"; attribute :>> condition="actual continuation restore distinguishes a fresh spawn from after-value access; arithmetic ID lemma is not native refinement"; }
part need9:NeedRow { attribute :>> key="c23-memory"; attribute :>> status="unresolved"; attribute :>> condition="claim/result release-acquire, safepoint coverage and module lifetime refine the scalar atomic-step model"; }
part need10:NeedRow { attribute :>> key="all-final-use"; attribute :>> status="unresolved"; attribute :>> condition="descriptor/root retirement has complete external/FFI/captured/late-reader closure"; }
part need11:NeedRow { attribute :>> key="effective-cohort"; attribute :>> status="unresolved"; attribute :>> condition="current source macros and compiler correspond to an actual configured native module cohort"; }
part need12:NeedRow { attribute :>> key="net-runtime-return"; attribute :>> status="unresolved"; attribute :>> condition="costs and useful parallel work overcome new overhead; no reduction in current noop task allocations claimed"; }
}
