package GambitVMResizeRefinement {
  private import ScalarValues::*;
  private import GambitVMResizeTransaction::*;
  attribute sourceSimulationClosed:Boolean = false;
  part def Step {
    ref part component:Contract;
    attribute quintAction:String; attribute cFunction:String;
    attribute representation:String; attribute guard:String;
    attribute leanLaw:String; attribute unresolved:String;
  }
  part request:Step { ref part :>> component=roots; attribute :>> quintAction="request"; attribute :>> cFunction="___vm_resize_pstate"; attribute :>> representation="QNT vmRoot = resize.thunk registered in mark_vm_scmobj; old = processor_count before old-set barrier"; attribute :>> guard="idle ledger, valid target, nonwrapping generation, POSIX coordinator cancellation excluded"; attribute :>> leanLaw="parkedRootsCoverEntry"; attribute :>> unresolved="Whole-root-view and nonlocal escape closure; generation exhaustion native control"; }
  part collect:Step { ref part :>> component=census; attribute :>> quintAction="collect"; attribute :>> cFunction="resize_heap"; attribute :>> representation="Closed gc_round.participant_count; assigned is physical alloc cursor prefix, not live-word estimate; abstract finite census does not enumerate all eleven contexts"; attribute :>> guard="all existing participants stopped; no independent worker or raw native publisher"; attribute :>> leanLaw="freeHeadroomCoversBudget"; attribute :>> unresolved="Universal concrete interval mapping, C arithmetic and allocation failure at restore"; }
  part reserve:Step { ref part :>> component=grant; attribute :>> quintAction="reserve"; attribute :>> cFunction="___reserve_vm_resize"; attribute :>> representation="QNT grant/assigned = all slot stack/heap pointers plus one charge; capacity table may relocate, individual sections remain stable; free R excluded from assigned"; attribute :>> guard="entire allocator result known; count/budget bounds; no observable incomplete grant"; attribute :>> leanLaw="grantFloor; consumePair; freeHeadroomCoversBudget"; attribute :>> unresolved="Multi-store linearization relies on exclusive stopped cohort; no helper takeover without stop receipt"; }
  part initialize:Step { ref part :>> component=grant; attribute :>> quintAction="initialize"; attribute :>> cFunction="___setup_mem_pstate"; attribute :>> representation="QNT initialized maps to per-slot INITIALIZED after full ___setup_pstate, not to a written context pointer or aggregate created counter"; attribute :>> guard="reserved distinct pair; no collection/callback while binding; failed setup cleans its own partial resources"; attribute :>> leanLaw="publishRequiresEveryInitialization"; attribute :>> unresolved="Every configuration of OS/actlog partial construction; raw nested callbacks"; }
  part create:Step { ref part :>> component=failure; attribute :>> quintAction="beginCreate; createSuccess; createFailure; createUnknown"; attribute :>> cFunction="___thread_create"; attribute :>> representation="CREATING written before native call; CREATED only after known successful return and stored native handle; QNT created includes existing published slots, not resize.created counter alone"; attribute :>> guard="returned pthread code used directly, common init before native call; children parked under entry gate"; attribute :>> leanLaw="publishRequiresEveryCreate"; attribute :>> unresolved="Unmanaged signal/longjmp/owner death and handle-result loss need stop/custody qualification; no inferred rollback"; }
  part commit:Step { ref part :>> component=publication; attribute :>> quintAction="commitMembers"; attribute :>> cFunction="barrier_sync_op"; attribute :>> representation="OP_SET_PROCESSOR_COUNT changes only at root after old-set gather; C slots cover every required child before request is emitted"; attribute :>> guard="all setups/creates succeeded, no unknown; old set consumes one result"; attribute :>> leanLaw="noNewMemberWithoutCreate"; attribute :>> unresolved="C memory-model proof of existing volatile-message barrier; this is a real native obligation"; }
  part enter:Step { ref part :>> component=roots; attribute :>> quintAction="releaseEntry; finish"; attribute :>> cFunction="start_processor_execution"; attribute :>> representation="Entry under mutex/condition release-acquire; TLS set after RUN permission; new-set finish then sync loop; thunk reloaded and rooted marker endpoint reads stable cell after allocation"; attribute :>> guard="context startup root registered before membership; logical allowance retained"; attribute :>> leanLaw="parkedRootsCoverEntry; stackSubdivisionCoversFudge"; attribute :>> unresolved="Complete generated first-frame B coverage; arbitrary foreign safepoints and legacy SFUN"; }
  part abort:Step { ref part :>> component=failure; attribute :>> quintAction="joinSuccess; joinUnknown; rollback"; attribute :>> cFunction="___rollback_vm_resize"; attribute :>> representation="Known abort children never enter Scheme; cleanup then restore alloc cursor/assigned/stacks/capacity only after every native join; retained state preserves root/grant"; attribute :>> guard="no in-flight unknown call; all joins have successful receipts; fixed grant not reused"; attribute :>> leanLaw="refundRequiresQuiescence; unknownPreventsRefund"; attribute :>> unresolved="Actual byte-free interruption, cancellation restoration and DataWriteClosed beyond managed leaf calls"; }
  part retire:Step { ref part :>> component=retirement; attribute :>> quintAction="shrinkReject; shrinkCommit; retireJoin; retireUnknown; transferAndFinish"; attribute :>> cFunction="___transfer_retired_still"; attribute :>> representation="Admitted owner invalidates entry marker before exit; successful join precedes still splice into active context; capacity stays allocated until later GC, not immediate refund"; attribute :>> guard="RC empty, no foreign effect, no retained non-entry marker; no unregistered external writer"; attribute :>> leanLaw="refundRequiresQuiescence"; attribute :>> unresolved="Raw borrow exclusion, retired processor-object identity and full still/statistics ownership refinement"; }
}
