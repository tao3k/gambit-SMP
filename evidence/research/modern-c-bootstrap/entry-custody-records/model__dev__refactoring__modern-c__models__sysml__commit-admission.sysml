package GambitModernCCommitAdmission {
  private import ScalarValues::*;
  ref part realization = GambitRuntimeRoleRealization::cut0;
  attribute candidateStatus : String = "LOCAL-CANDIDATE; NOT-ADMITTED; NOT-PUSHED";
  attribute currentStage : String = "official two-pass bootstrap complete; real map multi-shot/11-GC controls pass in one context; host-budget p11 startup capacity fails; lifetime/FFI/termination/source refinement remain open; no commit admission";
  attribute gitExecutionAuthorized : Boolean = false;

  part def Gate { attribute id : String; attribute purpose : String; }
  part tests : Gate { attribute :>> id = "tests"; attribute :>> purpose = "All tests required by this source cut must finish with exact source and profile receipts; missing, timeout, unknown and failed results block"; }
  part learning : Gate { attribute :>> id = "learning"; attribute :>> purpose = "State what the architecture taught us, what it amplifies, its actual retirement and added costs; no inferred speedup"; }
  part process : Gate { attribute :>> id = "process"; attribute :>> purpose = "Disclose the current refactoring stage, dependencies, remaining steps and acceptance boundary"; }
  part models : Gate { attribute :>> id = "models"; attribute :>> purpose = "Native SysML projection drives ASCENT; executable QNT and conditional Lean laws must be linked to the real consumers and source-refinement frontier"; }
  part questions : Gate { attribute :>> id = "questions"; attribute :>> purpose = "Answer the mandatory Gambit-paper, semantic, amplification and counterexample questions within the claimed cut; unresolved mandatory answers block"; }

  part def Need { ref part gate : Gate; attribute id : String; attribute method : String; attribute artifact : String; attribute scope : String; }
  part tObject : Need { ref part :>> gate = tests; attribute :>> id="T-OBJECT"; attribute :>> method="native"; attribute :>> artifact="vendor/gambit/lib/mem.c"; attribute :>> scope="six-canonical-objects-with-recorded-bazel-profile"; }
  part tStorage : Need { ref part :>> gate=tests; attribute :>> id="T-STORAGE"; attribute :>> method="native"; attribute :>> artifact="vendor/gambit/tests/runtime-roles.c"; attribute :>> scope="accessors-storage-sanitizer-and-retired-field-controls"; }
  part tFrame : Need { ref part :>> gate=tests; attribute :>> id="T-FRAME"; attribute :>> method="native"; attribute :>> artifact="vendor/gambit/tests/frame-contract.c"; attribute :>> scope="frame-fixtures-three-register-configurations"; }
  part tQnt : Need { ref part :>> gate=tests; attribute :>> id="T-QNT"; attribute :>> method="quint"; attribute :>> artifact="dev/refactoring/modern-c/models/quint/runtime_roles.qnt"; attribute :>> scope="three-histories-sampled-safety-and-four-invariant-negative-controls"; }
  part tLean : Need { ref part :>> gate=tests; attribute :>> id="T-LEAN"; attribute :>> method="lean"; attribute :>> artifact="dev/refactoring/modern-c/models/lean/RuntimeRoles.lean"; attribute :>> scope="six-conditional-laws-and-axiom-audit"; }
  part tCohort : Need { ref part :>> gate=tests; attribute :>> id="T-COHORT"; attribute :>> method="native"; attribute :>> artifact="vendor/gambit/lib/_kernel.scm"; attribute :>> scope="source-generated-compiler-runtime-bootstrap-cohort"; }
  part tMap : Need { ref part :>> gate=tests; attribute :>> id="T-MAP"; attribute :>> method="native"; attribute :>> artifact="vendor/gambit/lib/_std.scm"; attribute :>> scope="real-map-multishot-continuation-gc-and-resume"; }
  part tSmp : Need { ref part :>> gate=tests; attribute :>> id="T-SMP"; attribute :>> method="native"; attribute :>> artifact="vendor/gambit/lib/setup.c"; attribute :>> scope="resize-rc-roots-callbacks-join-failure-and-runtime-retirement"; }
  part aLesson : Need { ref part :>> gate=learning; attribute :>> id="A-LESSON"; attribute :>> method="source-analysis"; attribute :>> artifact="dev/refactoring/modern-c/bootstrap-validation.org"; attribute :>> scope="architectural-learning-and-real-consumer-replacement"; }
  part aCost : Need { ref part :>> gate=learning; attribute :>> id="A-COST"; attribute :>> method="source-analysis"; attribute :>> artifact="dev/refactoring/modern-c/bootstrap-validation.org"; attribute :>> scope="whole-vm-size-indirection-final-collective-and-unmeasured-costs"; }
  part pCurrent : Need { ref part :>> gate=process; attribute :>> id="P-CURRENT"; attribute :>> method="source-analysis"; attribute :>> artifact="dev/refactoring/modern-c/models/sysml/commit-admission.sysml"; attribute :>> scope="candidate-source-cut-stage-and-next-dependent-stages"; }
  part mNative : Need { ref part :>> gate=models; attribute :>> id="M-NATIVE"; attribute :>> method="sysml"; attribute :>> artifact="dev/refactoring/modern-c/models/sysml/runtime-role-realization.sysml"; attribute :>> scope="native-role-need-use-flow-projection"; }
  part mAscent : Need { ref part :>> gate=models; attribute :>> id="M-ASCENT"; attribute :>> method="ascent"; attribute :>> artifact="dev/modeling/ascent/bootstrap-cohort.rules.scm"; attribute :>> scope="artifact-scope-and-source-frontier-negative-controls"; }
  part mRefine : Need { ref part :>> gate=models; attribute :>> id="M-REFINE"; attribute :>> method="source-refinement"; attribute :>> artifact="vendor/gambit/lib/mem.c"; attribute :>> scope="real-root-freeze-termination-barrier-and-cleanup-to-model-obligations"; }

  part def Question { ref part gate : Gate = questions; attribute id : String; attribute method : String="paper-source-analysis"; attribute artifact : String="dev/refactoring/modern-c/commit-admission.org"; attribute scope : String; attribute prompt : String; attribute answer : String; attribute status : String; attribute evidence : String; attribute counterexample : String; }
  part qPvm : Question { attribute :>> id="Q-PVM"; attribute :>> scope="gvm-semantic-ownership-and-c-portability"; attribute :>> prompt="Which PVM idea is amplified, and which Scheme semantic decisions must stay out of C layout helpers?"; attribute :>> answer="Retain GVM target cooperation; one explicit frame/root origin feeds collectors and continuation consumers. The C role cut is groundwork, not a completed generator rewrite or LLVM backend."; attribute :>> status="answered-scoped"; attribute :>> evidence="FeeleyMillerLFP90 sections 1-2; gambit.h.in context accessors; mem.c mark_execution_roots; frame-consumers.org"; attribute :>> counterexample="Recreating Scheme control semantics independently in a new backend duplicates the semantic authority; moving C fields alone does not amplify PVM optimization."; }
  part qPoll : Question { attribute :>> id="Q-POLL"; attribute :>> scope="bounded-safepoint-and-participation-progress"; attribute :>> prompt="Does the new root participant prove progress for nonallocating loops, foreign blocking calls and collector cooperation?"; attribute :>> answer="No. This cut keeps the existing synchronous safepoint mechanism; phase guards establish ordering only. A bounded-progress claim needs generator placement, root freeze and foreign participation together."; attribute :>> status="answered-scoped"; attribute :>> evidence="Feeley1993 via retro-parallel section 3.4; mem.c require_gc_phase and garbage_collect_pstate; modernization-target.org"; attribute :>> counterexample="A nonallocating spin loop can avoid allocation checks and prevent a collective; new phase enums cannot force it to participate."; }
  part qMulti : Question { attribute :>> id="Q-MULTISHOT"; attribute :>> scope="map-capture-and-repeated-resume-with-gc"; attribute :>> prompt="Can captured map frames be resumed repeatedly after GC without consuming roots or imposing one-shot ownership?"; attribute :>> answer="Real generated-C map controls preserve original and 20/200 resumed results, 80 roots, dynamic-wind history, three C calls and eleven completed forced GCs in one context. This scoped witness does not prove arbitrary continuations, callbacks or SMP; the host-budget p11 startup fails before its body."; attribute :>> status="answered-scoped"; attribute :>> evidence="bootstrap-validation.org; mem.c mark_continuation/shared frame decoder; frame-continuation-roots.scm; retro-concurrency sections 4-5 distinguish one-shot fibers"; attribute :>> counterexample="Treating a captured frame as uniquely consumed after its first resume preserves an OCaml-style use case but breaks Scheme multi-shot behavior. A one-context pass cannot qualify failed multi-processor startup."; }
  part qLifetime : Question { attribute :>> id="Q-LIFETIME"; attribute :>> scope="independent-context-participant-worker-retirement"; attribute :>> prompt="What actually breaks the dependency on a terminating processor carrier?"; attribute :>> answer="Storage and call paths are separated, but cleanup_pstate still cleans context resources and allocator/logging still borrow a synchronous carrier; independent retirement is not implemented."; attribute :>> status="unresolved"; attribute :>> evidence="setup.c cleanup_pstate; mem.c worker carrier uses; runtime-role-realization.sysml RR-LIFETIME"; attribute :>> counterexample="Clearing carrier bytes leaves a VM array intact but does not prove that a thread or context can retire while users remain."; }
  part qFfi : Question { attribute :>> id="Q-FFI"; attribute :>> scope="foreign-roots-callbacks-and-cleanup-progress"; attribute :>> prompt="Can every RC/root writer, native callback and foreign destructor coexist with root freeze and worker completion without a wait cycle?"; attribute :>> answer="Per-participant RC scan origins are explicit; all-writer freeze, callback escape and destructor progress remain unqualified."; attribute :>> status="unresolved"; attribute :>> evidence="mem.c mark_rc and free_unmarked_still_objs; setup.c run/catcher/cleanup; native failure evidence RR-LIFETIME"; attribute :>> counterexample="GC waits for an owner callback while the owner waits for GC completion; a correct root array does not eliminate the cycle."; }
  part qFailure : Question { attribute :>> id="Q-FAILURE"; attribute :>> scope="closed-census-result-and-unknown-exit-custody"; attribute :>> prompt="Who retains roots and work after partial startup, failed join, unknown exit or a missing final acknowledgement?"; attribute :>> answer="Closed-round publication and readback are modeled; complete source/barrier/failure custody and actual native fault controls are open."; attribute :>> status="unresolved"; attribute :>> evidence="mem.c gc_round and final barrier; runtime_roles.qnt; setup.c resize cleanup; registered repair-9-12 evidence"; attribute :>> counterexample="A two-participant model assumes both members reach their barriers; a failed native participant can prevent that premise."; }
  part qCost : Question { attribute :>> id="Q-COST"; attribute :>> scope="structural-benefit-versus-runtime-cost"; attribute :>> prompt="Which work is removed now, what is added, and what would refute a net-benefit claim?"; attribute :>> answer="Old carrier fields, implicit root origin and collector queue selection are replaced. The recorded 64-slot VM grows 3080 bytes; root indirection and one final collective are added. No runtime speedup is measured."; attribute :>> status="answered-scoped"; attribute :>> evidence="matched parent/current sizeof; runtime-role-matrix.org; source commit diff; verification.json"; attribute :>> counterexample="A smaller carrier is not a smaller VM. If downstream retirement never occurs, extra indirection and coordination can exceed the value of the split."; }
  part qRetire : Question { attribute :>> id="Q-RETIRE"; attribute :>> scope="old-path-retirement-and-historical-evidence-separation"; attribute :>> prompt="Which old responsibilities actually disappear, and is any patch result being presented as refactoring acceptance?"; attribute :>> answer="Direct carrier root/memory fields and old visitor trio are removed; embedded C consumers change. Cleanup lifecycle and generated cohort are open. Bazel provides configuration; patch receipts remain separate historical observations with 8/12 unchanged."; attribute :>> status="answered-scoped"; attribute :>> evidence="negative old-field compile; source diff; runtime-role-realization.org; historical SMP observation"; attribute :>> counterexample="Importing patch candidates or labeling historical passes with the new source SHA does not retire ownership or establish native acceptance."; }

  part def Stage { attribute id : String; attribute status : String; attribute exitCriterion : String; }
  part design : Stage { attribute :>> id="semantic-contract"; attribute :>> status="scoped-design-and-open-premises"; attribute :>> exitCriterion="Source owners, semantic invariants, paper questions and dependency cuts explicitly recorded"; }
  part source : Stage { attribute :>> id="source-cut"; attribute :>> status="current-local-candidate"; attribute :>> exitCriterion="Representation and consumers replaced; exact tree bound; no fallback aliases"; }
  part projection : Stage { attribute :>> id="scoped-controls"; attribute :>> status="object-fixtures-and-local-models-checked"; attribute :>> exitCriterion="Recorded profile object controls and model negative controls; this does not replace bootstrap"; }
  part cohort : Stage { attribute :>> id="generated-cohort"; attribute :>> status="official-two-pass-bootstrap-complete"; attribute :>> exitCriterion="Regenerate and link matching compiler, embedded C, runtime and modules with existing Bazel profile"; }
  part semantics : Stage { attribute :>> id="semantic-lifecycle-acceptance"; attribute :>> status="one-context-map-gc-pass;host-p11-startup-fail;lifecycle-and-source-refinement-open"; attribute :>> exitCriterion="Real map multi-shot plus GC, RC roots, resize, FFI and failure custody controls; source-model bridge"; }
  part submit : Stage { attribute :>> id="commit-admission"; attribute :>> status="blocked"; attribute :>> exitCriterion="Five ASCENT gates ready for the exact candidate; no unresolved mandatory question or missing required test"; }
  part def Dependency { ref part sourceStage : Stage; ref part targetStage : Stage; }
  part d0 : Dependency { ref part :>> sourceStage=design; ref part :>> targetStage=source; }
  part d1 : Dependency { ref part :>> sourceStage=source; ref part :>> targetStage=projection; }
  part d2 : Dependency { ref part :>> sourceStage=projection; ref part :>> targetStage=cohort; }
  part d3 : Dependency { ref part :>> sourceStage=cohort; ref part :>> targetStage=semantics; }
  part d4 : Dependency { ref part :>> sourceStage=semantics; ref part :>> targetStage=submit; }
}
