/* Modern generated C physical preflight and caller-root research; no native admission. */
package GambitRestCapacityPreflight {
 private import ScalarValues::*;
 part def GrantState { attribute valid : Boolean; attribute fullRootView : Boolean; attribute actualHeapRange : Boolean; attribute actualStackRange : Boolean; attribute disjoint : Boolean; attribute metadataReserved : Boolean; attribute sameOwner : Boolean; attribute freshEpochLayoutSerial : Boolean; attribute inputStable : Boolean; attribute noncollectingGap : Boolean; }
 requirement def PhysicalGrantLaw { subject g : GrantState; require constraint { not g.valid or (g.fullRootView and g.actualHeapRange and g.actualStackRange and g.disjoint and g.metadataReserved and g.sameOwner and g.freshEpochLayoutSerial and g.inputStable and g.noncollectingGap) } }
 part def PreflightBound { attribute actual : Integer; attribute formal : Integer; attribute pairBody : Integer; attribute vectorBody : Integer; attribute wordBytes : Integer; attribute pairs : Integer=actual-formal+1; attribute pairWords : Integer=2+pairBody; attribute callerWords : Integer=pairs*pairWords+formal+vectorBody; attribute callerBytes : Integer=callerWords*wordBytes; attribute extraVsPostCons : Integer=pairWords; }
 ref part repairW4R0B1=GambitRestFrameParkCut::repairW4R0B1;
 part preflightW4R0B1 : PreflightBound { attribute :>> actual=4; attribute :>> formal=1; attribute :>> pairBody=1; attribute :>> vectorBody=1; attribute :>> wordBytes=4; }
 ref part repairW4R0B2=GambitRestFrameParkCut::repairW4R0B2;
 part preflightW4R0B2 : PreflightBound { attribute :>> actual=4; attribute :>> formal=1; attribute :>> pairBody=2; attribute :>> vectorBody=2; attribute :>> wordBytes=4; }
 ref part repairW4R1B1=GambitRestFrameParkCut::repairW4R1B1;
 part preflightW4R1B1 : PreflightBound { attribute :>> actual=4; attribute :>> formal=2; attribute :>> pairBody=1; attribute :>> vectorBody=1; attribute :>> wordBytes=4; }
 ref part repairW4R1B2=GambitRestFrameParkCut::repairW4R1B2;
 part preflightW4R1B2 : PreflightBound { attribute :>> actual=4; attribute :>> formal=2; attribute :>> pairBody=2; attribute :>> vectorBody=2; attribute :>> wordBytes=4; }
 ref part repairW8R0B1=GambitRestFrameParkCut::repairW8R0B1;
 part preflightW8R0B1 : PreflightBound { attribute :>> actual=4; attribute :>> formal=1; attribute :>> pairBody=1; attribute :>> vectorBody=1; attribute :>> wordBytes=8; }
 ref part repairW8R0B2=GambitRestFrameParkCut::repairW8R0B2;
 part preflightW8R0B2 : PreflightBound { attribute :>> actual=4; attribute :>> formal=1; attribute :>> pairBody=2; attribute :>> vectorBody=2; attribute :>> wordBytes=8; }
 ref part repairW8R1B1=GambitRestFrameParkCut::repairW8R1B1;
 part preflightW8R1B1 : PreflightBound { attribute :>> actual=4; attribute :>> formal=2; attribute :>> pairBody=1; attribute :>> vectorBody=1; attribute :>> wordBytes=8; }
 ref part repairW8R1B2=GambitRestFrameParkCut::repairW8R1B2;
 part preflightW8R1B2 : PreflightBound { attribute :>> actual=4; attribute :>> formal=2; attribute :>> pairBody=2; attribute :>> vectorBody=2; attribute :>> wordBytes=8; }
 part def FreshGeometry { attribute sectionWords : Integer=131072; attribute halfWords : Integer=65536; attribute linkWords : Integer=1; attribute markerWords : Integer=2; attribute usableWords : Integer=halfWords-linkWords-markerWords; attribute maxArgs : Integer=8192; attribute noHandlesMax : Integer=3*maxArgs+2; attribute handlesMax : Integer=4*maxArgs+3; attribute wordBytes : Integer; attribute sectionPayloadBytes : Integer=sectionWords*wordBytes; attribute noHandlesSlack : Integer=usableWords-noHandlesMax; attribute handlesSlack : Integer=usableWords-handlesMax; }
 part fresh32 : FreshGeometry { attribute :>> wordBytes=4; }
 part fresh64 : FreshGeometry { attribute :>> wordBytes=8; }
 ref part inheritedLayout32=GambitManagedMarkerLayout::layout32;
 ref part inheritedLayout64=GambitManagedMarkerLayout::layout64;
 part history : GambitAssuranceRouting::ModelNeed { ref part :>> owner=GambitRuntimeAssurance::work.component;
 attribute :>> obligationId="CP-H";
 attribute :>> kind="interleaving";
 attribute :>> subjectPath="models/gambit/rest_capacity_preflight.qnt";
 attribute :>> subjectScope="rest_capacity_preflight:33-named-histories;admitted;dynamic+native;direct-named;four-rest-args;epochs0and1;seed=17;each100x100";
 attribute :>> premise="One logical call after operand evaluation, stable complete CallInputView premise, actual four-arg no-handles heap budget14; finite arena offsets/stack budget12 are geometry examples, not actual caller FrameSpec; one reservation request, two ticket serials, old client reply, input/layout generations, one GC, initialized-prefix consumption and body-entry terminal; source/ABI/physical allocator and arbitrary callback/liveness proof remain open";
 }
 part induction : GambitAssuranceRouting::ModelNeed { ref part :>> owner=GambitRuntimeAssurance::work.component;
 attribute :>> obligationId="CP-I";
 attribute :>> kind="induction";
 attribute :>> subjectPath="models/gambit/lean/RestCapacityPreflight.lean";
 attribute :>> subjectScope="GambitSMP.RestCapacityPreflight:heapEnough;stackEnough;overlapRejected;shortHeapRejected;fourRestNoHandles;oneRequiredNoHandles;fourRestHandles;oneRequiredHandles;staleEpochRejected;staleArenaRejected;staleSerialRejected;changedInputRejected;grantPreserves;grantDoesNotAdvanceCursor;beginPreserves;writePreserves;finishPreserves;cancelPreserves;collectPreserves;liveTicketCannotCrossGc;partialFrameCannotCollect;cancelDoesNotRewindHp;collectDoesNotReevaluate;regrantUsesNewEpoch;regrantUsesNewArena;budgetPartition;completedBudgetHasNoUnused;knownDenyPreservesFullView;stepPreserves;tracePreserves";
 attribute :>> premise="30 conditional interval-fit/disjointness, caller-word arithmetic, stamp equality exclusions, initialized-prefix cursor and ticket/root lifecycle Step/Trace declarations; caller full-view and physical mapping are premises; no complete QNT/C allocator/generator/ABI simulation";
 }
 part safePoint : GambitAssuranceRouting::ModelNeed { ref part :>> owner=GambitRuntimeAssurance::work.component;
 attribute :>> obligationId="CP-SAFE";
 attribute :>> kind="source-refinement";
 attribute :>> subjectPath="models/gambit/lean/RestCapacityPreflight.lean";
 attribute :>> subjectScope="CP-SAFE:actual-source-refinement";
 attribute :>> premise="Create rooted CallInputView after operand evaluation; stage an already resolved target only at its allowed resolution point, or use target-independent arity envelope for late-bound global calls, without hoisting observable global reads; establish the view and before destructive expansion/argument relocation, R0 overwrite or native SFUN_ARG stores; dynamic apply cut before POP_ARGS2 and PUSH loop in app after wrapper splice, direct GVM cut before earliest destructive move and with all collecting block checks before final grant, native typed staging before raw outgoing stores and ___call; existing helper entry or late ___call is not a complete caller-view issuer";
 }
 part rootView : GambitAssuranceRouting::ModelNeed { ref part :>> owner=GambitRuntimeAssurance::work.component;
 attribute :>> obligationId="CP-ROOT";
 attribute :>> kind="source-refinement";
 attribute :>> subjectPath="models/gambit/lean/RestCapacityPreflight.lean";
 attribute :>> subjectScope="CP-ROOT:actual-source-refinement";
 attribute :>> premise="Preflight failure or cancellation retains exact logical target, ordered evaluated arguments/input spine, original continuation and native marker/code/result backing in collector-updateable roots; immutable/version-stable apply input can count then expand, general mutable input requires qualified single-read scan-safe staging, not rereading expressions/list after GC; no GC from existing unframed raw outgoing area; unknown source/input-root closure rejects managed profile";
 }
 part exclusion : GambitAssuranceRouting::ModelNeed { ref part :>> owner=GambitRuntimeAssurance::work.component;
 attribute :>> obligationId="CP-EXCLUDE";
 attribute :>> kind="source-refinement";
 attribute :>> subjectPath="models/gambit/lean/RestCapacityPreflight.lean";
 attribute :>> subjectScope="CP-EXCLUDE:actual-source-refinement";
 attribute :>> premise="Physical grant names one actual msection incarnation/semispace/layout and contiguous cursor window plus stack interval; exclude chunk link and end markers, require word alignment/checked offset arithmetic, heapHi<=stackLo when sharing, and no conflicting allocator/writer capability; logical global free space, fudge and compile-time reserved counters are not this proof; grant leaves hp unchanged so this profile needs no new sparse/uninitialized-gap scan contract; account initialized prefix plus unused reserved words once, and close/refund only unused capacity, never committed objects";
 }
 part receipt : GambitAssuranceRouting::ModelNeed { ref part :>> owner=GambitRuntimeAssurance::work.component;
 attribute :>> obligationId="CP-RECEIPT";
 attribute :>> kind="source-refinement";
 attribute :>> subjectPath="models/gambit/lean/RestCapacityPreflight.lean";
 attribute :>> subjectScope="CP-RECEIPT:actual-source-refinement";
 attribute :>> premise="Canonical noncollecting tryReserve on complete rooted input view is final allocator-layout effect before a no-GC/no-reentry shuffle/repair interval; reserve includes all rest pairs from first CONS plus fallback packet, frame/argument stack and metadata budgets; unused grant cancellation and construction entry share one arbitration; no intervening allocating helper/POLL or legacy heap_limit cursor migration while lease live; initialize objects then advance actual prefix hp, close lease at complete FrameReady before GC";
 }
 part resume : GambitAssuranceRouting::ModelNeed { ref part :>> owner=GambitRuntimeAssurance::work.component;
 attribute :>> obligationId="CP-RESUME";
 attribute :>> kind="source-refinement";
 attribute :>> subjectPath="models/gambit/lean/RestCapacityPreflight.lean";
 attribute :>> subjectScope="CP-RESUME:actual-source-refinement";
 attribute :>> premise="Unused grants must be canonically canceled before GC or allocator layout reassignment, active partial writer must finish full FrameReady and close lease first; flip/reset/reuse invalidates old epoch/layout/serial even at same address; after round/context/binding and root reload, rederive bounds from same stable logical call input and issue new ticket without reevaluating expressions; already completed rest packet needs fresh execution authority, not another rest construction grant";
 }
 part semantics : GambitAssuranceRouting::ModelNeed { ref part :>> owner=GambitRuntimeAssurance::work.component;
 attribute :>> obligationId="CP-SEMANTICS";
 attribute :>> kind="source-refinement";
 attribute :>> subjectPath="models/gambit/lean/RestCapacityPreflight.lean";
 attribute :>> subjectScope="CP-SEMANTICS:actual-source-refinement";
 attribute :>> premise="Known deny keeps complete root view and unchanged allocation cursor; lost grant ACK retains canonical unused grant and query rights, not a second reservation; unknown native allocator/assignment result retains arena transaction debt and cannot become deny/refund by timeout; failed/unknown cancel or entry outcome retains canonical responsibility; caller-input stability, ABI and origin profiles must be qualified, and original arity/error/tail/native return semantics are not replaced by invented pending success";
 }
 part order : GambitAssuranceRouting::ModelNeed { ref part :>> owner=GambitRuntimeAssurance::work.component;
 attribute :>> obligationId="CP-ORDER";
 attribute :>> kind="native-memory-order";
 attribute :>> subjectPath="models/gambit/lean/RestCapacityPreflight.lean";
 attribute :>> subjectScope="CP-ORDER:actual-C-memory-and-adapter-refinement";
 attribute :>> premise="Release-publish complete rooted call view before reservation; same atomic registry serializes grant/cancel/enter and GC/layout close; allocation owner and disjoint actual intervals validated before canonical grant, acquire consumer validates server status/epoch/layout/serial/input plus current cursor; last constructor store/initialized prefix and full frame precede lease close and GC admission; collector relocation precedes acquire root reload and new grant; old replies cannot mutate claimed writer permit, stale refund cannot retire new grant; actual C pointer arithmetic/atomics/lock order and helper effects remain open";
 }
 ref part priorSafe=GambitRestFrameParkCut::safePoint;
 ref part priorRoots=GambitRestFrameParkCut::rootView;
 ref part priorExclusion=GambitRestFrameParkCut::exclusion;
 ref part priorReceipt=GambitRestFrameParkCut::receipt;
 ref part priorResume=GambitRestFrameParkCut::resume;
 ref part priorOrder=GambitRestFrameParkCut::order;
 part dependency0 : GambitAssuranceRouting::NeedDependency { ref part :>> dependent=safePoint; ref part :>> prerequisite=history; }
 part dependency1 : GambitAssuranceRouting::NeedDependency { ref part :>> dependent=safePoint; ref part :>> prerequisite=induction; }
 part dependency2 : GambitAssuranceRouting::NeedDependency { ref part :>> dependent=safePoint; ref part :>> prerequisite=order; }
 part dependency3 : GambitAssuranceRouting::NeedDependency { ref part :>> dependent=rootView; ref part :>> prerequisite=history; }
 part dependency4 : GambitAssuranceRouting::NeedDependency { ref part :>> dependent=rootView; ref part :>> prerequisite=induction; }
 part dependency5 : GambitAssuranceRouting::NeedDependency { ref part :>> dependent=rootView; ref part :>> prerequisite=order; }
 part dependency6 : GambitAssuranceRouting::NeedDependency { ref part :>> dependent=exclusion; ref part :>> prerequisite=history; }
 part dependency7 : GambitAssuranceRouting::NeedDependency { ref part :>> dependent=exclusion; ref part :>> prerequisite=induction; }
 part dependency8 : GambitAssuranceRouting::NeedDependency { ref part :>> dependent=exclusion; ref part :>> prerequisite=order; }
 part dependency9 : GambitAssuranceRouting::NeedDependency { ref part :>> dependent=receipt; ref part :>> prerequisite=history; }
 part dependency10 : GambitAssuranceRouting::NeedDependency { ref part :>> dependent=receipt; ref part :>> prerequisite=induction; }
 part dependency11 : GambitAssuranceRouting::NeedDependency { ref part :>> dependent=receipt; ref part :>> prerequisite=order; }
 part dependency12 : GambitAssuranceRouting::NeedDependency { ref part :>> dependent=resume; ref part :>> prerequisite=history; }
 part dependency13 : GambitAssuranceRouting::NeedDependency { ref part :>> dependent=resume; ref part :>> prerequisite=induction; }
 part dependency14 : GambitAssuranceRouting::NeedDependency { ref part :>> dependent=resume; ref part :>> prerequisite=order; }
 part dependency15 : GambitAssuranceRouting::NeedDependency { ref part :>> dependent=semantics; ref part :>> prerequisite=history; }
 part dependency16 : GambitAssuranceRouting::NeedDependency { ref part :>> dependent=semantics; ref part :>> prerequisite=induction; }
 part dependency17 : GambitAssuranceRouting::NeedDependency { ref part :>> dependent=semantics; ref part :>> prerequisite=order; }
 part dependency18 : GambitAssuranceRouting::NeedDependency { ref part :>> dependent=order; ref part :>> prerequisite=history; }
 part dependency19 : GambitAssuranceRouting::NeedDependency { ref part :>> dependent=order; ref part :>> prerequisite=induction; }
 part dependency20 : GambitAssuranceRouting::NeedDependency { ref part :>> dependent=order; ref part :>> prerequisite=priorOrder; }
 part dependency21 : GambitAssuranceRouting::NeedDependency { ref part :>> dependent=safePoint; ref part :>> prerequisite=priorSafe; }
 part dependency22 : GambitAssuranceRouting::NeedDependency { ref part :>> dependent=safePoint; ref part :>> prerequisite=rootView; }
 part dependency23 : GambitAssuranceRouting::NeedDependency { ref part :>> dependent=rootView; ref part :>> prerequisite=priorRoots; }
 part dependency24 : GambitAssuranceRouting::NeedDependency { ref part :>> dependent=exclusion; ref part :>> prerequisite=priorExclusion; }
 part dependency25 : GambitAssuranceRouting::NeedDependency { ref part :>> dependent=receipt; ref part :>> prerequisite=priorReceipt; }
 part dependency26 : GambitAssuranceRouting::NeedDependency { ref part :>> dependent=receipt; ref part :>> prerequisite=rootView; }
 part dependency27 : GambitAssuranceRouting::NeedDependency { ref part :>> dependent=receipt; ref part :>> prerequisite=exclusion; }
 part dependency28 : GambitAssuranceRouting::NeedDependency { ref part :>> dependent=resume; ref part :>> prerequisite=priorResume; }
 part dependency29 : GambitAssuranceRouting::NeedDependency { ref part :>> dependent=resume; ref part :>> prerequisite=receipt; }
 part dependency30 : GambitAssuranceRouting::NeedDependency { ref part :>> dependent=semantics; ref part :>> prerequisite=safePoint; }
 part dependency31 : GambitAssuranceRouting::NeedDependency { ref part :>> dependent=semantics; ref part :>> prerequisite=exclusion; }
 part dependency32 : GambitAssuranceRouting::NeedDependency { ref part :>> dependent=resume; ref part :>> prerequisite=semantics; }
 part dependency33 : GambitAssuranceRouting::NeedDependency { ref part :>> dependent=rootView; ref part :>> prerequisite=priorExclusion; }
 part dependency34 : GambitAssuranceRouting::NeedDependency { ref part :>> dependent=safePoint; ref part :>> prerequisite=exclusion; }
 part safePointRoute : GambitHostRootsRefinement::Route { ref part :>> need=safePoint;
 attribute :>> sourceAnchors="lib/_kernel.scm:2989-3060;lib/_kernel.scm:3004-3024;lib/mem.h:63-65;gsc/_gvm.scm:466-473;gsc/_t-c-2.scm:1316-1390;gsc/_t-c-2.scm:1120-1143,1331-1390,2490-2499;tests/test5.ok:15750-15800;gsc/_ptree2.scm:2902-2930,3145-3187;include/gambit.h.in:10043-10071;lib/setup.c:3276-3360;lib/c_intf.c:6509-6564;include/gambit.h.in:10043-10064;tests/mix.scm:703-706,775-782;examples/tcltk/test.scm:9-33;examples/tcltk/tcltk.scm:221-228,673-674";
 attribute :>> patchAnchors="Design-only refactoring cut; no runtime patch or native test";
 attribute :>> projection="Create rooted CallInputView after operand evaluation; stage an already resolved target only at its allowed resolution point, or use target-independent arity envelope for late-bound global calls, without hoisting observable global reads; establish the view and before destructive expansion/argument relocation, R0 overwrite or native SFUN_ARG stores; dynamic apply cut before POP_ARGS2 and PUSH loop in app after wrapper splice, direct GVM cut before earliest destructive move and with all collecting block checks before final grant, native typed staging before raw outgoing stores and ___call; existing helper entry or late ___call is not a complete caller-view issuer";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part rootViewRoute : GambitHostRootsRefinement::Route { ref part :>> need=rootView;
 attribute :>> sourceAnchors="lib/_kernel.scm:2989-3060;lib/_kernel.scm:3004-3024;lib/mem.h:63-65;gsc/_ptree2.scm:2902-2930,3145-3187;include/gambit.h.in:10043-10071;lib/setup.c:3276-3360;lib/c_intf.c:6509-6564;include/gambit.h.in:10043-10064;lib/mem.c:7003-7085,4525-4567;lib/os_thread.c:697-710;tests/mix.scm:703-706,775-782;examples/tcltk/test.scm:9-33;examples/tcltk/tcltk.scm:221-228,673-674";
 attribute :>> patchAnchors="Design-only refactoring cut; no runtime patch or native test";
 attribute :>> projection="Preflight failure or cancellation retains exact logical target, ordered evaluated arguments/input spine, original continuation and native marker/code/result backing in collector-updateable roots; immutable/version-stable apply input can count then expand, general mutable input requires qualified single-read scan-safe staging, not rereading expressions/list after GC; no GC from existing unframed raw outgoing area; unknown source/input-root closure rejects managed profile";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part exclusionRoute : GambitHostRootsRefinement::Route { ref part :>> need=exclusion;
 attribute :>> sourceAnchors="lib/mem.c:3315-3325,3395-3407;lib/mem.h:63-71;lib/mem.c:3140-3174,3330-3356;lib/mem.c:3238-3270,3395-3407,3540-3623,3740-3800;lib/mem.c:7428-7505,4525-4567;lib/_kernel.scm:536-590;lib/mem.c:7115-7208,7380-7388;lib/mem.c:2194-2198,3413-3450;lib/mem.c:376-383,4928-4964;lib/setup.c:924-980;lib/os_thread.c:546-592";
 attribute :>> patchAnchors="Design-only refactoring cut; no runtime patch or native test";
 attribute :>> projection="Physical grant names one actual msection incarnation/semispace/layout and contiguous cursor window plus stack interval; exclude chunk link and end markers, require word alignment/checked offset arithmetic, heapHi<=stackLo when sharing, and no conflicting allocator/writer capability; logical global free space, fudge and compile-time reserved counters are not this proof; grant leaves hp unchanged so this profile needs no new sparse/uninitialized-gap scan contract; account initialized prefix plus unused reserved words once, and close/refund only unused capacity, never committed objects";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part receiptRoute : GambitHostRootsRefinement::Route { ref part :>> need=receipt;
 attribute :>> sourceAnchors="gsc/_gvm.scm:466-473;gsc/_t-c-2.scm:1316-1390;gsc/_t-c-2.scm:1120-1143,1331-1390,2490-2499;tests/test5.ok:15750-15800;lib/setup.c:3276-3360;lib/mem.c:3315-3325,3395-3407;lib/mem.h:63-71;lib/mem.c:3140-3174,3330-3356;lib/mem.c:3238-3270,3395-3407,3540-3623,3740-3800;lib/mem.c:7428-7505,4525-4567;lib/_kernel.scm:536-590;lib/mem.c:376-383,4928-4964;lib/setup.c:924-980;lib/os_thread.c:546-592";
 attribute :>> patchAnchors="Design-only refactoring cut; no runtime patch or native test";
 attribute :>> projection="Canonical noncollecting tryReserve on complete rooted input view is final allocator-layout effect before a no-GC/no-reentry shuffle/repair interval; reserve includes all rest pairs from first CONS plus fallback packet, frame/argument stack and metadata budgets; unused grant cancellation and construction entry share one arbitration; no intervening allocating helper/POLL or legacy heap_limit cursor migration while lease live; initialize objects then advance actual prefix hp, close lease at complete FrameReady before GC";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part resumeRoute : GambitHostRootsRefinement::Route { ref part :>> need=resume;
 attribute :>> sourceAnchors="lib/_kernel.scm:3004-3024;lib/mem.h:63-65;lib/mem.c:7428-7505,4525-4567;lib/_kernel.scm:536-590;lib/mem.c:7115-7208,7380-7388;lib/mem.c:2194-2198,3413-3450;lib/mem.c:7003-7085,4525-4567;lib/os_thread.c:697-710;tests/mix.scm:703-706,775-782;examples/tcltk/test.scm:9-33;examples/tcltk/tcltk.scm:221-228,673-674";
 attribute :>> patchAnchors="Design-only refactoring cut; no runtime patch or native test";
 attribute :>> projection="Unused grants must be canonically canceled before GC or allocator layout reassignment, active partial writer must finish full FrameReady and close lease first; flip/reset/reuse invalidates old epoch/layout/serial even at same address; after round/context/binding and root reload, rederive bounds from same stable logical call input and issue new ticket without reevaluating expressions; already completed rest packet needs fresh execution authority, not another rest construction grant";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part semanticsRoute : GambitHostRootsRefinement::Route { ref part :>> need=semantics;
 attribute :>> sourceAnchors="lib/_kernel.scm:2989-3060;lib/_kernel.scm:3004-3024;lib/mem.h:63-65;gsc/_ptree2.scm:2902-2930,3145-3187;include/gambit.h.in:10043-10071;lib/setup.c:3276-3360;lib/c_intf.c:6509-6564;include/gambit.h.in:10043-10064;lib/mem.c:7003-7085,4525-4567;lib/os_thread.c:697-710;lib/mem.c:376-383,4928-4964;lib/setup.c:924-980;lib/os_thread.c:546-592";
 attribute :>> patchAnchors="Design-only refactoring cut; no runtime patch or native test";
 attribute :>> projection="Known deny keeps complete root view and unchanged allocation cursor; lost grant ACK retains canonical unused grant and query rights, not a second reservation; unknown native allocator/assignment result retains arena transaction debt and cannot become deny/refund by timeout; failed/unknown cancel or entry outcome retains canonical responsibility; caller-input stability, ABI and origin profiles must be qualified, and original arity/error/tail/native return semantics are not replaced by invented pending success";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part orderRoute : GambitHostRootsRefinement::Route { ref part :>> need=order;
 attribute :>> sourceAnchors="lib/_kernel.scm:2989-3060;lib/_kernel.scm:3004-3024;lib/mem.h:63-65;gsc/_gvm.scm:466-473;gsc/_t-c-2.scm:1316-1390;gsc/_t-c-2.scm:1120-1143,1331-1390,2490-2499;tests/test5.ok:15750-15800;gsc/_ptree2.scm:2902-2930,3145-3187;include/gambit.h.in:10043-10071;lib/setup.c:3276-3360;lib/c_intf.c:6509-6564;include/gambit.h.in:10043-10064;lib/mem.c:3315-3325,3395-3407;lib/mem.h:63-71;lib/mem.c:3140-3174,3330-3356;lib/mem.c:3238-3270,3395-3407,3540-3623,3740-3800;lib/mem.c:7428-7505,4525-4567;lib/_kernel.scm:536-590;lib/mem.c:7115-7208,7380-7388;lib/mem.c:2194-2198,3413-3450;lib/mem.c:7003-7085,4525-4567;lib/os_thread.c:697-710;tests/mix.scm:703-706,775-782;examples/tcltk/test.scm:9-33;examples/tcltk/tcltk.scm:221-228,673-674;lib/mem.c:376-383,4928-4964;lib/setup.c:924-980;lib/os_thread.c:546-592";
 attribute :>> patchAnchors="Design-only refactoring cut; no runtime patch or native test";
 attribute :>> projection="Release-publish complete rooted call view before reservation; same atomic registry serializes grant/cancel/enter and GC/layout close; allocation owner and disjoint actual intervals validated before canonical grant, acquire consumer validates server status/epoch/layout/serial/input plus current cursor; last constructor store/initialized prefix and full frame precede lease close and GC admission; collector relocation precedes acquire root reload and new grant; old replies cannot mutate claimed writer permit, stale refund cannot retire new grant; actual C pointer arithmetic/atomics/lock order and helper effects remain open";
 attribute :>> failureCustodian="Source complete CallInputView retains evaluated target/args/native backing on failure; VM canonical reservation retains unused/active/unknown range duty after ACK loss; GC/layout reset waits settled arena transactions and active writer closure; stale tickets/replies cannot authorize replay, refund or new cursor use; completed packet is not reconstructed";
 attribute :>> status="source-and-native-order-refinement-open";
 }
 part def CallerRow { attribute callerId : String; attribute sourceAnchors : String; attribute actualChain : String; attribute hazard : String; attribute replacement : String; }
 part caller0 : CallerRow {
 attribute :>> callerId="dynamic-apply-wrapper";
 attribute :>> sourceAnchors="lib/_kernel.scm:2989-3060";
 attribute :>> actualChain="apply wrapper may splice own rest list before app; app immediately POP_ARGS2 then PUSH each car while walking cdr, finally jump target";
 attribute :>> hazard="Collecting reserve inserted inside raw PUSH loop would expose partial incoming argument frame; retrying wrapper can repeat mutation";
 attribute :>> replacement="New CallInputView cut at Scheme app boundary before inline C pops/expansion, after original evaluation/splice; logical inputs preserved";
 }
 part caller1 : CallerRow {
 attribute :>> callerId="apply-count-and-stability";
 attribute :>> sourceAnchors="lib/_kernel.scm:3004-3024;lib/mem.h:63-65";
 attribute :>> actualChain="Current app counts na while pushing, detects >MAX_NB_ARGS, removes pushed args then tail raises limit exception";
 attribute :>> hazard="No existing count-before-expand descriptor or stable snapshot; two-pass count can change mutable input observations";
 attribute :>> replacement="Stable input profile or scan-safe single-read CallArgPacket staging; retain target and spine/prefix roots; preserve invalid-input/error read order";
 }
 part caller2 : CallerRow {
 attribute :>> callerId="direct-gvm-jump";
 attribute :>> sourceAnchors="gsc/_gvm.scm:466-473;gsc/_t-c-2.scm:1316-1390";
 attribute :>> actualChain="Jump carries opnd/ret/nargs/poll/frame; emitter may overwrite R0 or spare destination, emit block checks, adjust stack then jump";
 attribute :>> hazard="Late-bound global target lookup also cannot be hoisted across collecting callbacks; reserve at final jump may already follow destructive operand moves";
 attribute :>> replacement="Scheme semantic completion emits pre-shuffle CallInputView and final grant/consume region; source producer placement proof remains open";
 }
 part caller3 : CallerRow {
 attribute :>> callerId="block-checks-and-specialization";
 attribute :>> sourceAnchors="gsc/_t-c-2.scm:1120-1143,1331-1390,2490-2499;tests/test5.ok:15750-15800";
 attribute :>> actualChain="Compile-time reserved counters drive checks; jump inline/direct dispatch may bypass generic rest entry";
 attribute :>> hazard="Compiler reserved count and passing POLL do not reserve an exclusive physical interval; late poll can invalidate grant";
 attribute :>> replacement="Run required collecting checks with complete view first, then final noncollecting grant; specialize exact body/argument contract instead of blanket rest charge";
 }
 part caller4 : CallerRow {
 attribute :>> callerId="native-conversion-producer";
 attribute :>> sourceAnchors="gsc/_ptree2.scm:2902-2930,3145-3187;include/gambit.h.in:10043-10071";
 attribute :>> actualChain="c-make-function converts parameters, generated make-body emits SFUN_ARG stores then SFUN_CALL; BEGIN allocates marker earlier";
 attribute :>> hazard="Converted SCMOBJ locals and raw outgoing stores are not automatically a complete GC view before ___call";
 attribute :>> replacement="Typed NativeCallInputView/root frame before raw stores; preserve conversion order, error/result ABI and same invocation leases";
 }
 part caller5 : CallerRow {
 attribute :>> callerId="native-call-frame";
 attribute :>> sourceAnchors="lib/setup.c:3276-3360";
 attribute :>> actualChain="___call assumes C caller already placed args above fp, builds return marker frame, pops regs and sets target";
 attribute :>> hazard="Collecting capacity request inside ___call before reconstructing rooted outgoing inputs is not automatically safe";
 attribute :>> replacement="Preflight at staged native caller; keep return-to-C frame construction noncollecting under exact stack lease";
 }
 part caller6 : CallerRow {
 attribute :>> callerId="marker-input-root-gap";
 attribute :>> sourceAnchors="lib/c_intf.c:6509-6564;include/gambit.h.in:10043-10064";
 attribute :>> actualChain="Marker allocator uses make_vector before copying proc, source TODO for protecting input; SFUN conversion errors may call Scheme";
 attribute :>> hazard="Native staging cannot claim safe preflight if marker/proc roots already unprotected";
 attribute :>> replacement="Root target before marker allocation, all-domain handles and complete ancestor native root/exit plan; inherited gap stays open";
 }
 part caller7 : CallerRow {
 attribute :>> callerId="heap-msection-data-range";
 attribute :>> sourceAnchors="lib/mem.c:3315-3325,3395-3407;lib/mem.h:63-71";
 attribute :>> actualChain="set_heap_msection selects tospace half; prepare leaves two end marker words, writes first link word and starts data chunk";
 attribute :>> hazard="Raw half-section size overcounts client data; allocating a logical window must not skip uninitialized prefix";
 attribute :>> replacement="Grant current hp-to-dataHi offsets after metadata; fresh separate half has 65533 candidate data words by source arithmetic only";
 }
 part caller8 : CallerRow {
 attribute :>> callerId="shared-stack-heap-layout";
 attribute :>> sourceAnchors="lib/mem.c:3140-3174,3330-3356";
 attribute :>> actualChain="Shared msection changes both limits with fudge and 1/4-versus-3/4 split";
 attribute :>> hazard="Independent heap/stack scalar capacity can double-promise intersecting bytes";
 attribute :>> replacement="Grant actual disjoint intervals and guard budget under one layout incarnation, or use separately owned sections";
 }
 part caller9 : CallerRow {
 attribute :>> callerId="chunk-lifecycle";
 attribute :>> sourceAnchors="lib/mem.c:3238-3270,3395-3407,3540-3623,3740-3800";
 attribute :>> actualChain="Current scanner/allocation tracks chunk start, markers and initialized allocation prefix";
 attribute :>> hazard="Publishing an uninitialized gap as a scannable copying chunk is unqualified; collector-copy chunk limits and mutator data bounds are different roles";
 attribute :>> replacement="Cursor-window lease leaves hp unchanged; write complete objects and advance only initialized prefix; chunk transitions must join plan or be excluded";
 }
 part caller10 : CallerRow {
 attribute :>> callerId="heap-limit-can-reassign";
 attribute :>> sourceAnchors="lib/mem.c:7428-7505,4525-4567;lib/_kernel.scm:536-590";
 attribute :>> actualChain="heap_limit can take free msection or get next section, prepare new hp/limits, or signal GC need";
 attribute :>> hazard="A ticket for prior hp/layout does not remain valid across this helper even without GC";
 attribute :>> replacement="Replace admitted repair path with lease-local noncollecting budget/need-GC check, close lease at full frame before normal collector";
 }
 part caller11 : CallerRow {
 attribute :>> callerId="stack-limit-migration";
 attribute :>> sourceAnchors="lib/mem.c:7115-7208,7380-7388";
 attribute :>> actualChain="stack_limit may allocate/reuse msection and migrate frames/stack break; old section can join free list";
 attribute :>> hazard="Same GC epoch does not imply unchanged stack interval/cursor or live pointer locations";
 attribute :>> replacement="Layout generation changes invalidate unused grants; qualify stack-demand FrameSpec and prohibit migration inside leased shuffle";
 }
 part caller12 : CallerRow {
 attribute :>> callerId="gc-flip-and-reset";
 attribute :>> sourceAnchors="lib/mem.c:2194-2198,3413-3450";
 attribute :>> actualChain="setup_stack_heap_vmstate flips tospace offset, resets per-PSTATE free list/section/cursors/chunk queues";
 attribute :>> hazard="Old capacity receipt cannot survive semispace flip/reset; addresses can later repeat";
 attribute :>> replacement="Cancel unused grants and settle active constructors before GC, use epoch+layout+serial and reissue against new actual intervals";
 }
 part caller13 : CallerRow {
 attribute :>> callerId="round-context-reload";
 attribute :>> sourceAnchors="lib/mem.c:7003-7085,4525-4567;lib/os_thread.c:697-710";
 attribute :>> actualChain="GC phases/resize/fudge then prepare context, with notification before preparation; TLS binding is separate";
 attribute :>> hazard="GC interrupt/result alone does not authorize new raw cursor use or stale root access";
 attribute :>> replacement="Whole-round result, exact owner/context binding and relocated CallInputView handle reload before new grant or completed packet resume";
 }
 part caller14 : CallerRow {
 attribute :>> callerId="actual-rest-consumers";
 attribute :>> sourceAnchors="tests/mix.scm:703-706,775-782;examples/tcltk/test.scm:9-33;examples/tcltk/tcltk.scm:221-228,673-674";
 attribute :>> actualChain="f3 generic rest source and real Tcl setter -> variadic tcl caller provide zero/one-required four-arg shapes";
 attribute :>> hazard="Direct specialization/generic slow execution and physical pressure are conditional; no native run receipt";
 attribute :>> replacement="Front-load all four/three pair costs plus fallback packet; retain existing single native invocation and nargs=-1 completed-packet resume";
 }
 part caller15 : CallerRow {
 attribute :>> callerId="locks-ownership-and-cleanup";
 attribute :>> sourceAnchors="lib/mem.c:376-383,4928-4964;lib/setup.c:924-980;lib/os_thread.c:546-592";
 attribute :>> actualChain="alloc_mem_lock protects selected section operations; PSTATE cleanup frees resources before later join result handling";
 attribute :>> hazard="Allocation lock is not a complete per-call ticket/GC exclusion protocol; unknown stop cannot retire active writer";
 attribute :>> replacement="VM canonical reservation records, no GC-critical lock held while waiting, known stop/final-effect evidence before range reclamation";
 }
 part def CostRow { attribute capability : String; attribute removedWork : String; attribute bound : String; attribute addedCost : String; attribute condition : String; }
 part cost0 : CostRow {
 attribute :>> capability="Caller versus post-CONS budget";
 attribute :>> removedWork="Budget from before first destructive allocation";
 attribute :>> bound="Hcaller=(na-np+1)*(2+PAIR_BODY)+np+VECTOR_BODY; four args no handles:14/12 words";
 attribute :>> addedCost="Stack-demand FrameSpec, metadata/root budget and physical data interval";
 attribute :>> condition="Prior 11/9-word repair examples start after checked CONS; difference is one pair, not new total allocation";
 }
 part cost1 : CostRow {
 attribute :>> capability="Fresh-section geometry";
 attribute :>> removedWork="Demonstrate a feasible heap-only envelope";
 attribute :>> bound="Half65536 minus first-link1 and end-markers2 =65533 words; max legal rest envelope24578/32771 for no-handles/handles";
 attribute :>> addedCost="Exclusive data ownership, actual layout and separate/nonoverlapping stack reserve";
 attribute :>> condition="Arithmetic does not prove allocation success, arbitrary current section slack, C ABI or caller stack bound";
 }
 part cost2 : CostRow {
 attribute :>> capability="Reservation representation";
 attribute :>> removedWork="Avoid uninitialized holes in current prefix scanner";
 attribute :>> bound="Grant adds0 hp advancement; consuming each initialized pair adds its actual words";
 attribute :>> addedCost="Canonical cursor-window lease and no intervening allocating/reentrant helper";
 attribute :>> condition="Cannot keep old heap_limit/msection migration inside admitted leased region without explicit continuation of layout contract";
 }
 part cost3 : CostRow {
 attribute :>> capability="Dynamic apply work";
 attribute :>> removedWork="Preserve evaluated target/input across failed preflight and GC";
 attribute :>> bound="Stable two-pass input adds an O(n) count pass; typed staging uses O(n) slots and O(n) read/copy work";
 attribute :>> addedCost="Version/stability proof or scan-safe staged-prefix root descriptor";
 attribute :>> condition="Neither route proves a baseline CPU saving; raw shared mutable input needs separate read-order refinement";
 }
 part cost4 : CostRow {
 attribute :>> capability="Direct calls";
 attribute :>> removedWork="Keep precise per-call or specialized demand";
 attribute :>> bound="Known na/target bound is O(1); late-bound target uses conservative arity envelope without early global read; specialized body paths differ";
 attribute :>> addedCost="Pre-shuffle root materialization and collecting checks before grant";
 attribute :>> condition="No blanket charge to calls that bypass rest construction; current exact emission placement proof remains open";
 }
 part cost5 : CostRow {
 attribute :>> capability="Native ingress";
 attribute :>> removedWork="Make conversion failure and retry root-safe";
 attribute :>> bound="One native invocation remains1; preflight query/retry adds0 native invocation";
 attribute :>> addedCost="Rooted conversion staging, marker/code/input/result leases and native stack bound";
 attribute :>> condition="Late ___call insertion is insufficient; marker-root TODO and loaded native origins remain open";
 }
 part cost6 : CostRow {
 attribute :>> capability="GC and ticket expiry";
 attribute :>> removedWork="Prevent stale same-address permission after collection or layout reset";
 attribute :>> bound="Unused ticket cancel before GC; new epoch/layout/serial on retry; no operand reevaluation";
 attribute :>> addedCost="Canonical cancel/enter race, context/root reload and protected result lookup";
 attribute :>> condition="Active partial work must reach full frame; completed rest packet needs reentry authority, not rest reconstruction";
 }
 part cost7 : CostRow {
 attribute :>> capability="Failure and unknown outcomes";
 attribute :>> removedWork="Known denial keeps full root view and original cursor";
 attribute :>> bound="No allocation cursor write on deny; missing ACK query invokes no native operation";
 attribute :>> addedCost="Pending arena transaction and root/native metadata retained until known outcome";
 attribute :>> condition="Unknown native effect/entry/stop cannot be converted to failure or refund by timeout; may block GC";
 }
 part cost8 : CostRow {
 attribute :>> capability="Lease-local check work";
 attribute :>> removedWork="Replace admitted per-CONS limit checks with whole-window validation";
 attribute :>> bound="Current checked prefix j in [1,k] does j comparisons; candidate validates once then honors pending GC at full-frame boundary";
 attribute :>> addedCost="Reservation, root materialization, completion pressure poll and used+unused budget ledger";
 attribute :>> condition="Logical comparison reduction only; staging/atomic/retention costs may exceed savings, so no CPU speedup is proved";
 }
 part cost9 : CostRow {
 attribute :>> capability="Peak memory";
 attribute :>> removedWork="Count real backing and staging overlap";
 attribute :>> bound="Peak=max_t(H+P+N+Q); a new full msection payload=131072*wordBytes, 1MiB at8-byte words";
 attribute :>> addedCost="Potential staged inputs, retained roots/native frames and separately required stack sections";
 attribute :>> condition="Fresh assignment from existing pool is not new payload/RSS; allocator may batch-grow; no whole-round peak reduction proved";
 }
 part cost10 : CostRow {
 attribute :>> capability="Retirement";
 attribute :>> removedWork="Replace implicit current-limit and raw-call root responsibilities";
 attribute :>> bound="0 production paths retired; no duplicated expression evaluation or rest construction due to retry";
 attribute :>> addedCost="Scheme-generated CallInputSpec/FrameSpec plus modern C capacity/root/ticket service";
 attribute :>> condition="Retire admitted lease-internal raw heap_limit/POLL and unrooted native stores only after caller/effect/source/order qualification";
 }
 part cost11 : CostRow {
 attribute :>> capability="Modern C mainline";
 attribute :>> removedWork="Share allocator, root and caller plans across Scheme/native entry";
 attribute :>> bound="No Zig-only removal of necessary correctness work demonstrated";
 attribute :>> addedCost="Both require same physical interval, GC epoch, native-root, staging and exception contracts";
 attribute :>> condition="Positive CPU/peak net benefit needs actual removed baseline work/overlap to exceed new checks/retention; not established by this design alone";
 }
 part def DiagramNode { attribute nodeId : String; attribute labelText : String; }
 part def DiagramEdge { ref producer : DiagramNode; ref consumer : DiagramNode; attribute labelText : String; }
 part node0 : DiagramNode { attribute :>> nodeId="input"; attribute :>> labelText="Evaluated target + arguments\\ncomplete caller / native root view"; }
 part node1 : DiagramNode { attribute :>> nodeId="plan"; attribute :>> labelText="CallInputSpec + exact rest / stack demand\\nno destructive argument movement"; }
 part node2 : DiagramNode { attribute :>> nodeId="checks"; attribute :>> labelText="All collecting checks while rooted\\nfreeze/reload logical inputs"; }
 part node3 : DiagramNode { attribute :>> nodeId="grant"; attribute :>> labelText="Canonical noncollecting tryReserve\\nactual heap/stack cursor windows"; }
 part node4 : DiagramNode { attribute :>> nodeId="deny"; attribute :>> labelText="Known deny / unresolved result\\nkeep full roots; no argument replay"; }
 part node5 : DiagramNode { attribute :>> nodeId="consume"; attribute :>> labelText="Atomic unused-ticket -> active writer\\nvalidate epoch/layout/serial/input/cursor"; }
 part node6 : DiagramNode { attribute :>> nodeId="build"; attribute :>> labelText="No-GC shuffle / full rest repair\\nadvance initialized prefix only"; }
 part node7 : DiagramNode { attribute :>> nodeId="frame"; attribute :>> labelText="Complete mapped FrameReady\\nclose active construction lease"; }
 part node8 : DiagramNode { attribute :>> nodeId="gc"; attribute :>> labelText="Cancel unused grants / settle active work\\nGC flips layouts and root values"; }
 part node9 : DiagramNode { attribute :>> nodeId="reissue"; attribute :>> labelText="Round/context/binding/root reload\\nnew ticket for unbuilt call only"; }
 part node10 : DiagramNode { attribute :>> nodeId="body"; attribute :>> labelText="Completed packet resumes same call\\nfresh execution authority, no new rest ticket"; }
 part node11 : DiagramNode { attribute :>> nodeId="custody"; attribute :>> labelText="VM ticket + source/native/root custody\\nunknown never means free"; }
 part node12 : DiagramNode { attribute :>> nodeId="formal"; attribute :>> labelText="SysML -> ASCENT -> QNT / Lean\\nphysical C/source/ABI gaps open"; }
 part edge0 : DiagramEdge { ref :>> producer=node0; ref :>> consumer=node1; attribute :>> labelText="after evaluation, before POP/shuffle"; }
 part edge1 : DiagramEdge { ref :>> producer=node1; ref :>> consumer=node2; attribute :>> labelText="complete roots retained"; }
 part edge2 : DiagramEdge { ref :>> producer=node2; ref :>> consumer=node3; attribute :>> labelText="final noncollecting layout effect"; }
 part edge3 : DiagramEdge { ref :>> producer=node3; ref :>> consumer=node5; attribute :>> labelText="known unused grant, one winner"; }
 part edge4 : DiagramEdge { ref :>> producer=node3; ref :>> consumer=node4; attribute :>> labelText="failure or response uncertainty"; }
 part edge5 : DiagramEdge { ref :>> producer=node5; ref :>> consumer=node6; attribute :>> labelText="close cannot revoke active writer"; }
 part edge6 : DiagramEdge { ref :>> producer=node6; ref :>> consumer=node7; attribute :>> labelText="all fields and root map complete"; }
 part edge7 : DiagramEdge { ref :>> producer=node7; ref :>> consumer=node8; attribute :>> labelText="lease closed before collector"; }
 part edge8 : DiagramEdge { ref :>> producer=node4; ref :>> consumer=node8; attribute :>> labelText="only settled arena result and full roots"; }
 part edge9 : DiagramEdge { ref :>> producer=node8; ref :>> consumer=node9; attribute :>> labelText="old addresses and tickets invalid"; }
 part edge10 : DiagramEdge { ref :>> producer=node9; ref :>> consumer=node3; attribute :>> labelText="same logical inputs, no reevaluation"; }
 part edge11 : DiagramEdge { ref :>> producer=node7; ref :>> consumer=node10; attribute :>> labelText="no GC path still needs body contract"; }
 part edge12 : DiagramEdge { ref :>> producer=node9; ref :>> consumer=node10; attribute :>> labelText="already built packet, no reconstruction"; }
 part edge13 : DiagramEdge { ref :>> producer=node0; ref :>> consumer=node11; attribute :>> labelText="reserve input/native/control lifetime"; }
 part edge14 : DiagramEdge { ref :>> producer=node11; ref :>> consumer=node3; attribute :>> labelText="canonical ticket identity and interval owner"; }
 part edge15 : DiagramEdge { ref :>> producer=node11; ref :>> consumer=node4; attribute :>> labelText="lost ACK -> query, retain debt"; }
 part edge16 : DiagramEdge { ref :>> producer=node12; ref :>> consumer=node5; attribute :>> labelText="atomic cancel/enter and interval proof"; }
 part edge17 : DiagramEdge { ref :>> producer=node12; ref :>> consumer=node9; attribute :>> labelText="stamp expiry and source boundaries"; }
}
