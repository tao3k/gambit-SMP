/* Whole-architecture decisions extend existing canonical module owners. No runtime adoption asserted. */
package GambitModernizationTarget { private import ScalarValues::*;
part def ArchitectureDecision { ref part owner:GambitRuntimeComposition::BlueprintModule; ref part interleaving:GambitAssuranceRouting::ModelNeed; ref part induction:GambitAssuranceRouting::ModelNeed; attribute decisionId:String; attribute target:String; attribute lesson:String; attribute replacement:String; attribute retirement:String; attribute sourceAnchors:String; attribute obligation:String; attribute benefit:String; attribute addedCost:String; }
part need0Q:GambitAssuranceRouting::ModelNeed { ref part :>> owner=GambitRuntimeAssurance::roots.component; attribute :>> obligationId="MW-SEMANTIC-Q"; attribute :>> kind="interleaving"; attribute :>> subjectPath="models/gambit/ffi_gc_frame_protocol.qnt"; attribute :>> subjectScope="modernization-target:semantic:whole-source-composition-open"; attribute :>> premise="Existing fragment only; Prove complete encoding, decoding, root coverage, tail/non-tail and continuation origins; existing fragments are insufficient; no complete-source composition receipt in this scope"; }
part need0L:GambitAssuranceRouting::ModelNeed { ref part :>> owner=GambitRuntimeAssurance::roots.component; attribute :>> obligationId="MW-SEMANTIC-L"; attribute :>> kind="induction"; attribute :>> subjectPath="models/gambit/lean/SavedStackRootClosure.lean"; attribute :>> subjectScope="modernization-target:semantic:whole-source-composition-open"; attribute :>> premise="Existing fragment only; Prove complete encoding, decoding, root coverage, tail/non-tail and continuation origins; existing fragments are insufficient; no complete-source composition receipt in this scope"; }
part decision0:ArchitectureDecision { ref part :>> owner=GambitRuntimeComposition::blueprintModule0; ref part :>> interleaving=need0Q; ref part :>> induction=need0L; attribute :>> decisionId="semantic"; attribute :>> target="GVM-to-native semantic contract compiler"; attribute :>> lesson="PVM paper: front/back cooperation exposes representation, calls and target knowledge"; attribute :>> replacement="Scheme owns FrameSpec/PointId/ModuleSpec/EffectSpec/AllocationSpec; generate typed C functions/tables and explicit ABI"; attribute :>> retirement="Retire duplicated semantic macro emission and layout decisions after all generators/runtime consumers use the schema"; attribute :>> sourceAnchors="vendor/gambit/gsc/_back.scm;gsc/_t-c-1.scm;gsc/_ptree2.scm;include/gambit.h.in"; attribute :>> obligation="Prove complete encoding, decoding, root coverage, tail/non-tail and continuation origins; existing fragments are insufficient"; attribute :>> benefit="Count repeated preprocessing/compile bytes and semantic decisions eliminated; no new language runtime required"; attribute :>> addedCost="Schema/compiler bootstrap cost and an ABI rebuild; simple C portability macros may remain"; }
part need1Q:GambitAssuranceRouting::ModelNeed { ref part :>> owner=GambitRuntimeAssurance::roots.component; attribute :>> obligationId="MW-DOMAIN-Q"; attribute :>> kind="interleaving"; attribute :>> subjectPath="models/gambit/scheduler_gc_root_cohort_composition.qnt"; attribute :>> subjectScope="modernization-target:domain:whole-source-composition-open"; attribute :>> premise="Existing fragment only; Compose safepoint progress, membership closure, root leases and task termination; exclude collector/owner wait cycles; no complete-source composition receipt in this scope"; }
part need1L:GambitAssuranceRouting::ModelNeed { ref part :>> owner=GambitRuntimeAssurance::roots.component; attribute :>> obligationId="MW-DOMAIN-L"; attribute :>> kind="induction"; attribute :>> subjectPath="models/gambit/lean/WorkAccounting.lean"; attribute :>> subjectScope="modernization-target:domain:whole-source-composition-open"; attribute :>> premise="Existing fragment only; Compose safepoint progress, membership closure, root leases and task termination; exclude collector/owner wait cycles; no complete-source composition receipt in this scope"; }
part decision1:ArchitectureDecision { ref part :>> owner=GambitRuntimeComposition::blueprintModule2; ref part :>> interleaving=need1Q; ref part :>> induction=need1L; attribute :>> decisionId="domain"; attribute :>> target="Execution, participation and collection carriers separated"; attribute :>> lesson="OCaml parallelism paper and domain/backup-thread source: GC participation is an explicit protocol"; attribute :>> replacement="VM owns membership/heap epochs; ExecutionContext owns Scheme state; GCParticipant freezes roots; CollectorWorkContext owns scan work independent of OS/PSTATE lifetime"; attribute :>> retirement="Retire implicit PSTATE ownership of collector queues, allocation state and cleanup after exact producer/consumer/lifetime replacement"; attribute :>> sourceAnchors="vendor/gambit/lib/mem.c:277-318;lib/setup.c:resize;vendor/ocaml/runtime/domain.c"; attribute :>> obligation="Compose safepoint progress, membership closure, root leases and task termination; exclude collector/owner wait cycles"; attribute :>> benefit="Reduce owner-dependent GC callbacks and repeated membership reconstruction; measure contention and pause population"; attribute :>> addedCost="Root snapshots, epoch bookkeeping and scheduler/worker coordination; no universal dead-thread recovery"; }
part need2Q:GambitAssuranceRouting::ModelNeed { ref part :>> owner=GambitRuntimeAssurance::roots.component; attribute :>> obligationId="MW-HEAP-Q"; attribute :>> kind="interleaving"; attribute :>> subjectPath="models/gambit/generational_barrier.qnt"; attribute :>> subjectScope="modernization-target:heap:whole-source-composition-open"; attribute :>> premise="Existing fragment only; Prove no omitted mature-to-young edge, root-complete minor cut, promotion failure custody and capacity conservation; no complete-source composition receipt in this scope"; }
part need2L:GambitAssuranceRouting::ModelNeed { ref part :>> owner=GambitRuntimeAssurance::roots.component; attribute :>> obligationId="MW-HEAP-L"; attribute :>> kind="induction"; attribute :>> subjectPath="models/gambit/lean/GenerationalBarrier.lean"; attribute :>> subjectScope="modernization-target:heap:whole-source-composition-open"; attribute :>> premise="Existing fragment only; Prove no omitted mature-to-young edge, root-complete minor cut, promotion failure custody and capacity conservation; no complete-source composition receipt in this scope"; }
part decision2:ArchitectureDecision { ref part :>> owner=GambitRuntimeComposition::blueprintModule4; ref part :>> interleaving=need2Q; ref part :>> induction=need2L; attribute :>> decisionId="heap"; attribute :>> target="Generational heap with precise publication and mutation"; attribute :>> lesson="OCaml paper compares concurrent minor/read-barrier design with parallel STW minor; learn the tradeoff"; attribute :>> replacement="Context-local nurseries, shared mature heap, parallel STW minor, generated remembered writes and explicit promotion budget; isolate major algorithm behind heap/phase contract"; attribute :>> retirement="Retire full mature-graph minor scanning only after all roots, continuation/denv/FFI writers and sparse/promotion layouts close"; attribute :>> sourceAnchors="vendor/gambit/lib/mem.c;vendor/ocaml/runtime/minor_gc.c:886-934"; attribute :>> obligation="Prove no omitted mature-to-young edge, root-complete minor cut, promotion failure custody and capacity conservation"; attribute :>> benefit="Minor work = young live + remembered edges + roots; savings require avoiding mature scan beyond barrier/promotion overhead"; attribute :>> addedCost="Remembered sets, barriers, survival/promotion copies and reserve peaks; mature moving/nonmoving and concurrent major remain open choices"; }
part need3Q:GambitAssuranceRouting::ModelNeed { ref part :>> owner=GambitRuntimeAssurance::roots.component; attribute :>> obligationId="MW-CONTROL-Q"; attribute :>> kind="interleaving"; attribute :>> subjectPath="models/gambit/captured_heap_frame_operations.qnt"; attribute :>> subjectScope="modernization-target:control:whole-source-composition-open"; attribute :>> premise="Existing fragment only; Capture map continuation, collect/promote, mutate legal frames/denv and resume more than once with same observable semantics; no complete-source composition receipt in this scope"; }
part need3L:GambitAssuranceRouting::ModelNeed { ref part :>> owner=GambitRuntimeAssurance::roots.component; attribute :>> obligationId="MW-CONTROL-L"; attribute :>> kind="induction"; attribute :>> subjectPath="models/gambit/lean/SavedStackRootClosure.lean"; attribute :>> subjectScope="modernization-target:control:whole-source-composition-open"; attribute :>> premise="Existing fragment only; Capture map continuation, collect/promote, mutate legal frames/denv and resume more than once with same observable semantics; no complete-source composition receipt in this scope"; }
part decision3:ArchitectureDecision { ref part :>> owner=GambitRuntimeComposition::blueprintModule5; ref part :>> interleaving=need3Q; ref part :>> induction=need3L; attribute :>> decisionId="control"; attribute :>> target="Continuation-centric control and scheduler boundary"; attribute :>> lesson="Effects paper makes suspension/resumption a runtime concern; Gambit already has stronger multi-shot semantics"; attribute :>> replacement="One precise frame/root format for running, captured and resumed computation; persistent or copy-on-write captured frames; one-shot optimization only with proven use"; attribute :>> retirement="Retire carrier-local C control assumptions after repeated resumption, dynamic-wind, exceptions and supported FFI escapes are preserved"; attribute :>> sourceAnchors="vendor/gambit/lib/_kernel.scm;lib/_thread.scm;vendor/ocaml/runtime/fiber.c"; attribute :>> obligation="Capture map continuation, collect/promote, mutate legal frames/denv and resume more than once with same observable semantics"; attribute :>> benefit="Reuse captured immutable graph across minor GC only with complete mutation evidence; direct-style scheduling without rewriting Scheme"; attribute :>> addedCost="Frame ownership/COW bookkeeping, remembered mutations and handler/FFI boundary cost; do not impose one-shot restriction"; }
part need4Q:GambitAssuranceRouting::ModelNeed { ref part :>> owner=GambitRuntimeAssurance::roots.component; attribute :>> obligationId="MW-FOREIGN-Q"; attribute :>> kind="interleaving"; attribute :>> subjectPath="models/gambit/native_entry_close_cleanup.qnt"; attribute :>> subjectScope="modernization-target:foreign:whole-source-composition-open"; attribute :>> premise="Existing fragment only; Compose nested callback, exact last use, late result, exception/continuation escape and release descendants with GC progress; no complete-source composition receipt in this scope"; }
part need4L:GambitAssuranceRouting::ModelNeed { ref part :>> owner=GambitRuntimeAssurance::roots.component; attribute :>> obligationId="MW-FOREIGN-L"; attribute :>> kind="induction"; attribute :>> subjectPath="models/gambit/lean/NativeEntryCloseCleanup.lean"; attribute :>> subjectScope="modernization-target:foreign:whole-source-composition-open"; attribute :>> premise="Existing fragment only; Compose nested callback, exact last use, late result, exception/continuation escape and release descendants with GC progress; no complete-source composition receipt in this scope"; }
part decision4:ArchitectureDecision { ref part :>> owner=GambitRuntimeComposition::blueprintModule6; ref part :>> interleaving=need4Q; ref part :>> induction=need4L; attribute :>> decisionId="foreign"; attribute :>> target="Root-safe native activation and effect/resource ownership"; attribute :>> lesson="OCaml source separates blocking leave/reenter and GC service; Gambit needs its own continuation-aware contract"; attribute :>> replacement="RootRegistry before allocation; generated native entry plans; park/freeze/reload; VM-owned outcomes and effect-classified release tasks outside collector critical phase"; attribute :>> retirement="Retire raw marker-only lifetime, ad hoc root choreography and inline arbitrary release only after whole real caller coverage"; attribute :>> sourceAnchors="vendor/gambit/lib/c_intf.c;lib/setup.c:call/run;lib/mem.c:foreign cleanup;vendor/ocaml/runtime/signals.c:147-205"; attribute :>> obligation="Compose nested callback, exact last use, late result, exception/continuation escape and release descendants with GC progress"; attribute :>> benefit="Remove duplicated per-entry ownership logic and avoid waiting for blocked owner in collector phase"; attribute :>> addedCost="Stable roots, task custody, resource affinity and root-aware resumption; unknown unregistered writers still require refusal/retention"; }
part need5Q:GambitAssuranceRouting::ModelNeed { ref part :>> owner=GambitRuntimeAssurance::roots.component; attribute :>> obligationId="MW-BUILD-Q"; attribute :>> kind="interleaving"; attribute :>> subjectPath="models/build/incremental_build.qnt"; attribute :>> subjectScope="modernization-target:build:whole-source-composition-open"; attribute :>> premise="Existing fragment only; Prove dynamic dependency closure, stable input snapshot, output encoding/consumer reflection and failure invalidation; no complete-source composition receipt in this scope"; }
part need5L:GambitAssuranceRouting::ModelNeed { ref part :>> owner=GambitRuntimeAssurance::roots.component; attribute :>> obligationId="MW-BUILD-L"; attribute :>> kind="induction"; attribute :>> subjectPath="models/build/IncrementalBuild.lean"; attribute :>> subjectScope="modernization-target:build:whole-source-composition-open"; attribute :>> premise="Existing fragment only; Prove dynamic dependency closure, stable input snapshot, output encoding/consumer reflection and failure invalidation; no complete-source composition receipt in this scope"; }
part decision5:ArchitectureDecision { ref part :>> owner=GambitRuntimeComposition::blueprintModule8; ref part :>> interleaving=need5Q; ref part :>> induction=need5L; attribute :>> decisionId="build"; attribute :>> target="Semantic artifact graph and native compilation boundary"; attribute :>> lesson="PVM separation plus existing build research: interface programs and dependency-aware products, not command wrappers"; attribute :>> replacement="Scheme frontend/session -> semantic module artifacts -> generated C/runtime ABI artifacts; phase-ready dependency DAG, stable snapshots, incremental/parallel scheduling and reusable AOT interface programs"; attribute :>> retirement="Retire repeated expansion and regenerated/recompiled unaffected units after clean-versus-incremental observational equivalence"; attribute :>> sourceAnchors="vendor/gambit/gsc/_front.scm;gsc/_t-c-1.scm;dev/architecture/toolchain"; attribute :>> obligation="Prove dynamic dependency closure, stable input snapshot, output encoding/consumer reflection and failure invalidation"; attribute :>> benefit="Unchanged/leaf/macro-change work counts; whole build latency and C parser work under existing caps"; attribute :>> addedCost="Dependency/snapshot storage, artifact validation and unavoidable state instantiation; LLVM/MLIR adapters consume contracts, Zig optional"; }
part def CandidateAdoption { attribute semanticsComplete:Boolean; attribute replacesOldResponsibilities:Boolean; attribute capacitySupportsNativeSemantics:Boolean; attribute measuredNetBenefit:Boolean; attribute canAdopt:Boolean=semanticsComplete and replacesOldResponsibilities and capacitySupportsNativeSemantics and measuredNetBenefit; attribute reason:String; }
part nativeScopeCandidate:CandidateAdoption { attribute :>> semanticsComplete=false; attribute :>> replacesOldResponsibilities=false; attribute :>> capacitySupportsNativeSemantics=false; attribute :>> measuredNetBenefit=false; attribute :>> reason="MC-SCOPE is an isolated inactive candidate primitive. Fixed roles, actor id, generation and slot capacity must not become arbitrary restrictions on Scheme/FFI semantics. No further activation is justified by its commit or finite model alone."; }
}
