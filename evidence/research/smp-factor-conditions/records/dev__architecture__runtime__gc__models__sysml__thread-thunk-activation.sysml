/* SysML semantic authority: modern C bootstrap/activation research. */
package GambitThreadThunkActivation { private import ScalarValues::*;
part history : GambitAssuranceRouting::ModelNeed { ref part :>> owner=GambitRuntimeAssurance::roots.component;
attribute :>> obligationId="TA-H";
attribute :>> kind="interleaving";
attribute :>> subjectPath="models/gambit/thread_thunk_activation.qnt";
attribute :>> subjectScope="thread_thunk_activation:publication-sync-activation;finite-histories;seed17";
attribute :>> premise="One prospective worker, one GC movement and one activation; root payload opaque, registry and result observations atomic. No C weak-memory or liveness proof.";
}
part induction : GambitAssuranceRouting::ModelNeed { ref part :>> owner=GambitRuntimeAssurance::roots.component;
attribute :>> obligationId="TA-I";
attribute :>> kind="induction";
attribute :>> subjectPath="models/gambit/lean/ThreadThunkActivation.lean";
attribute :>> subjectScope="GambitSMP.ThreadThunkActivation:conditional-custody-and-cost-laws";
attribute :>> premise="Selective custody, version/reload and cleanup lemmas under explicit guards, not complete source or QNT simulation.";
}
part origin : GambitAssuranceRouting::ModelNeed { ref part :>> owner=GambitRuntimeAssurance::roots.component;
attribute :>> obligationId="TA-ORIGIN";
attribute :>> kind="source-refinement";
attribute :>> subjectPath="models/gambit/lean/ThreadThunkActivation.lean";
attribute :>> subjectScope="TA-ORIGIN:resize-CFUN-origin-before-GC";
attribute :>> premise="Full caller location/handle acquired before on_all_processors and possible resize GC; ordinary startup procedure permanence must be proved per generated profile.";
}
part publish : GambitAssuranceRouting::ModelNeed { ref part :>> owner=GambitRuntimeAssurance::roots.component;
attribute :>> obligationId="TA-PUBLISH";
attribute :>> kind="source-refinement";
attribute :>> subjectPath="models/gambit/lean/ThreadThunkActivation.lean";
attribute :>> subjectScope="TA-PUBLISH:descriptor-before-membership-and-create";
attribute :>> premise="Stable VM descriptor is scanned independently of processor_count; valid source until child accepts; child may run before create returns. Known create error excludes child; lost result does not.";
}
part reload : GambitAssuranceRouting::ModelNeed { ref part :>> owner=GambitRuntimeAssurance::roots.component;
attribute :>> obligationId="TA-RELOAD";
attribute :>> kind="source-refinement";
attribute :>> subjectPath="models/gambit/lean/ThreadThunkActivation.lean";
attribute :>> subjectScope="TA-RELOAD:sync-loop-root-reload";
attribute :>> premise="No cached movable thunk across sync; context binding and exact collector epoch are ready before root reload and activation acceptance.";
}
part scope : GambitAssuranceRouting::ModelNeed { ref part :>> owner=GambitRuntimeAssurance::roots.component;
attribute :>> obligationId="TA-SCOPE";
attribute :>> kind="source-refinement";
attribute :>> subjectPath="models/gambit/lean/ThreadThunkActivation.lean";
attribute :>> subjectScope="TA-SCOPE:both-run-callers-and-marker-exit";
attribute :>> premise="Activation slots fully initialized before registration; source overlap until accepted; marker failure/rethrow funnel after END_TRY; unique marker clear/drop before status.";
}
part order : GambitAssuranceRouting::ModelNeed { ref part :>> owner=GambitRuntimeAssurance::roots.component;
attribute :>> obligationId="TA-ORDER";
attribute :>> kind="native-memory-order";
attribute :>> subjectPath="models/gambit/lean/ThreadThunkActivation.lean";
attribute :>> subjectScope="TA-ORDER:root-publication-scan-retirement";
attribute :>> premise="Explicit registry lock or equivalent snapshot/pin protocol; scalar release/acquire cannot alone establish moving-root scan exclusion. POSIX create success does not cover later collector writes.";
}
ref part priorMarker=GambitNativeEntryCloseCleanup::marker;
ref part priorCleanup=GambitNativeEntryCloseCleanup::conversion;
ref part priorGcRoot=GambitRestAllocatorRootPublication::roots;
part dependency0 : GambitAssuranceRouting::NeedDependency { ref part :>> dependent=origin; ref part :>> prerequisite=history; }
part dependency1 : GambitAssuranceRouting::NeedDependency { ref part :>> dependent=origin; ref part :>> prerequisite=induction; }
part dependency2 : GambitAssuranceRouting::NeedDependency { ref part :>> dependent=publish; ref part :>> prerequisite=history; }
part dependency3 : GambitAssuranceRouting::NeedDependency { ref part :>> dependent=publish; ref part :>> prerequisite=induction; }
part dependency4 : GambitAssuranceRouting::NeedDependency { ref part :>> dependent=reload; ref part :>> prerequisite=history; }
part dependency5 : GambitAssuranceRouting::NeedDependency { ref part :>> dependent=reload; ref part :>> prerequisite=induction; }
part dependency6 : GambitAssuranceRouting::NeedDependency { ref part :>> dependent=scope; ref part :>> prerequisite=history; }
part dependency7 : GambitAssuranceRouting::NeedDependency { ref part :>> dependent=scope; ref part :>> prerequisite=induction; }
part dependency8 : GambitAssuranceRouting::NeedDependency { ref part :>> dependent=order; ref part :>> prerequisite=history; }
part dependency9 : GambitAssuranceRouting::NeedDependency { ref part :>> dependent=order; ref part :>> prerequisite=induction; }
part dependency10 : GambitAssuranceRouting::NeedDependency { ref part :>> dependent=publish; ref part :>> prerequisite=origin; }
part dependency11 : GambitAssuranceRouting::NeedDependency { ref part :>> dependent=reload; ref part :>> prerequisite=publish; }
part dependency12 : GambitAssuranceRouting::NeedDependency { ref part :>> dependent=scope; ref part :>> prerequisite=reload; }
part dependency13 : GambitAssuranceRouting::NeedDependency { ref part :>> dependent=scope; ref part :>> prerequisite=priorMarker; }
part dependency14 : GambitAssuranceRouting::NeedDependency { ref part :>> dependent=scope; ref part :>> prerequisite=priorCleanup; }
part dependency15 : GambitAssuranceRouting::NeedDependency { ref part :>> dependent=publish; ref part :>> prerequisite=priorGcRoot; }
part dependency16 : GambitAssuranceRouting::NeedDependency { ref part :>> dependent=scope; ref part :>> prerequisite=order; }
part def CallerRow { attribute callerId:String; attribute sourceAnchors:String; attribute actualChain:String; attribute hazard:String; attribute replacement:String; }
part caller0:CallerRow { attribute :>> callerId="RESIZE-ORIGIN"; attribute :>> sourceAnchors="vendor/gambit/lib/_thread.scm:3158-3159,6892-6893;lib/_kernel.scm:2353-2361;lib/setup.c:1155-1178,870-916"; attribute :>> actualChain="##cvmr -> ##current-vm-resize c-lambda -> sop.arg[0] -> on_all_processors -> vm_resize -> possible GC"; attribute :>> hazard="Root source before sync publication or first GC; ordinary callers supply ##startup-processor!, not a demonstrated movable closure."; attribute :>> replacement="Select profile/generated procedure identity and full CFUN argument root map. Arbitrary thunk route requires stronger handle admission."; }
part caller1:CallerRow { attribute :>> callerId="WORKER-CREATOR"; attribute :>> sourceAnchors="vendor/gambit/lib/setup.c:941-1003;include/gambit.h.in:11100-11117;lib/os_thread.c:426-539"; attribute :>> actualChain="setup pstate -> set processor_count -> fill thread descriptor -> OS create"; attribute :>> hazard="Current membership becomes visible before OS threads are created; stable root descriptor must exist before collector-visible membership and keep identity through partial creation."; attribute :>> replacement="Do not reorder existing barrier algorithm blindly. Separate planned membership from runnable/GC membership, or prove existing protocol with descriptors."; }
part caller2:CallerRow { attribute :>> callerId="RUN-WORKER"; attribute :>> sourceAnchors="vendor/gambit/lib/setup.c:763-835,1015-1112"; attribute :>> actualChain="start_processor_execution loads raw thunk -> binds pstate -> sync loop -> run_and_throw -> ___run"; attribute :>> hazard="Remove early raw thunk cache; acquire bootstrap lease, synchronize with no raw borrow, obtain context seal and reload, then activation handoff."; attribute :>> replacement="Do not use t->thread_id written after pthread_create as pre-entry readiness; child-before-return is admitted."; }
part caller3:CallerRow { attribute :>> callerId="RUN-MAIN"; attribute :>> sourceAnchors="vendor/gambit/lib/setup.c:1993-2043,6363,6395-6440;lib/mem.c:1712-1730"; attribute :>> actualChain="setup_modules permanent descriptor -> program_descr -> first module thunk -> ___run"; attribute :>> hazard="Descriptor vectors use make_vector(NULL); certify selected thunk lifetime separately, then share activation entry protocol."; attribute :>> replacement="A permanent descriptor container alone does not prove all reachable thunks permanent; generated module binding evidence remains open."; }
part caller4:CallerRow { attribute :>> callerId="RUN-SCOPE"; attribute :>> sourceAnchors="vendor/gambit/lib/setup.c:3276-3423;lib/c_intf.c:6511-6564;include/gambit.h.in:9979-9988"; attribute :>> actualChain="___run marker allocation -> ___call normal/rethrow -> outer catcher -> status"; attribute :>> hazard="Source and marker ownership live in canonical scope record; clear/drop/root retirement in one exit funnel after catcher restoration."; attribute :>> replacement="Do not store sole cleanup progress in modified nonvolatile setjmp locals; unknown decrement is not replayable."; }
part def PathRow { attribute pathId:String; attribute sourceAnchors:String; attribute actualPath:String; attribute contract:String; attribute failure:String; attribute custodian:String; }
part path0:PathRow { attribute :>> pathId="PREPARE"; attribute :>> sourceAnchors="setup.c:1155-1178,870-916"; attribute :>> actualPath="Raw thunk travels through sop and C parameters before growth GC"; attribute :>> contract="Create descriptor with safe false slots and valid origin, register VM root before on_all_processors; reload at each use after possible movement."; attribute :>> failure="Allocation failure occurs while caller full view still valid; no descriptor publication with incomplete scan map."; attribute :>> custodian="Caller owns until VM acceptance; parent borrow cannot survive park without freeze/reload."; }
part path1:PathRow { attribute :>> pathId="PUBLISH"; attribute :>> sourceAnchors="setup.c:941-1003;os_thread.c:493-539"; attribute :>> actualPath="Membership then thread publication"; attribute :>> contract="Reserve one lease per prospective child before OS call; commit one child identity independently of creator result arrival."; attribute :>> failure="Known failure releases only failed child reservation; previously created children stay rooted. Unknown outcome retains lease."; attribute :>> custodian="VM bootstrap registry, never dead creator/PSTATE-only list."; }
part path2:PathRow { attribute :>> pathId="RELOAD"; attribute :>> sourceAnchors="setup.c:805-835,1029,1050-1112"; attribute :>> actualPath="Raw cache precedes loop capable of GC"; attribute :>> contract="Loop executes with root token only; context-ready acquire and collector-updated slot reload occur after final sync and again after any allocation window."; attribute :>> failure="GC-done is not context-ready; use-after-reload allocation needs its own live mapped root."; attribute :>> custodian="Bootstrap lease until activation root acceptance with matching identity/epoch."; }
part path3:PathRow { attribute :>> pathId="ENTER"; attribute :>> sourceAnchors="setup.c:3394-3423;c_intf.c:6511-6545"; attribute :>> actualPath="Marker allocation before proc_or_false store"; attribute :>> contract="Prepare nonmoving native metadata under valid source; FAL-initialize slots; register; accept source; allocate marker; reload thunk for marker store; commit marker ownership."; attribute :>> failure="Partial marker construction retains unique initialization duty; known failure goes to common cleanup."; attribute :>> custodian="NativeActivationScope pinned independently of C catcher locals."; }
part path4:PathRow { attribute :>> pathId="EXIT"; attribute :>> sourceAnchors="setup.c:3350-3423;c_intf.c:6553-6564"; attribute :>> actualPath="Call can rethrow past inline kill"; attribute :>> contract="Restore outer catcher, claim cleanup, record clear then count drop, retire roots only after scan readers drain, return original err."; attribute :>> failure="Unknown clear/drop retains scope; failed/unknown join does not authorize retirement."; attribute :>> custodian="One canonical cleanup claimant; no wait for callback while holding registry lock."; }
part def OrderRow { attribute edgeId:String; attribute orderContract:String; attribute rejectedShortcut:String; }
part orderRow0:OrderRow { attribute :>> edgeId="ORIGIN"; attribute :>> orderContract="Full caller root map and safe slots precede release registry insertion; collector acquires/pins exact descriptor generation."; attribute :>> rejectedShortcut="Raw C parameter, sop argument and W_ALL alone are not new all-domain scanner proofs."; }
part orderRow1:OrderRow { attribute :>> edgeId="SPAWN"; attribute :>> orderContract="Descriptor insertion and child lease precede processor membership/create; OS entry acquires stable descriptor without relying on creator return."; attribute :>> rejectedShortcut="pthread_create synchronizes creation-time writes, not later root relocation. Preserve actual return code, not ambient errno."; }
part orderRow2:OrderRow { attribute :>> edgeId="SCAN"; attribute :>> orderContract="Registry snapshot holds descriptor pin; relocation excludes raw owner access; retirement closes admission then drains snapshot readers."; attribute :>> rejectedShortcut="Do not hold registry lock across GC barrier, pthread_join or Scheme callback; avoid GC/creator/child cycles."; }
part orderRow3:OrderRow { attribute :>> edgeId="RELOAD"; attribute :>> orderContract="Collector slot update and context binding precede resume release; child acquires, reloads and accepts under same epoch."; attribute :>> rejectedShortcut="Thread binding alone or sync NOOP is not proof that all resume prerequisites hold."; }
part orderRow4:OrderRow { attribute :>> edgeId="ACK"; attribute :>> orderContract="Child acceptance recorded before source lease ACK; duplicate ACK is identity-checked; last lease release cannot erase a live activation."; attribute :>> rejectedShortcut="Unknown create/ACK and ignored join keep custody, not a retry that creates a second child."; }
part orderRow5:OrderRow { attribute :>> edgeId="EXIT"; attribute :>> orderContract="END_TRY catcher restore precedes clear/count/root/status funnel; progress lives outside indeterminate setjmp locals."; attribute :>> rejectedShortcut="A nonallocating decrement is neither idempotent nor automatically safe to replay."; }
part def CostRow { attribute capability:String; attribute removedWork:String; attribute bound:String; attribute addedCost:String; attribute condition:String; }
part cost0:CostRow { attribute :>> capability="Bootstrap sharing"; attribute :>> removedWork="Replace N raw thread thunk caches with one relocatable value cell plus N identity leases"; attribute :>> bound="Value slot bytes N*w -> w if one shared thunk and joint scan protocol; saving (N-1)*w"; attribute :>> addedCost="Descriptor H, N leases L and scan-reader metadata R; O(N) lifecycle work remains"; attribute :>> condition="Value sharing alone wins bytes only when (N-1)*w > H+N*L+R relative to replaced support. No claimed total saving."; }
part cost1:CostRow { attribute :>> capability="Root scanning"; attribute :>> removedWork="Scan one shared bootstrap cell once instead of N registered duplicate cells"; attribute :>> bound="N -> 1 slot visits per GC for this cell, only while at least one lease exists"; attribute :>> addedCost="N child lease/accounting operations and active marker roots remain"; attribute :>> condition="Current raw data_scmobj scanning is not established; compare safe modern C alternatives, not unsafe baseline scan=0."; }
part cost2:CostRow { attribute :>> capability="Reload"; attribute :>> removedWork="Remove stale raw thunk lifetime across moving epoch"; attribute :>> bound="At least one post-loop load per successful worker; another after marker allocation if it can GC"; attribute :>> addedCost="Acquire/context check and explicit reload per allocation boundary"; attribute :>> condition="No extra Scheme evaluation, native create or closure copy; compiler barrier alone is insufficient."; }
part cost3:CostRow { attribute :>> capability="Activation root payload"; attribute :>> removedWork="Reuse one root/exit contract for two actual run families"; attribute :>> bound="A active scopes, at most two dedicated slots each -> 2*A*w before proven alias elision"; attribute :>> addedCost="Record/map/pin overhead and still marker backing counted separately"; attribute :>> condition="No requirement to allocate duplicate slots when existing permanent/owned-still authority is certified."; }
part cost4:CostRow { attribute :>> capability="Unknown create"; attribute :>> removedWork="Avoid duplicate OS creation and source-root loss"; attribute :>> bound="One canonical creation attempt per child generation until actual result settles"; attribute :>> addedCost="Unknown U attempts retain U*L plus shared H/root and possible native stacks/PSTATEs"; attribute :>> condition="No bounded peak or eventual recovery without result/stop evidence; process fatal path is not recoverable success."; }
part cost5:CostRow { attribute :>> capability="Peak accounting"; attribute :>> removedWork="Count unique thunk backing once across source/descriptor/activation overlap"; attribute :>> bound="P=max_t(B_values+H+N*L+R+2*A*w+M_still+S_native+U_extra); all backing classes disjoint"; attribute :>> addedCost="B_values excludes marker/native/metadata backing; U_extra excludes unknown stacks/leases already counted; overlap may increase peak"; attribute :>> condition="Positive total/runtime performance remains open; no benchmark, percent or person-days."; }
part cost6:CostRow { attribute :>> capability="Retirement"; attribute :>> removedWork="Replace early worker thunk read, raw descriptor carrier and normal-only kill assumption"; attribute :>> bound="Two ___run caller families; zero runtime paths retired in this study"; attribute :>> addedCost="All-context scanner, producer admission, platform failure and common cleanup must migrate together"; attribute :>> condition="Retire old ownership duties only after source/C-order/native gates; keep Scheme, tail calls, continuation and C portability."; }
part cost7:CostRow { attribute :>> capability="Language choice"; attribute :>> removedWork="Modern C keeps one generated/runtime protocol and C ABI"; attribute :>> bound="No Zig-specific reduction proved for root/lease/GC/cleanup state"; attribute :>> addedCost="Zig would still need same protocol, scanner and platform contracts"; attribute :>> condition="Modern C is required mainline; Zig is optional only with separate demonstrated net value."; }
part def SourceRoute { ref part need:GambitAssuranceRouting::ModelNeed; attribute sourceAnchors:String; attribute projection:String; attribute failureCustodian:String; attribute status:String; }
part route0:SourceRoute { ref part :>> need=origin; attribute :>> sourceAnchors="setup.c:1155-1178,870-916"; attribute :>> projection="Create descriptor with safe false slots and valid origin, register VM root before on_all_processors; reload at each use after possible movement."; attribute :>> failureCustodian="Caller owns until VM acceptance; parent borrow cannot survive park without freeze/reload."; attribute :>> status="source-and-C-order-refinement-open"; }
part route1:SourceRoute { ref part :>> need=publish; attribute :>> sourceAnchors="setup.c:941-1003;os_thread.c:493-539"; attribute :>> projection="Reserve one lease per prospective child before OS call; commit one child identity independently of creator result arrival."; attribute :>> failureCustodian="VM bootstrap registry, never dead creator/PSTATE-only list."; attribute :>> status="source-and-C-order-refinement-open"; }
part route2:SourceRoute { ref part :>> need=reload; attribute :>> sourceAnchors="setup.c:805-835,1029,1050-1112"; attribute :>> projection="Loop executes with root token only; context-ready acquire and collector-updated slot reload occur after final sync and again after any allocation window."; attribute :>> failureCustodian="Bootstrap lease until activation root acceptance with matching identity/epoch."; attribute :>> status="source-and-C-order-refinement-open"; }
part route3:SourceRoute { ref part :>> need=scope; attribute :>> sourceAnchors="setup.c:3394-3423;c_intf.c:6511-6545"; attribute :>> projection="Prepare nonmoving native metadata under valid source; FAL-initialize slots; register; accept source; allocate marker; reload thunk for marker store; commit marker ownership."; attribute :>> failureCustodian="NativeActivationScope pinned independently of C catcher locals."; attribute :>> status="source-and-C-order-refinement-open"; }
part route4:SourceRoute { ref part :>> need=order; attribute :>> sourceAnchors="gambit.h.in:9979-9988,11100-11117;mem.c:6830-6868;os_thread.c:493-539"; attribute :>> projection="ORIGIN,SPAWN,SCAN,RELOAD,ACK,EXIT"; attribute :>> failureCustodian="VM root registry with participating owner"; attribute :>> status="source-and-C-order-refinement-open"; }
part def DiagramNode { attribute nodeId:String; attribute labelText:String; }
part def DiagramEdge { ref part producer:DiagramNode; ref part consumer:DiagramNode; attribute labelText:String; }
part node0:DiagramNode { attribute :>> nodeId="origin"; attribute :>> labelText="Caller root before resize GC"; }
part node1:DiagramNode { attribute :>> nodeId="desc"; attribute :>> labelText="VM bootstrap descriptor and leases"; }
part node2:DiagramNode { attribute :>> nodeId="member"; attribute :>> labelText="Membership and OS create"; }
part node3:DiagramNode { attribute :>> nodeId="child"; attribute :>> labelText="Child bind and sync loop"; }
part node4:DiagramNode { attribute :>> nodeId="reload"; attribute :>> labelText="Context ready and reload roots"; }
part node5:DiagramNode { attribute :>> nodeId="main"; attribute :>> labelText="Permanent module origin qualification"; }
part node6:DiagramNode { attribute :>> nodeId="scope"; attribute :>> labelText="NativeActivationScope accept"; }
part node7:DiagramNode { attribute :>> nodeId="marker"; attribute :>> labelText="Marker allocate and reload"; }
part node8:DiagramNode { attribute :>> nodeId="catch"; attribute :>> labelText="Call or rethrow to catcher"; }
part node9:DiagramNode { attribute :>> nodeId="cleanup"; attribute :>> labelText="One cleanup claim and settle"; }
part node10:DiagramNode { attribute :>> nodeId="retire"; attribute :>> labelText="Drain root readers and deliver status"; }
part node11:DiagramNode { attribute :>> nodeId="unknown"; attribute :>> labelText="Unknown result retains VM custody"; }
part edge0:DiagramEdge { ref part :>> producer=node0; ref part :>> consumer=node1; attribute :>> labelText="register before possible GC"; }
part edge1:DiagramEdge { ref part :>> producer=node1; ref part :>> consumer=node2; attribute :>> labelText="lease before publish"; }
part edge2:DiagramEdge { ref part :>> producer=node2; ref part :>> consumer=node3; attribute :>> labelText="child before creator return"; }
part edge3:DiagramEdge { ref part :>> producer=node3; ref part :>> consumer=node4; attribute :>> labelText="no raw cache across loop"; }
part edge4:DiagramEdge { ref part :>> producer=node4; ref part :>> consumer=node6; attribute :>> labelText="source overlap until accepted"; }
part edge5:DiagramEdge { ref part :>> producer=node5; ref part :>> consumer=node6; attribute :>> labelText="other actual run caller"; }
part edge6:DiagramEdge { ref part :>> producer=node6; ref part :>> consumer=node7; attribute :>> labelText="safe slots first"; }
part edge7:DiagramEdge { ref part :>> producer=node7; ref part :>> consumer=node8; attribute :>> labelText="unique marker ownership"; }
part edge8:DiagramEdge { ref part :>> producer=node8; ref part :>> consumer=node9; attribute :>> labelText="END_TRY restored"; }
part edge9:DiagramEdge { ref part :>> producer=node9; ref part :>> consumer=node10; attribute :>> labelText="settled clear and drop"; }
part edge10:DiagramEdge { ref part :>> producer=node2; ref part :>> consumer=node11; attribute :>> labelText="lost result"; }
part edge11:DiagramEdge { ref part :>> producer=node9; ref part :>> consumer=node11; attribute :>> labelText="unknown cleanup"; }
part edge12:DiagramEdge { ref part :>> producer=node11; ref part :>> consumer=node1; attribute :>> labelText="same identity retained"; }
part def Transition { ref part need:GambitAssuranceRouting::ModelNeed; attribute fromPhase:String; attribute toPhase:String; attribute qntStep:String; attribute guardContract:String; attribute leanLaw:String; attribute sourceAnchors:String; }
part transition0:Transition { ref part :>> need=origin; attribute :>> fromPhase="OriginBorrowed"; attribute :>> toPhase="Prepared"; attribute :>> qntStep="register"; attribute :>> guardContract="Caller view valid; allocate non-GC metadata, FAL slots and map before linking"; attribute :>> leanLaw="registerCovers"; attribute :>> sourceAnchors="setup.c:1155-1178;_kernel.scm:2353-2361"; }
part transition1:Transition { ref part :>> need=publish; attribute :>> fromPhase="Prepared"; attribute :>> toPhase="PublishPending"; attribute :>> qntStep="beginCreate"; attribute :>> guardContract="VM root visible and prospective child lease reserved before membership/create"; attribute :>> leanLaw="registerCovers"; attribute :>> sourceAnchors="setup.c:941-1003"; }
part transition2:Transition { ref part :>> need=publish; attribute :>> fromPhase="PublishPending"; attribute :>> toPhase="ChildBound"; attribute :>> qntStep="childEntry"; attribute :>> guardContract="Stable descriptor identity; may precede creator result; bind PSTATE before synchronization"; attribute :>> leanLaw="childPreventsRollback"; attribute :>> sourceAnchors="setup.c:805-835;os_thread.c:426-439"; }
part transition3:Transition { ref part :>> need=publish; attribute :>> fromPhase="PublishPending"; attribute :>> toPhase="KnownNoChild"; attribute :>> qntStep="createFailure / confirmNoChild"; attribute :>> guardContract="Actual OS failure or external no-child evidence; never timeout"; attribute :>> leanLaw="unknownRetainsDescriptor"; attribute :>> sourceAnchors="os_thread.c:493-539"; }
part transition4:Transition { ref part :>> need=reload; attribute :>> fromPhase="ChildBound"; attribute :>> toPhase="SyncComplete"; attribute :>> qntStep="finishSync"; attribute :>> guardContract="Loop completion plus exact resume context/binding; no movable raw cache"; attribute :>> leanLaw="stoppedMovePreserves"; attribute :>> sourceAnchors="setup.c:1050-1112"; }
part transition5:Transition { ref part :>> need=reload; attribute :>> fromPhase="SyncComplete"; attribute :>> toPhase="Reloaded"; attribute :>> qntStep="reloadThunk"; attribute :>> guardContract="Acquire context-ready and read collector-updated cell for current epoch"; attribute :>> leanLaw="reloadRequiresContext"; attribute :>> sourceAnchors="setup.c:805-835"; }
part transition6:Transition { ref part :>> need=scope; attribute :>> fromPhase="Reloaded"; attribute :>> toPhase="ActivationAccepted"; attribute :>> qntStep="acceptActivation / acknowledgeSource"; attribute :>> guardContract="Initialize safe slots, register/pin scope, accept same identity before source ACK; canonical result settled"; attribute :>> leanLaw="ackRequiresAccepted"; attribute :>> sourceAnchors="setup.c:3394-3423"; }
part transition7:Transition { ref part :>> need=scope; attribute :>> fromPhase="ActivationAccepted"; attribute :>> toPhase="MarkerReady"; attribute :>> qntStep="allocateMarker / reloadThunk"; attribute :>> guardContract="Marker root exists before allocation; reload proc after allocation; failure retains duty"; attribute :>> leanLaw="acceptanceCovers"; attribute :>> sourceAnchors="c_intf.c:6511-6545"; }
part transition8:Transition { ref part :>> need=scope; attribute :>> fromPhase="MarkerReady"; attribute :>> toPhase="Caught"; attribute :>> qntStep="callReturn / callRethrow / markerFailure"; attribute :>> guardContract="Outer catcher restored; preserve original status and marker presence"; attribute :>> leanLaw="returnRequiresRestored"; attribute :>> sourceAnchors="setup.c:3350-3423;gambit.h.in:9979-9988"; }
part transition9:Transition { ref part :>> need=scope; attribute :>> fromPhase="Caught"; attribute :>> toPhase="CleanupClaimed"; attribute :>> qntStep="claimExit / clearMarker / dropMarker"; attribute :>> guardContract="Single canonical progress record; clear before one count drop; no sole modified setjmp local"; attribute :>> leanLaw="decrementAtMostOnce"; attribute :>> sourceAnchors="c_intf.c:6553-6564"; }
part transition10:Transition { ref part :>> need=scope; attribute :>> fromPhase="CleanupClaimed"; attribute :>> toPhase="RootsRetired"; attribute :>> qntStep="retireActivation"; attribute :>> guardContract="Known settled marker or never-created marker; root readers drained externally"; attribute :>> leanLaw="unknownExitRetainsRoot"; attribute :>> sourceAnchors="setup.c:3394-3423;mem.c:6830-6868"; }
part transition11:Transition { ref part :>> need=scope; attribute :>> fromPhase="RootsRetired"; attribute :>> toPhase="StatusDelivered"; attribute :>> qntStep="deliver"; attribute :>> guardContract="Root/marker custody settled; native descriptor can still retain unresolved creation outcome"; attribute :>> leanLaw="returnRequiresRestored"; attribute :>> sourceAnchors="setup.c:763-803,6425-6440"; }
part def RootPayload { attribute workers:Integer; attribute wordBytes:Integer=8; attribute oldSlotsBytes:Integer=workers*wordBytes; attribute sharedSlotBytes:Integer=wordBytes; attribute slotSavingBytes:Integer=oldSlotsBytes-sharedSlotBytes; }
part flat:RootPayload { attribute :>> workers=1; }
part shared:RootPayload { attribute :>> workers=8; }
}
