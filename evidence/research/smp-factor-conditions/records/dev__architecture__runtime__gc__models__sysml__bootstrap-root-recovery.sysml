/* SysML semantic authority: modern C bootstrap registration recovery. */
package GambitBootstrapRootRecovery { private import ScalarValues::*;
part history:GambitAssuranceRouting::ModelNeed { ref part :>> owner=GambitRuntimeAssurance::roots.component;
attribute :>> obligationId="BR-H";
attribute :>> kind="interleaving";
attribute :>> subjectPath="models/gambit/bootstrap_root_recovery.qnt";
attribute :>> subjectScope="bootstrap_root_recovery:one-key-three-deliveries-GC-and-restored-binding;seed17";
attribute :>> premise="One logical key, bounded retries, one GC and one live-parent restoration; atomic ledger/view/scanner and consumer-drain premises. Includes lost registration and ACK histories; no C/multi-key table/liveness proof.";
}
part induction:GambitAssuranceRouting::ModelNeed { ref part :>> owner=GambitRuntimeAssurance::roots.component;
attribute :>> obligationId="BR-I";
attribute :>> kind="induction";
attribute :>> subjectPath="models/gambit/lean/BootstrapRootRecovery.lean";
attribute :>> subjectScope="GambitSMP.BootstrapRootRecovery:conditional-ACK-view-key-and-lifetime-laws";
attribute :>> premise="Selective operation laws, guarded root coverage, retained physical scan pin, restored-pin separation, key fence and arithmetic; no complete QNT Step induction/source simulation.";
}
part identityDuty:GambitAssuranceRouting::ModelNeed { ref part :>> owner=GambitRuntimeAssurance::roots.component;
attribute :>> obligationId="BR-ID";
attribute :>> kind="source-refinement";
attribute :>> subjectPath="models/gambit/lean/BootstrapRootRecovery.lean";
attribute :>> subjectScope="BR-ID:logical-request-origin-and-binding-identities";
attribute :>> premise="Generated semantic invocation/key sequence, immutable origin specification and request generation; exclude physical FP/SCMOBJ address as identity; legitimate Scheme reinvocation differs from delivery retry.";
}
part lookupDuty:GambitAssuranceRouting::ModelNeed { ref part :>> owner=GambitRuntimeAssurance::roots.component;
attribute :>> obligationId="BR-QUERY";
attribute :>> kind="source-refinement";
attribute :>> subjectPath="models/gambit/lean/BootstrapRootRecovery.lean";
attribute :>> subjectScope="BR-QUERY:canonical-insert-query-cancel-and-retry";
attribute :>> premise="Per-VM canonical record reserved before effects; matching-key dedup, immutable intent, current revision and lifetime pin; absence with delayed request does not prove no effect.";
}
part ackDuty:GambitAssuranceRouting::ModelNeed { ref part :>> owner=GambitRuntimeAssurance::roots.component;
attribute :>> obligationId="BR-ACK";
attribute :>> kind="source-refinement";
attribute :>> subjectPath="models/gambit/lean/BootstrapRootRecovery.lean";
attribute :>> subjectScope="BR-ACK:source-lease-ACK-not-Scheme-frame-removal";
attribute :>> premise="ACK closes one exact extra origin lease only after canonical root/effect custody; retain physical view pin through readers/borrowers. Never clear natural Scheme slot/map or restored-parent pin.";
}
part restoreDuty:GambitAssuranceRouting::ModelNeed { ref part :>> owner=GambitRuntimeAssurance::roots.component;
attribute :>> obligationId="BR-RESTORE";
attribute :>> kind="source-refinement";
attribute :>> subjectPath="models/gambit/lean/BootstrapRootRecovery.lean";
attribute :>> subjectScope="BR-RESTORE:parent-frame-generation-restore-and-reload";
attribute :>> premise="Reacquire logical frame and current slot after relocation/restoration; distinguish same-live-native invocation from fresh Scheme reinvocation and unwound C activation; continuation/denv writers remain a premise.";
}
part unwindDuty:GambitAssuranceRouting::ModelNeed { ref part :>> owner=GambitRuntimeAssurance::roots.component;
attribute :>> obligationId="BR-EXIT";
attribute :>> kind="source-refinement";
attribute :>> subjectPath="models/gambit/lean/BootstrapRootRecovery.lean";
attribute :>> subjectScope="BR-EXIT:CFUN-nonlocal-exit-VM-escrow-and-entry-close";
attribute :>> premise="Actual selected CFUN lacks cleanup body; outer run/call catcher and native guard must transfer source view/key and close future publication before unwind; dynamic-wind alone is insufficient.";
}
part retireDuty:GambitAssuranceRouting::ModelNeed { ref part :>> owner=GambitRuntimeAssurance::roots.component;
attribute :>> obligationId="BR-RETIRE";
attribute :>> kind="source-refinement";
attribute :>> subjectPath="models/gambit/lean/BootstrapRootRecovery.lean";
attribute :>> subjectScope="BR-RETIRE:result-ACK-frontier-and-record-reader-drain";
attribute :>> premise="Source ACK, terminal result handoff, incoming delivery/query/scanner drain and persistent retired-key admission fence are distinct; no max-seen shortcut, wrap or recreation after tombstone deletion.";
}
part orderDuty:GambitAssuranceRouting::ModelNeed { ref part :>> owner=GambitRuntimeAssurance::work.component;
attribute :>> obligationId="BR-ORDER";
attribute :>> kind="native-memory-order";
attribute :>> subjectPath="models/gambit/lean/BootstrapRootRecovery.lean";
attribute :>> subjectScope="BR-ORDER:insert-close-query-ACK-and-purge-C-order";
attribute :>> premise="Concrete control-lock/atomic and storage lifetime proof for lookup pin, revision recheck, collector relocation and deferred physical release; no weak-memory/source receipt.";
}
ref part priorView=GambitResizeBootstrapAdmission::rootView;
ref part priorGate=GambitResizeBootstrapAdmission::gate;
ref part priorMembers=GambitResizeBootstrapAdmission::membership;
ref part priorScope=GambitThreadThunkActivation::scope;
part dependency0:GambitAssuranceRouting::NeedDependency { ref part :>> dependent=identityDuty; ref part :>> prerequisite=history; }
part dependency1:GambitAssuranceRouting::NeedDependency { ref part :>> dependent=identityDuty; ref part :>> prerequisite=induction; }
part dependency2:GambitAssuranceRouting::NeedDependency { ref part :>> dependent=lookupDuty; ref part :>> prerequisite=history; }
part dependency3:GambitAssuranceRouting::NeedDependency { ref part :>> dependent=lookupDuty; ref part :>> prerequisite=induction; }
part dependency4:GambitAssuranceRouting::NeedDependency { ref part :>> dependent=ackDuty; ref part :>> prerequisite=history; }
part dependency5:GambitAssuranceRouting::NeedDependency { ref part :>> dependent=ackDuty; ref part :>> prerequisite=induction; }
part dependency6:GambitAssuranceRouting::NeedDependency { ref part :>> dependent=restoreDuty; ref part :>> prerequisite=history; }
part dependency7:GambitAssuranceRouting::NeedDependency { ref part :>> dependent=restoreDuty; ref part :>> prerequisite=induction; }
part dependency8:GambitAssuranceRouting::NeedDependency { ref part :>> dependent=unwindDuty; ref part :>> prerequisite=history; }
part dependency9:GambitAssuranceRouting::NeedDependency { ref part :>> dependent=unwindDuty; ref part :>> prerequisite=induction; }
part dependency10:GambitAssuranceRouting::NeedDependency { ref part :>> dependent=retireDuty; ref part :>> prerequisite=history; }
part dependency11:GambitAssuranceRouting::NeedDependency { ref part :>> dependent=retireDuty; ref part :>> prerequisite=induction; }
part dependency12:GambitAssuranceRouting::NeedDependency { ref part :>> dependent=orderDuty; ref part :>> prerequisite=history; }
part dependency13:GambitAssuranceRouting::NeedDependency { ref part :>> dependent=orderDuty; ref part :>> prerequisite=induction; }
part dependency14:GambitAssuranceRouting::NeedDependency { ref part :>> dependent=identityDuty; ref part :>> prerequisite=priorView; }
part dependency15:GambitAssuranceRouting::NeedDependency { ref part :>> dependent=lookupDuty; ref part :>> prerequisite=identityDuty; }
part dependency16:GambitAssuranceRouting::NeedDependency { ref part :>> dependent=lookupDuty; ref part :>> prerequisite=priorGate; }
part dependency17:GambitAssuranceRouting::NeedDependency { ref part :>> dependent=ackDuty; ref part :>> prerequisite=lookupDuty; }
part dependency18:GambitAssuranceRouting::NeedDependency { ref part :>> dependent=ackDuty; ref part :>> prerequisite=orderDuty; }
part dependency19:GambitAssuranceRouting::NeedDependency { ref part :>> dependent=ackDuty; ref part :>> prerequisite=priorView; }
part dependency20:GambitAssuranceRouting::NeedDependency { ref part :>> dependent=restoreDuty; ref part :>> prerequisite=ackDuty; }
part dependency21:GambitAssuranceRouting::NeedDependency { ref part :>> dependent=restoreDuty; ref part :>> prerequisite=priorScope; }
part dependency22:GambitAssuranceRouting::NeedDependency { ref part :>> dependent=unwindDuty; ref part :>> prerequisite=lookupDuty; }
part dependency23:GambitAssuranceRouting::NeedDependency { ref part :>> dependent=unwindDuty; ref part :>> prerequisite=ackDuty; }
part dependency24:GambitAssuranceRouting::NeedDependency { ref part :>> dependent=unwindDuty; ref part :>> prerequisite=priorScope; }
part dependency25:GambitAssuranceRouting::NeedDependency { ref part :>> dependent=retireDuty; ref part :>> prerequisite=identityDuty; }
part dependency26:GambitAssuranceRouting::NeedDependency { ref part :>> dependent=retireDuty; ref part :>> prerequisite=lookupDuty; }
part dependency27:GambitAssuranceRouting::NeedDependency { ref part :>> dependent=retireDuty; ref part :>> prerequisite=unwindDuty; }
part dependency28:GambitAssuranceRouting::NeedDependency { ref part :>> dependent=retireDuty; ref part :>> prerequisite=priorMembers; }
part dependency29:GambitAssuranceRouting::NeedDependency { ref part :>> dependent=orderDuty; ref part :>> prerequisite=priorGate; }
part def CallerRow {  attribute callerId:String; attribute sourceAnchors:String; attribute actualChain:String; attribute hazard:String; attribute replacement:String; }
part caller0:CallerRow { attribute :>> callerId="GENERATOR-ENTRY"; attribute :>> sourceAnchors="vendor/gambit/lib/_kernel.scm:2353-2361;gsc/_ptree2.scm:2850-2874,2902-2925,3238-3251"; attribute :>> actualChain="c-lambda source argument aliases mapped CFUN slot; cleanup-body selection depends on parameter conversion needs"; attribute :>> hazard="Issue logical native-invocation key and origin token after conversion, before first possible effect"; attribute :>> replacement="No key computed from physical stack/value address; arbitrary c-code/direct C callers require explicit origin."; }
part caller1:CallerRow { attribute :>> callerId="TRACKED-CFUN"; attribute :>> sourceAnchors="vendor/gambit/lib/_kernel.c:6258-6288,26338-26368,30819-30821;include/gambit.h.in:10325-10404"; attribute :>> actualChain="No-cleanup CFUN body calls current_vm_resize; OOL returns through resource-specific R_ALL"; attribute :>> hazard="Scope/key/source lease progress must survive a bypassed normal C return"; attribute :>> replacement="Tracked source shape fs3/link2/map7, not installed binary/profile equivalence."; }
part caller2:CallerRow { attribute :>> callerId="SYNC-RETURN-AND-THROW"; attribute :>> sourceAnchors="vendor/gambit/lib/setup.c:1050-1112,1155-1178"; attribute :>> actualChain="sop result copied back/operation NOOP marked, then processor0 may throw collected error"; attribute :>> hazard="Publish canonical registration/lease disposition before caller sees status; original status and logical pending state live outside local sop"; attribute :>> replacement="OP_NOOP or absence of normal return is not proof that an effect never happened."; }
part caller3:CallerRow { attribute :>> callerId="OUTER-CATCHER"; attribute :>> sourceAnchors="vendor/gambit/lib/setup.c:3276-3423;include/gambit.h.in:9979-9988"; attribute :>> actualChain="call restores local catcher and may rethrow to run; normal inline marker cleanup can be bypassed"; attribute :>> hazard="VM escrow accepts frozen source view/key, closes admission, then stable scope exit guard handles every catcher path"; attribute :>> replacement="Modified nonvolatile setjmp locals are not sole cleanup/result state; no resurrected dead C activation."; }
part caller4:CallerRow { attribute :>> callerId="REAL-FRAME-RESTORE"; attribute :>> sourceAnchors="vendor/gambit/lib/mem.c:3898-3965,4529-4561;include/gambit.h.in:10402;lib/_kernel.scm:1026-1066"; attribute :>> actualChain="GC prepares current PSTATE fp; CFUN_ARG recomputes address; return-to-C validates processor and live marker"; attribute :>> hazard="Re-resolve logical FrameSpec/PointId and bind generation before reload; old source-ACK cannot target new frame pin"; attribute :>> replacement="Stable Scheme continuation does not guarantee old physical fp or live C stack."; }
part caller5:CallerRow { attribute :>> callerId="CONTINUATION-WRITERS"; attribute :>> sourceAnchors="vendor/gambit/lib/_kernel.scm:3154-3163,3512-3550;lib/_thread.scm:4794-4813,4990-5021,5047-5077"; attribute :>> actualChain="Frame/denv writes and continuation-return/graft; same dynamic-wind context goes directly to continue"; attribute :>> hazard="Track source lease identity and restore binding; guard every actual resume/use, not only wind hooks"; attribute :>> replacement="All writers/serialization/native borrowers remain source obligations; no immutable captured-frame assumption."; }
part caller6:CallerRow { attribute :>> callerId="TWO-RUN-FAMILIES"; attribute :>> sourceAnchors="vendor/gambit/lib/setup.c:763-835,6395-6440;lib/c_intf.c:6511-6564"; attribute :>> actualChain="Main module thunk and worker bootstrap thunk converge on run and marker handling"; attribute :>> hazard="Shared activation/root/query/exit protocol, then independent per-child source handoff and consumer drain"; attribute :>> replacement="Registration acceptance/ACK is not thread creation, GC member commit or child-stop evidence."; }
part def PathRow {  attribute pathId:String; attribute sourceAnchors:String; attribute actualPath:String; attribute contract:String; attribute failure:String; attribute custodian:String; }
part path0:PathRow { attribute :>> pathId="CANONICAL-KEY"; attribute :>> sourceAnchors="_kernel.c:6258-6288;setup.c:1155-1178"; attribute :>> actualPath="Existing C parameter and local sop do not encode recoverable invocation identity"; attribute :>> contract="Allocate key before publication; insert-or-find one canonical immutable-intent record; duplicate submits reuse it"; attribute :>> failure="Conflicting intent rejects; failed/unknown insertion keeps source view; query absence alone cannot release it"; attribute :>> custodian="Live NativeActivation/source lease until VM record custody is known"; }
part path1:PathRow { attribute :>> pathId="QUERY"; attribute :>> sourceAnchors="setup.c:1050-1112;gambit.h.in:11599-11603"; attribute :>> actualPath="Operation may execute before original sop caller gets a normal result"; attribute :>> contract="Pin canonical record, read key/descriptor/revision/status only; ACK later revalidates under same control domain"; attribute :>> failure="No SCMOBJ payload returned as a raw query capability; stale/wrong-key receipt rejects"; attribute :>> custodian="VM owns canonical entry/root and lookup lifetime; caller retains exact old source lease"; }
part path2:PathRow { attribute :>> pathId="SOURCE-ACK"; attribute :>> sourceAnchors="mem.c:3898-3965;_kernel.c:26358-26368;gambit.h.in:10402"; attribute :>> actualPath="Natural Scheme frame remains a precise root independent of helper lease"; attribute :>> contract="Logical ACK closes exact extra origin lease once; physical old-view pin waits for its scanner/borrowers"; attribute :>> failure="Never erase arg slot, frame map, still refcount or newer binding pin as a broad ACK cleanup"; attribute :>> custodian="VM descriptor or terminal no-future-effect record owns operation; natural GVM frame retains language roots"; }
part path3:PathRow { attribute :>> pathId="RESTORE"; attribute :>> sourceAnchors="mem.c:4529-4561;_thread.scm:4990-5021,5047-5077"; attribute :>> actualPath="Physical fp and dynamic/control extent can change across resume"; attribute :>> contract="Keep old operation/source token separate from restored binding token; reload current generation/epoch before use"; attribute :>> failure="Old receipt settles old lease only; dead native marker cannot be revived"; attribute :>> custodian="Original source backing/VM escrow plus independent restored-parent pin"; }
part path4:PathRow { attribute :>> pathId="EXCEPTION"; attribute :>> sourceAnchors="_ptree2.scm:3238-3251;setup.c:1109-1111,3350-3423"; attribute :>> actualPath="No-cleanup CFUN can be bypassed by a nonlocal exit to outer catcher"; attribute :>> contract="Before exit, transfer stable view/key, close future publication; pending request cancels, accepted root stays VM owned until drain"; attribute :>> failure="No hidden continuation retry or callback under control lock; unknown root/view write refuses handoff"; attribute :>> custodian="VM canonical escrow, not stack local progress or unwound owner"; }
part path5:PathRow { attribute :>> pathId="RETIRE"; attribute :>> sourceAnchors="setup.c:763-803,1155-1178;_kernel.scm:1026-1066"; attribute :>> actualPath="Runtime statuses, native return and resource stop have separate endpoints"; attribute :>> contract="Keep terminal outcome until delivered/acknowledged; then drain query/scanner/delivery readers and retain anti-replay frontier"; attribute :>> failure="No tombstone free from source ACK alone; delayed attempts cannot recreate a retired key"; attribute :>> custodian="VM record/result acceptor; per-child native custody remains imported RB-MEMBERS duty"; }
part def OrderRow {  attribute edgeId:String; attribute orderContract:String; attribute rejectedShortcut:String; }
part orderRow0:OrderRow { attribute :>> edgeId="INSERT"; attribute :>> orderContract="Key/origin intent and safe empty slots precede insert-or-find; accept-vs-GC-close arbitration is the predecessor shared cut."; attribute :>> rejectedShortcut="No helper effect before key/source view is recoverable; no pointer-address dedup after moving GC."; }
part orderRow1:OrderRow { attribute :>> edgeId="QUERY-PIN"; attribute :>> orderContract="Lookup and lifetime pin precede reading record; copied receipt names key/generation/revision only; unpin may follow."; attribute :>> rejectedShortcut="Receipt is not a raw pointer lease or a load of current Scheme value. ACK must resolve and recheck again."; }
part orderRow2:OrderRow { attribute :>> edgeId="ACK"; attribute :>> orderContract="Revalidate canonical identity/root-or-terminal custody and old borrower stop, then one logical lease ACK."; attribute :>> rejectedShortcut="Physical pin release is deferred while source scan readers exist, even if the descriptor is already accepted."; }
part orderRow3:OrderRow { attribute :>> edgeId="RESTORE"; attribute :>> orderContract="Frame restore closes old raw borrow; fresh binding/map/epoch is acquired before new use; old ACK touches only old lease."; attribute :>> rejectedShortcut="No old C stack frame pointer/loaded value/catcher/token reused as new-generation authority."; }
part orderRow4:OrderRow { attribute :>> edgeId="UNWIND"; attribute :>> orderContract="Stable VM ownership and publication-close record precede physical source exit; cleanup state is outside indeterminate locals."; attribute :>> rejectedShortcut="No callback/wind hook or normal-only CFUN AT_END assumed to run on every exception/continuation edge."; }
part orderRow5:OrderRow { attribute :>> edgeId="PURGE"; attribute :>> orderContract="Terminal status handoff, source lease settlement, old scanner/query/delivery drain and persistent retired-key gate precede metadata free."; attribute :>> rejectedShortcut="Max observed request sequence is not a contiguous retired prefix; no fence reset or ID wrap while stale producers remain."; }
part def CostRow {  attribute capability:String; attribute removedWork:String; attribute bound:String; attribute addedCost:String; attribute condition:String; }
part cost0:CostRow { attribute :>> capability="Dedup root storage"; attribute :>> removedWork="Prevent duplicate descriptor/root creation from retrying one uncertain operation"; attribute :>> bound="Per logical key: at most1 canonical allocation and at most1 accepted root across modeled deliveries"; attribute :>> addedCost="Key/intent comparison, status/revision and O(R) work for R deliveries"; attribute :>> condition="No claim R native retries already occur; this eliminates support needed by a correct recoverable path."; }
part cost1:CostRow { attribute :>> capability="Source ACK scope"; attribute :>> removedWork="Release only extra operation/source lease"; attribute :>> bound="0 natural Scheme slots or GC-map entries removed; one old lease ACK at most once"; attribute :>> addedCost="Old view pin may outlive ACK until scanner/raw borrowers drain"; attribute :>> condition="No GC scan saving claimed for natural Scheme frame; separate pin retention may shrink only after its own gate."; }
part cost2:CostRow { attribute :>> capability="Parent restoration"; attribute :>> removedWork="Keep same live request through pause rather than repeat native effect"; attribute :>> bound="Old source lease0 and restored-parent pin1 are independent; query reload does not re-evaluate Scheme arguments"; attribute :>> addedCost="Frame-generation/epoch validation and map reacquisition"; attribute :>> condition="Legitimate fresh Scheme invocation needs a fresh key; old unwound C activation remains invalid."; }
part cost3:CostRow { attribute :>> capability="Query path"; attribute :>> removedWork="Recover status without materializing a Scheme thunk copy"; attribute :>> bound="0 Scheme payload loads/evaluations by the control-only query design"; attribute :>> addedCost="Lookup lifetime pin and current-revision recheck; may retry under mutation"; attribute :>> condition="Not a latency bound; lock contention and allocator/table behavior remain unmeasured."; }
part cost4:CostRow { attribute :>> capability="Closed GC"; attribute :>> removedWork="Reuse frozen mapped source while insertion waits"; attribute :>> bound="Pending record contains safe empty slots plus identity, not an extra unscanned thunk copy"; attribute :>> addedCost="Source-view/native metadata retained across close; descriptor accepted only after current reload"; attribute :>> condition="Inherited full-view/close C implementation and complete writer census must be admitted."; }
part cost5:CostRow { attribute :>> capability="Outcome retention"; attribute :>> removedWork="Do not confuse root ACK with status/result acceptance"; attribute :>> bound="Source ACK plus result ACK plus producer/read drain required before purge"; attribute :>> addedCost="Result/tombstone metadata retained after value lease closes"; attribute :>> condition="Unknown status delivery or producer history has no bounded total retention theorem."; }
part cost6:CostRow { attribute :>> capability="Late producer rejection"; attribute :>> removedWork="Prevent old key recreation after record deletion"; attribute :>> bound="One-key fence remains after tombstone free; duplicate effect count stays1"; attribute :>> addedCost="Persistent within-VM retired prefix/sparse holes or equivalent generation table"; attribute :>> condition="Full multi-key frontier/holes/wrap proof remains open; not disk crash durability or timeout-based deletion."; }
part cost7:CostRow { attribute :>> capability="Peak accounting"; attribute :>> removedWork="Count unique backing across source, descriptor, result and restored parent"; attribute :>> bound="P=max_t(B_unique + H_active + H_tombstones + V_old + V_new + Q_pins + Fence + Native_unique)"; attribute :>> addedCost="Unknown ownership/delivery can extend overlap; value-cell bytes alone do not determine peak"; attribute :>> condition="Disjoint classes only; budget L caps L*H metadata only if admission gates preserve waiting source roots; no whole-runtime bound."; }
part cost8:CostRow { attribute :>> capability="Modern C leverage"; attribute :>> removedWork="One generated origin/guard/key protocol shared by Scheme and native runtime consumers"; attribute :>> bound="Retire raw sop thunk ownership and normal-only cleanup assumptions only after all consuming paths migrate"; attribute :>> addedCost="Typed metadata, canonical service and generated FrameSpec/PointId/effect contracts"; attribute :>> condition="Zig would still require the same root/query/ACK/restore semantics; no extra Zig net benefit proved here."; }
part def IdentityField { ref part need:GambitAssuranceRouting::ModelNeed; attribute fieldId:String; attribute sourceAnchors:String; attribute valueContract:String; attribute invalidShortcut:String; attribute failureCustodian:String; }
part fieldRow0:IdentityField { ref part :>> need=GambitBootstrapRootRecovery::identityDuty; attribute :>> fieldId="REQUEST-KEY"; attribute :>> sourceAnchors="_kernel.scm:2353-2361;_ptree2.scm:3238-3251"; attribute :>> valueContract="VM identity + logical native invocation + operation sequence + non-reused request generation"; attribute :>> invalidShortcut="Not physical fp, callsite alone, Scheme value address, thread ID or delivery counter"; attribute :>> failureCustodian="Parent scope/VM record keeps key stable before any effect"; }
part fieldRow1:IdentityField { ref part :>> need=GambitBootstrapRootRecovery::identityDuty; attribute :>> fieldId="IMMUTABLE-INTENT"; attribute :>> sourceAnchors="_kernel.c:6260-6271;gambit.h.in:10402"; attribute :>> valueContract="Operation kind, target count and exact logical origin/lease identity; moving payload accessed through current mapped cell"; attribute :>> invalidShortcut="No hash of raw SCMOBJ bits or mutable payload to infer identity"; attribute :>> failureCustodian="Mismatch rejects without modifying accepted request/root"; }
part fieldRow2:IdentityField { ref part :>> need=GambitBootstrapRootRecovery::lookupDuty; attribute :>> fieldId="QUERY-RECEIPT"; attribute :>> sourceAnchors="setup.c:1050-1112"; attribute :>> valueContract="Key, canonical descriptor identity, revision/status and record-lifetime binding"; attribute :>> invalidShortcut="No raw payload/root-read capability; absence is not no-effect"; attribute :>> failureCustodian="Query reader then ACK relookup/control-domain revalidation"; }
part fieldRow3:IdentityField { ref part :>> need=GambitBootstrapRootRecovery::ackDuty; attribute :>> fieldId="SOURCE-LEASE"; attribute :>> sourceAnchors="mem.c:3898-3965;_kernel.c:26358-26368"; attribute :>> valueContract="Exact additional operation root-view lease and old pin identity"; attribute :>> invalidShortcut="Not natural Scheme slot, gcmap, whole denv or still refcount ownership"; attribute :>> failureCustodian="Logical ACK idempotent; pin physically retained for current readers"; }
part fieldRow4:IdentityField { ref part :>> need=GambitBootstrapRootRecovery::restoreDuty; attribute :>> fieldId="RESTORED-BINDING"; attribute :>> sourceAnchors="mem.c:4529-4561;_thread.scm:5047-5077"; attribute :>> valueContract="Independent frame/view generation, PointId, owner binding and current loaded epoch"; attribute :>> invalidShortcut="Restoring Scheme does not revive an unwound C frame or authorize reuse of old fp"; attribute :>> failureCustodian="New binding pin survives old source ACK"; }
part fieldRow5:IdentityField { ref part :>> need=GambitBootstrapRootRecovery::unwindDuty; attribute :>> fieldId="EXIT-DISPOSITION"; attribute :>> sourceAnchors="gambit.h.in:9979-9988;setup.c:3350-3423"; attribute :>> valueContract="Canonical VM accepted custody and future-entry-close progress plus original status"; attribute :>> invalidShortcut="No sole changed nonvolatile setjmp local or dynamic-wind-only release"; attribute :>> failureCustodian="Pending cancel or accepted-root/consumer drain under VM ownership"; }
part fieldRow6:IdentityField { ref part :>> need=GambitBootstrapRootRecovery::retireDuty; attribute :>> fieldId="RESULT-AND-FRONTIER"; attribute :>> sourceAnchors="setup.c:763-803,1155-1178"; attribute :>> valueContract="Terminal outcome handed to actual acceptor; retired-key gate survives metadata deletion"; attribute :>> invalidShortcut="Source ACK is not result ACK; max-seen ID is not hole-free retirement"; attribute :>> failureCustodian="Retain tombstone/result until acceptance and reader/delivery fences close"; }
part def Transition { ref part need:GambitAssuranceRouting::ModelNeed; attribute fromPhase:String; attribute toPhase:String; attribute qntStep:String; attribute guardContract:String; attribute leanLaw:String; attribute sourceAnchors:String; }
part transition0:Transition { ref part :>> need=GambitBootstrapRootRecovery::identityDuty; attribute :>> fromPhase="UncertainCall"; attribute :>> toPhase="CanonicalPending"; attribute :>> qntStep="submit / arrive"; attribute :>> guardContract="Same key/immutable intent; source map pinned before effects"; attribute :>> leanLaw="reserveDuplicateIdempotent"; attribute :>> sourceAnchors="_kernel.c:6260-6271;setup.c:1155-1178"; }
part transition1:Transition { ref part :>> need=GambitBootstrapRootRecovery::lookupDuty; attribute :>> fromPhase="UnknownOutcome"; attribute :>> toPhase="PinnedQuery"; attribute :>> qntStep="pinQuery / readQuery / unpinQuery"; attribute :>> guardContract="Lookup pin protects record; receipt is control metadata only"; attribute :>> leanLaw="wrongKeyRejected"; attribute :>> sourceAnchors="setup.c:1050-1112;proposed canonical service"; }
part transition2:Transition { ref part :>> need=GambitBootstrapRootRecovery::lookupDuty; attribute :>> fromPhase="AbsentWithDelayedCall"; attribute :>> toPhase="TerminalNoFutureEffect"; attribute :>> qntStep="queryAbsent / cancelUnseen"; attribute :>> guardContract="Absence keeps source; cancel publishes a canonical tombstone before delayed arrival can accept"; attribute :>> leanLaw="noRecordBeforeArrivalIsNotTerminal"; attribute :>> sourceAnchors="setup.c:1050-1112;proposed admission cut"; }
part transition3:Transition { ref part :>> need=GambitBootstrapRootRecovery::ackDuty; attribute :>> fromPhase="AcceptedOrTerminal"; attribute :>> toPhase="SourceLeaseAcked"; attribute :>> qntStep="ackAccepted / ackTerminal"; attribute :>> guardContract="Current identity/revision/root or terminal fence; no old/nested borrow"; attribute :>> leanLaw="ackPreservesCoverage"; attribute :>> sourceAnchors="mem.c:3898-3965;gambit.h.in:10402"; }
part transition4:Transition { ref part :>> need=GambitBootstrapRootRecovery::ackDuty; attribute :>> fromPhase="SourceLeaseAcked"; attribute :>> toPhase="SourcePinReleased"; attribute :>> qntStep="releaseSourcePin"; attribute :>> guardContract="No scanner/borrower holds old view; natural frame map remains"; attribute :>> leanLaw="readerPreventsPhysicalRelease"; attribute :>> sourceAnchors="mem.c:3898-3965,6854-6865"; }
part transition5:Transition { ref part :>> need=GambitBootstrapRootRecovery::ackDuty; attribute :>> fromPhase="AckReplyLost"; attribute :>> toPhase="SameAckRecorded"; attribute :>> qntStep="loseReply / replayAck"; attribute :>> guardContract="Canonical same lease is already acknowledged; no second decrement"; attribute :>> leanLaw="oneGuardedAck"; attribute :>> sourceAnchors="setup.c:1155-1178;proposed canonical lease progress"; }
part transition6:Transition { ref part :>> need=GambitBootstrapRootRecovery::restoreDuty; attribute :>> fromPhase="LivePausedParent"; attribute :>> toPhase="NewBinding"; attribute :>> qntStep="restoreParent / reloadParent"; attribute :>> guardContract="New map/generation/epoch before use; old source token targets old pin only"; attribute :>> leanLaw="ackDoesNotDropRestoredPin"; attribute :>> sourceAnchors="mem.c:4529-4561;_thread.scm:5047-5077"; }
part transition7:Transition { ref part :>> need=GambitBootstrapRootRecovery::restoreDuty; attribute :>> fromPhase="NewBinding"; attribute :>> toPhase="RawUse"; attribute :>> qntStep="borrowParent / freezeParent"; attribute :>> guardContract="Only live same-native-invocation binding; no stale loaded epoch/generation"; attribute :>> leanLaw="restoreStopsOldBorrow"; attribute :>> sourceAnchors="_kernel.scm:1026-1066;gambit.h.in:10402"; }
part transition8:Transition { ref part :>> need=GambitBootstrapRootRecovery::unwindDuty; attribute :>> fromPhase="PendingOrAccepted"; attribute :>> toPhase="VmOwnedClosing"; attribute :>> qntStep="takeVmCustody / exitParent"; attribute :>> guardContract="Stable VM view/key accepted and future publication closed before nonlocal exit"; attribute :>> leanLaw="exitRequiresEscrow"; attribute :>> sourceAnchors="_ptree2.scm:3238-3251;setup.c:1109-1111,3350-3423"; }
part transition9:Transition { ref part :>> need=GambitBootstrapRootRecovery::unwindDuty; attribute :>> fromPhase="VmOwnedClosing"; attribute :>> toPhase="TerminalOrRootHeld"; attribute :>> qntStep="cancelPending / observeConsumerDrain / retireAccepted"; attribute :>> guardContract="No root retirement over consumer or collector read; preserve original status"; attribute :>> leanLaw="releasedPinNeedsRootOrNoValue"; attribute :>> sourceAnchors="setup.c:763-835;c_intf.c:6511-6564"; }
part transition10:Transition { ref part :>> need=GambitBootstrapRootRecovery::retireDuty; attribute :>> fromPhase="TerminalOutcome"; attribute :>> toPhase="OutcomeAccepted"; attribute :>> qntStep="ackTerminalResult"; attribute :>> guardContract="Actual result acceptor owns copied status or rooted payload; distinct from source ACK"; attribute :>> leanLaw="ackKeepsPhysicalPinUntilDrain"; attribute :>> sourceAnchors="setup.c:1155-1178;proposed completion guard"; }
part transition11:Transition { ref part :>> need=GambitBootstrapRootRecovery::retireDuty; attribute :>> fromPhase="TerminalDrained"; attribute :>> toPhase="RetiredKey"; attribute :>> qntStep="sealKey / purge"; attribute :>> guardContract="Result/source ACK plus lookup/scanner/delivery drain; persistent old-key rejection"; attribute :>> leanLaw="retiredKeyNeverAllocates"; attribute :>> sourceAnchors="setup.c:763-803;proposed registry retirement"; }
part transition12:Transition { ref part :>> need=GambitBootstrapRootRecovery::retireDuty; attribute :>> fromPhase="RetiredKey"; attribute :>> toPhase="ExpiredQuery"; attribute :>> qntStep="queryRetiredFence / replayAckFromFence"; attribute :>> guardContract="Return retired/settled disposition without recreation; full old outcome need not remain after proven delivery"; attribute :>> leanLaw="retiredKeyNeverAllocates"; attribute :>> sourceAnchors="proposed generation/frontier gate"; }
part def SourceRoute { ref part need:GambitAssuranceRouting::ModelNeed; attribute sourceAnchors:String; attribute projection:String; attribute failureCustodian:String; attribute status:String; }
part route0:SourceRoute { ref part :>> need=GambitBootstrapRootRecovery::identityDuty; attribute :>> sourceAnchors="_kernel.c:6258-6288;setup.c:1155-1178"; attribute :>> projection="Allocate key before publication; insert-or-find one canonical immutable-intent record; duplicate submits reuse it"; attribute :>> failureCustodian="Live NativeActivation/source lease until VM record custody is known"; attribute :>> status="source-and-C-order-refinement-open"; }
part route1:SourceRoute { ref part :>> need=GambitBootstrapRootRecovery::lookupDuty; attribute :>> sourceAnchors="setup.c:1050-1112;gambit.h.in:11599-11603"; attribute :>> projection="Pin canonical record, read key/descriptor/revision/status only; ACK later revalidates under same control domain"; attribute :>> failureCustodian="VM owns canonical entry/root and lookup lifetime; caller retains exact old source lease"; attribute :>> status="source-and-C-order-refinement-open"; }
part route2:SourceRoute { ref part :>> need=GambitBootstrapRootRecovery::ackDuty; attribute :>> sourceAnchors="mem.c:3898-3965;_kernel.c:26358-26368;gambit.h.in:10402"; attribute :>> projection="Logical ACK closes exact extra origin lease once; physical old-view pin waits for its scanner/borrowers"; attribute :>> failureCustodian="VM descriptor or terminal no-future-effect record owns operation; natural GVM frame retains language roots"; attribute :>> status="source-and-C-order-refinement-open"; }
part route3:SourceRoute { ref part :>> need=GambitBootstrapRootRecovery::restoreDuty; attribute :>> sourceAnchors="mem.c:4529-4561;_thread.scm:4990-5021,5047-5077"; attribute :>> projection="Keep old operation/source token separate from restored binding token; reload current generation/epoch before use"; attribute :>> failureCustodian="Original source backing/VM escrow plus independent restored-parent pin"; attribute :>> status="source-and-C-order-refinement-open"; }
part route4:SourceRoute { ref part :>> need=GambitBootstrapRootRecovery::unwindDuty; attribute :>> sourceAnchors="_ptree2.scm:3238-3251;setup.c:1109-1111,3350-3423"; attribute :>> projection="Before exit, transfer stable view/key, close future publication; pending request cancels, accepted root stays VM owned until drain"; attribute :>> failureCustodian="VM canonical escrow, not stack local progress or unwound owner"; attribute :>> status="source-and-C-order-refinement-open"; }
part route5:SourceRoute { ref part :>> need=GambitBootstrapRootRecovery::retireDuty; attribute :>> sourceAnchors="setup.c:763-803,1155-1178;_kernel.scm:1026-1066"; attribute :>> projection="Keep terminal outcome until delivered/acknowledged; then drain query/scanner/delivery readers and retain anti-replay frontier"; attribute :>> failureCustodian="VM record/result acceptor; per-child native custody remains imported RB-MEMBERS duty"; attribute :>> status="source-and-C-order-refinement-open"; }
part route6:SourceRoute { ref part :>> need=GambitBootstrapRootRecovery::orderDuty; attribute :>> sourceAnchors="setup.c:763-803,1155-1178;_kernel.scm:1026-1066"; attribute :>> projection="Insert/close/query/ACK/restore/purge actual C order and lifetime"; attribute :>> failureCustodian="VM record/result acceptor; per-child native custody remains imported RB-MEMBERS duty"; attribute :>> status="source-and-C-order-refinement-open"; }
part def DiagramNode {  attribute nodeId:String; attribute labelText:String; }
part node0:DiagramNode { attribute :>> nodeId="origin"; attribute :>> labelText="Generated mapped origin and invocation key"; }
part node1:DiagramNode { attribute :>> nodeId="ledger"; attribute :>> labelText="Canonical record and immutable intent"; }
part node2:DiagramNode { attribute :>> nodeId="close"; attribute :>> labelText="GC close: frozen source remains"; }
part node3:DiagramNode { attribute :>> nodeId="accept"; attribute :>> labelText="One accepted descriptor root"; }
part node4:DiagramNode { attribute :>> nodeId="query"; attribute :>> labelText="Pinned status query; revalidate ACK"; }
part node5:DiagramNode { attribute :>> nodeId="ack"; attribute :>> labelText="One extra source lease ACK"; }
part node6:DiagramNode { attribute :>> nodeId="pin"; attribute :>> labelText="Old scanner/borrowers drain"; }
part node7:DiagramNode { attribute :>> nodeId="restore"; attribute :>> labelText="Restored binding and reload"; }
part node8:DiagramNode { attribute :>> nodeId="exitGuard"; attribute :>> labelText="VM escrow and close before exit"; }
part node9:DiagramNode { attribute :>> nodeId="result"; attribute :>> labelText="Terminal result accepted"; }
part node10:DiagramNode { attribute :>> nodeId="fence"; attribute :>> labelText="Drain readers; keep retired-key fence"; }
part node11:DiagramNode { attribute :>> nodeId="late"; attribute :>> labelText="Late retry rejected; no recreation"; }
part def DiagramEdge { ref part producer:DiagramNode; ref part consumer:DiagramNode; attribute labelText:String; }
part edge0:DiagramEdge { ref part :>> producer=node0; ref part :>> consumer=node1; attribute :>> labelText="reserve before possible effect"; }
part edge1:DiagramEdge { ref part :>> producer=node1; ref part :>> consumer=node2; attribute :>> labelText="close wins"; }
part edge2:DiagramEdge { ref part :>> producer=node2; ref part :>> consumer=node1; attribute :>> labelText="same key after reload"; }
part edge3:DiagramEdge { ref part :>> producer=node1; ref part :>> consumer=node3; attribute :>> labelText="register wins"; }
part edge4:DiagramEdge { ref part :>> producer=node3; ref part :>> consumer=node4; attribute :>> labelText="reply lost or status needed"; }
part edge5:DiagramEdge { ref part :>> producer=node1; ref part :>> consumer=node4; attribute :>> labelText="query pending or absent"; }
part edge6:DiagramEdge { ref part :>> producer=node4; ref part :>> consumer=node5; attribute :>> labelText="exact canonical custody"; }
part edge7:DiagramEdge { ref part :>> producer=node5; ref part :>> consumer=node6; attribute :>> labelText="logical is not physical release"; }
part edge8:DiagramEdge { ref part :>> producer=node0; ref part :>> consumer=node7; attribute :>> labelText="same live invocation restores"; }
part edge9:DiagramEdge { ref part :>> producer=node7; ref part :>> consumer=node4; attribute :>> labelText="old source and new pin differ"; }
part edge10:DiagramEdge { ref part :>> producer=node0; ref part :>> consumer=node8; attribute :>> labelText="exception or native escape"; }
part edge11:DiagramEdge { ref part :>> producer=node8; ref part :>> consumer=node4; attribute :>> labelText="VM queries or cancels"; }
part edge12:DiagramEdge { ref part :>> producer=node6; ref part :>> consumer=node9; attribute :>> labelText="separate result handoff"; }
part edge13:DiagramEdge { ref part :>> producer=node9; ref part :>> consumer=node10; attribute :>> labelText="all lifetime gates"; }
part edge14:DiagramEdge { ref part :>> producer=node10; ref part :>> consumer=node11; attribute :>> labelText="persistent rejection after purge"; }
part def ResearchGate { attribute gateId:String; }
part def GateNeed { ref part gate:ResearchGate; ref part need:GambitAssuranceRouting::ModelNeed; }
part gateRow0:ResearchGate { attribute :>> gateId="registration-recovery"; }
part gateNeed0:GateNeed { ref part :>> gate=gateRow0; ref part :>> need=GambitBootstrapRootRecovery::identityDuty; }
part gateNeed1:GateNeed { ref part :>> gate=gateRow0; ref part :>> need=GambitBootstrapRootRecovery::lookupDuty; }
part gateNeed2:GateNeed { ref part :>> gate=gateRow0; ref part :>> need=GambitBootstrapRootRecovery::ackDuty; }
part gateNeed3:GateNeed { ref part :>> gate=gateRow0; ref part :>> need=GambitBootstrapRootRecovery::orderDuty; }
part gateNeed4:GateNeed { ref part :>> gate=gateRow0; ref part :>> need=GambitBootstrapRootRecovery::priorGate; }
part gateNeed5:GateNeed { ref part :>> gate=gateRow0; ref part :>> need=GambitBootstrapRootRecovery::priorView; }
part gateRow1:ResearchGate { attribute :>> gateId="parent-exit-restore"; }
part gateNeed6:GateNeed { ref part :>> gate=gateRow1; ref part :>> need=GambitBootstrapRootRecovery::restoreDuty; }
part gateNeed7:GateNeed { ref part :>> gate=gateRow1; ref part :>> need=GambitBootstrapRootRecovery::unwindDuty; }
part gateNeed8:GateNeed { ref part :>> gate=gateRow1; ref part :>> need=GambitBootstrapRootRecovery::ackDuty; }
part gateNeed9:GateNeed { ref part :>> gate=gateRow1; ref part :>> need=GambitBootstrapRootRecovery::priorScope; }
part gateRow2:ResearchGate { attribute :>> gateId="first-cut"; }
part gateNeed10:GateNeed { ref part :>> gate=gateRow2; ref part :>> need=GambitBootstrapRootRecovery::identityDuty; }
part gateNeed11:GateNeed { ref part :>> gate=gateRow2; ref part :>> need=GambitBootstrapRootRecovery::lookupDuty; }
part gateNeed12:GateNeed { ref part :>> gate=gateRow2; ref part :>> need=GambitBootstrapRootRecovery::ackDuty; }
part gateNeed13:GateNeed { ref part :>> gate=gateRow2; ref part :>> need=GambitBootstrapRootRecovery::restoreDuty; }
part gateNeed14:GateNeed { ref part :>> gate=gateRow2; ref part :>> need=GambitBootstrapRootRecovery::unwindDuty; }
part gateNeed15:GateNeed { ref part :>> gate=gateRow2; ref part :>> need=GambitBootstrapRootRecovery::retireDuty; }
part gateNeed16:GateNeed { ref part :>> gate=gateRow2; ref part :>> need=GambitBootstrapRootRecovery::orderDuty; }
part gateNeed17:GateNeed { ref part :>> gate=gateRow2; ref part :>> need=GambitBootstrapRootRecovery::priorMembers; }
part def AckCut { attribute acceptedOwned:Boolean; attribute terminalSafe:Boolean; attribute keyMatches:Boolean; attribute revisionMatches:Boolean; attribute sourceLeasePending:Boolean; attribute oldBorrow:Boolean; attribute ackRecorded:Boolean; attribute sourceReaders:Integer; attribute sourcePinHeld:Boolean; attribute resultAck:Boolean; attribute retiredKeyGate:Boolean; attribute queryOrDeliveryReaders:Integer; attribute canAck:Boolean=(acceptedOwned or terminalSafe) and keyMatches and revisionMatches and sourceLeasePending and not oldBorrow; attribute canReleaseOldPin:Boolean=ackRecorded and sourcePinHeld and sourceReaders==0 and not oldBorrow; attribute canPurge:Boolean=terminalSafe and ackRecorded and not sourcePinHeld and resultAck and retiredKeyGate and sourceReaders==0 and queryOrDeliveryReaders==0; attribute naturalSchemeSlotsCleared:Integer=0; attribute restoredPinsDroppedByOldAck:Integer=0; }
part accepted:AckCut { attribute :>> acceptedOwned=true; attribute :>> terminalSafe=false; attribute :>> keyMatches=true; attribute :>> revisionMatches=true; attribute :>> sourceLeasePending=true; attribute :>> oldBorrow=false; attribute :>> ackRecorded=false; attribute :>> sourceReaders=0; attribute :>> sourcePinHeld=true; attribute :>> resultAck=false; attribute :>> retiredKeyGate=false; attribute :>> queryOrDeliveryReaders=0; }
part wrongKey:AckCut { attribute :>> acceptedOwned=true; attribute :>> terminalSafe=false; attribute :>> keyMatches=false; attribute :>> revisionMatches=true; attribute :>> sourceLeasePending=true; attribute :>> oldBorrow=false; attribute :>> ackRecorded=false; attribute :>> sourceReaders=0; attribute :>> sourcePinHeld=true; attribute :>> resultAck=false; attribute :>> retiredKeyGate=false; attribute :>> queryOrDeliveryReaders=0; }
part staleQuery:AckCut { attribute :>> acceptedOwned=true; attribute :>> terminalSafe=false; attribute :>> keyMatches=true; attribute :>> revisionMatches=false; attribute :>> sourceLeasePending=true; attribute :>> oldBorrow=false; attribute :>> ackRecorded=false; attribute :>> sourceReaders=0; attribute :>> sourcePinHeld=true; attribute :>> resultAck=false; attribute :>> retiredKeyGate=false; attribute :>> queryOrDeliveryReaders=0; }
part scanAfterAck:AckCut { attribute :>> acceptedOwned=true; attribute :>> terminalSafe=false; attribute :>> keyMatches=true; attribute :>> revisionMatches=true; attribute :>> sourceLeasePending=false; attribute :>> oldBorrow=false; attribute :>> ackRecorded=true; attribute :>> sourceReaders=1; attribute :>> sourcePinHeld=true; attribute :>> resultAck=false; attribute :>> retiredKeyGate=false; attribute :>> queryOrDeliveryReaders=0; }
part restoredOldPin:AckCut { attribute :>> acceptedOwned=true; attribute :>> terminalSafe=false; attribute :>> keyMatches=true; attribute :>> revisionMatches=true; attribute :>> sourceLeasePending=false; attribute :>> oldBorrow=false; attribute :>> ackRecorded=true; attribute :>> sourceReaders=0; attribute :>> sourcePinHeld=true; attribute :>> resultAck=false; attribute :>> retiredKeyGate=false; attribute :>> queryOrDeliveryReaders=0; }
part sourceAckOnly:AckCut { attribute :>> acceptedOwned=false; attribute :>> terminalSafe=true; attribute :>> keyMatches=true; attribute :>> revisionMatches=true; attribute :>> sourceLeasePending=false; attribute :>> oldBorrow=false; attribute :>> ackRecorded=true; attribute :>> sourceReaders=0; attribute :>> sourcePinHeld=false; attribute :>> resultAck=false; attribute :>> retiredKeyGate=true; attribute :>> queryOrDeliveryReaders=0; }
part fullyDelivered:AckCut { attribute :>> acceptedOwned=false; attribute :>> terminalSafe=true; attribute :>> keyMatches=true; attribute :>> revisionMatches=true; attribute :>> sourceLeasePending=false; attribute :>> oldBorrow=false; attribute :>> ackRecorded=true; attribute :>> sourceReaders=0; attribute :>> sourcePinHeld=false; attribute :>> resultAck=true; attribute :>> retiredKeyGate=true; attribute :>> queryOrDeliveryReaders=0; }
requirement def PhysicalAckLaw { subject cut:AckCut; require constraint { not cut.canReleaseOldPin or (cut.ackRecorded and cut.sourceReaders==0 and not cut.oldBorrow) } }
part def RetryPayload { attribute deliveries:Integer; attribute wordBytes:Integer=8; attribute duplicateBytes:Integer=deliveries*wordBytes; attribute canonicalBytes:Integer=wordBytes; attribute slotSavingBytes:Integer=duplicateBytes-canonicalBytes; }
part flat:RetryPayload { attribute :>> deliveries=1; }
part retried:RetryPayload { attribute :>> deliveries=8; }
}
