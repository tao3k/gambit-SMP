package GambitSizeFamilyHoldBalance { private import ScalarValues::*;
part def SourceRow { attribute key:String; attribute path:String; attribute needle:String; attribute obligation:String; }
part source0:SourceRow { attribute :>> key="type-registry"; attribute :>> path="vendor/gambit/gsc/_parms.scm"; attribute :>> needle="(cons size_t-sym"; attribute :>> obligation="three built-in c-type vectors choose forward/back converters; cleanup false"; }
part source1:SourceRow { attribute :>> key="alias-resolution"; attribute :>> path="vendor/gambit/gsc/_ptree2.scm"; attribute :>> needle="(define (c-type-converter to-scmobj? typ from to)"; attribute :>> obligation="vector 2/3 selected by direction; aliases recurse"; }
part source2:SourceRow { attribute :>> key="emit-scope"; attribute :>> path="vendor/gambit/gsc/_ptree2.scm"; attribute :>> needle="(define (c-convert-representation sfun? to-scmobj? typ from to i body)"; attribute :>> obligation="BEGIN wraps body then END; no inference from cleanup bit"; }
part source3:SourceRow { attribute :>> key="arg-direction"; attribute :>> path="vendor/gambit/gsc/_ptree2.scm"; attribute :>> needle="(c-convert-representation sfun? sfun? typ from to i body)"; attribute :>> obligation="SFUN parameter is C to Scheme"; }
part source4:SourceRow { attribute :>> key="result-direction"; attribute :>> path="vendor/gambit/gsc/_ptree2.scm"; attribute :>> needle="(not sfun?)\n           result-typ"; attribute :>> obligation="CFUN result is C to Scheme"; }
part source5:SourceRow { attribute :>> key="cleanup-boolean"; attribute :>> path="vendor/gambit/gsc/_ptree2.scm"; attribute :>> needle="(define (type-needs-cleanup? typ-source)"; attribute :>> obligation="CFUN parameter error cleanup does not fix missing result/input END"; }
part source6:SourceRow { attribute :>> key="wrapper-size"; attribute :>> path="vendor/gambit/lib/c_intf.c"; attribute :>> needle="return ___U64_to_SCMOBJ (___ps, ___U64_from_ULONGLONG (___CAST(___ULONGLONG,x)), obj, arg_num);"; attribute :>> obligation="no-width-loss premise <=64 bits"; }
part source7:SourceRow { attribute :>> key="wrapper-signed"; attribute :>> path="vendor/gambit/lib/c_intf.c"; attribute :>> needle="return ___S64_to_SCMOBJ (___ps, ___S64_from_LONGLONG (___CAST(___LONGLONG,x)), obj, arg_num);"; attribute :>> obligation="ssize_t and ptrdiff_t forward signed"; }
part source8:SourceRow { attribute :>> key="signed-boundary"; attribute :>> path="vendor/gambit/lib/c_intf.c"; attribute :>> needle="if (___S64_fits_in_width (x, ___FIX_WIDTH))"; attribute :>> obligation="inside fixnum vs fresh still bignum"; }
part source9:SourceRow { attribute :>> key="unsigned-boundary"; attribute :>> path="vendor/gambit/lib/c_intf.c"; attribute :>> needle="if (___U64_fits_in_width (x, ___FIX_WIDTH-1))"; attribute :>> obligation="unsigned fixnum uses one fewer sign bit"; }
part source10:SourceRow { attribute :>> key="conversion-owner"; attribute :>> path="vendor/gambit/lib/c_intf.c"; attribute :>> needle="a still object with a reference count of 1 allocated in that"; attribute :>> obligation="nonnull ps owns one native hold; null ps permanent"; }
part source11:SourceRow { attribute :>> key="count-created"; attribute :>> path="vendor/gambit/lib/_mem/object-allocation.inc"; attribute :>> needle="base[___STILL_REFCOUNT] = 1;"; attribute :>> obligation="initial count, not language-root counter"; }
part source12:SourceRow { attribute :>> key="release-primitive"; attribute :>> path="vendor/gambit/lib/_mem/object-allocation.inc"; attribute :>> needle="___EXP_FUNC(___SCMOBJ,___release_scmobj)"; attribute :>> obligation="only still object decremented; immediate/permanent no-op"; }
part source13:SourceRow { attribute :>> key="physical-effect"; attribute :>> path="vendor/gambit/lib/_mem/still-refcount.inc"; attribute :>> needle="___BODY0(obj)[___STILL_REFCOUNT-___STILL_BODY]--;"; attribute :>> obligation="plain decrement; no C23 concurrent ownership proof"; }
part source14:SourceRow { attribute :>> key="gc-roots"; attribute :>> path="vendor/gambit/lib/_mem/object-scanning.inc"; attribute :>> needle="if (base[___STILL_REFCOUNT] == 0)"; attribute :>> obligation="nonzero count is root independent of language reachability"; }
part source15:SourceRow { attribute :>> key="sweep"; attribute :>> path="vendor/gambit/lib/_mem/still-sweep.inc"; attribute :>> needle="if (base[___STILL_MARK] == -1)"; attribute :>> obligation="sweep not per-call release; bignum not foreign payload"; }
part source16:SourceRow { attribute :>> key="whole-teardown"; attribute :>> path="vendor/gambit/lib/_mem/still-sweep.inc"; attribute :>> needle="___HIDDEN void free_still_objs"; attribute :>> obligation="whole-runtime reclamation not balanced conversion hold"; }
part source17:SourceRow { attribute :>> key="rc-separate"; attribute :>> path="vendor/gambit/lib/_mem/rc-allocation.inc"; attribute :>> needle="___HIDDEN void cleanup_rc"; attribute :>> obligation="RC allocation list not still-bignum identity"; }
part source18:SourceRow { attribute :>> key="marker-separate"; attribute :>> path="vendor/gambit/lib/c_intf.c"; attribute :>> needle="___still_obj_refcount_dec (marker);"; attribute :>> obligation="marker is distinct object"; }
part source19:SourceRow { attribute :>> key="sfun-end"; attribute :>> path="vendor/gambit/include/_gambit/foreign_conversion.h.in"; attribute :>> needle="#define ___END_SFUN_SIZE_T_TO_SCMOBJ(c,s,i)}"; attribute :>> obligation="close only; all three audited"; }
part source20:SourceRow { attribute :>> key="cfun-end"; attribute :>> path="vendor/gambit/include/_gambit/foreign_conversion.h.in"; attribute :>> needle="#define ___END_CFUN_SIZE_T_TO_SCMOBJ(c,s)"; attribute :>> obligation="empty; all three audited"; }
part source21:SourceRow { attribute :>> key="result-root"; attribute :>> path="vendor/gambit/include/_gambit/foreign_conversion.h.in"; attribute :>> needle="#define ___CFUN_RESULT ___PSR1"; attribute :>> obligation="converted result writes PSR1 before native release"; }
part source22:SourceRow { attribute :>> key="arg-root"; attribute :>> path="vendor/gambit/include/_gambit/foreign_conversion.h.in"; attribute :>> needle="#define ___SFUN_ARG(i,arg)___PSSTK"; attribute :>> obligation="argument stack publication is not a count decrement"; }
part source23:SourceRow { attribute :>> key="backend-return"; attribute :>> path="vendor/gambit/gsc/_t-c-2.scm"; attribute :>> needle="(define (targ-scan-c-procedure"; attribute :>> obligation="return GC-map/stack work is not native hold retirement"; }
part source24:SourceRow { attribute :>> key="native-types"; attribute :>> path="vendor/gambit/include/_gambit/value_types.h.in"; attribute :>> needle="#define ___SIZE_T size_t"; attribute :>> obligation="standard headers or explicit fallback; macros overridable"; }
part source25:SourceRow { attribute :>> key="fix-width"; attribute :>> path="vendor/gambit/include/_gambit/utilities.h.in"; attribute :>> needle="#define ___FIX_WIDTH"; attribute :>> obligation="non-NAN object bits minus fixnum tag bits"; }
part source26:SourceRow { attribute :>> key="tag-default"; attribute :>> path="vendor/gambit/include/_gambit/object_tags.h.in"; attribute :>> needle="#define ___USE_3_TAG_BITS"; attribute :>> obligation="default 64-bit three-tag profile, not arbitrary overrides"; }
part source27:SourceRow { attribute :>> key="shift-test"; attribute :>> path="vendor/gambit/include/_gambit/native_platform.h.in"; attribute :>> needle="#define ___S64_fits_in_width(val,width)"; attribute :>> obligation="GCC sign-extending signed shift premise"; }
part source28:SourceRow { attribute :>> key="configured-command"; attribute :>> path="vendor/gambit/config.status"; attribute :>> needle="'--disable-smp'"; attribute :>> obligation="historical configured defaults; not SMP/native ABI qualification"; }
part source29:SourceRow { attribute :>> key="configured-width"; attribute :>> path="vendor/gambit/config.log"; attribute :>> needle="ac_cv_sizeof_long=8"; attribute :>> obligation="also voidp 8; aarch64 Darwin; configured GCC16.2"; }
part source30:SourceRow { attribute :>> key="configured-build"; attribute :>> path="vendor/gambit/bin/gambuild-C"; attribute :>> needle="/opt/homebrew/Cellar/gcc/16.2.0/bin/gcc-16"; attribute :>> obligation="default command; invocation env/overrides unobserved"; }
part source31:SourceRow { attribute :>> key="generated-cohort"; attribute :>> path="vendor/gambit/include/gambit.h"; attribute :>> needle="#define ___END_SFUN_SIZE_T_TO_SCMOBJ(c,s,i)}"; attribute :>> obligation="relevant conversion macro agreement not whole cohort identity"; }
part source32:SourceRow { attribute :>> key="sdk-arm"; attribute :>> path="/Library/Developer/CommandLineTools/SDKs/MacOSX26.sdk/usr/include/arm/_types.h"; attribute :>> needle="typedef long                    __darwin_ssize_t;"; attribute :>> obligation="ssize signed long; ptrdiff builtin or long under LP64"; }
part source33:SourceRow { attribute :>> key="sdk-ssize"; attribute :>> path="/Library/Developer/CommandLineTools/SDKs/MacOSX26.sdk/usr/include/sys/_types/_ssize_t.h"; attribute :>> needle="typedef __darwin_ssize_t        ssize_t;"; attribute :>> obligation="sys/types route"; }
part source34:SourceRow { attribute :>> key="gcc-stddef"; attribute :>> path="/opt/homebrew/Cellar/gcc/16.2.0/lib/gcc/current/gcc/aarch64-apple-darwin25/16/include/stddef.h"; attribute :>> needle="typedef __SIZE_TYPE__ size_t;"; attribute :>> obligation="builtin/default unsigned long; ptrdiff signed long, predefines unobserved"; }
part source35:SourceRow { attribute :>> key="gambit-paper"; attribute :>> path="evidence/research/sfun-converter-use-closure/primary-paper.json"; attribute :>> needle="A Portable Implementation of First-Class Continuations"; attribute :>> obligation="Feeley 2000 interoperability motivation; not proof of this defect"; }
part def ProfileRow { attribute key:String; attribute bits:String; attribute fixWidth:String; attribute minimum:String; attribute maximum:String; attribute unsignedMax:String; attribute signedMin:String; attribute signedMax:String; attribute status:String; }
part profile0:ProfileRow { attribute :>> key="Darwin-default"; attribute :>> bits="64"; attribute :>> fixWidth="61"; attribute :>> minimum="-1152921504606846976"; attribute :>> maximum="1152921504606846975"; attribute :>> unsignedMax="18446744073709551615"; attribute :>> signedMin="-9223372036854775808"; attribute :>> signedMax="9223372036854775807"; attribute :>> status="static conditional; overrides and binary cohort unresolved"; }
part profile1:ProfileRow { attribute :>> key="two-tag-override"; attribute :>> bits="64"; attribute :>> fixWidth="62"; attribute :>> minimum="-2305843009213693952"; attribute :>> maximum="2305843009213693951"; attribute :>> unsignedMax="18446744073709551615"; attribute :>> signedMin="-9223372036854775808"; attribute :>> signedMax="9223372036854775807"; attribute :>> status="alternative; not effective-default claim"; }
part profile2:ProfileRow { attribute :>> key="NAN-or-32bit-fixnum"; attribute :>> bits="profile-dependent"; attribute :>> fixWidth="30"; attribute :>> minimum="-536870912"; attribute :>> maximum="536870911"; attribute :>> unsignedMax="native-type-dependent"; attribute :>> signedMin="native-type-dependent"; attribute :>> signedMax="native-type-dependent"; attribute :>> status="alternative; reject receipt with default boundaries"; }
part def RouteRow { attribute component:String; attribute actionName:String; attribute lemma:String; attribute producerAnchor:String; attribute obligationId:String; }
part route0:RouteRow { attribute :>> component="ffi-conversion"; attribute :>> actionName="size_family_hold_balance.selectSizeMax"; attribute :>> lemma="SizeHold.selectSizeMaxPreserves"; attribute :>> producerAnchor="signed-boundary"; attribute :>> obligationId="ownership-preservation"; }
part route1:RouteRow { attribute :>> component="ffi-conversion"; attribute :>> actionName="size_family_hold_balance.selectSignedMin"; attribute :>> lemma="SizeHold.selectSignedMinPreserves"; attribute :>> producerAnchor="signed-boundary"; attribute :>> obligationId="ownership-preservation"; }
part route2:RouteRow { attribute :>> component="ffi-conversion"; attribute :>> actionName="size_family_hold_balance.selectSignedMax"; attribute :>> lemma="SizeHold.selectSignedMaxPreserves"; attribute :>> producerAnchor="signed-boundary"; attribute :>> obligationId="ownership-preservation"; }
part route3:RouteRow { attribute :>> component="ffi-conversion"; attribute :>> actionName="size_family_hold_balance.selectAboveFix"; attribute :>> lemma="SizeHold.selectAboveFixPreserves"; attribute :>> producerAnchor="signed-boundary"; attribute :>> obligationId="ownership-preservation"; }
part route4:RouteRow { attribute :>> component="ffi-conversion"; attribute :>> actionName="size_family_hold_balance.selectAtFix"; attribute :>> lemma="SizeHold.selectAtFixPreserves"; attribute :>> producerAnchor="signed-boundary"; attribute :>> obligationId="ownership-preservation"; }
part route5:RouteRow { attribute :>> component="ffi-conversion"; attribute :>> actionName="size_family_hold_balance.selectMinFix"; attribute :>> lemma="SizeHold.selectMinFixPreserves"; attribute :>> producerAnchor="signed-boundary"; attribute :>> obligationId="ownership-preservation"; }
part route6:RouteRow { attribute :>> component="ffi-conversion"; attribute :>> actionName="size_family_hold_balance.selectBelowFix"; attribute :>> lemma="SizeHold.selectBelowFixPreserves"; attribute :>> producerAnchor="signed-boundary"; attribute :>> obligationId="ownership-preservation"; }
part route7:RouteRow { attribute :>> component="ffi-conversion"; attribute :>> actionName="size_family_hold_balance.convertBoxed"; attribute :>> lemma="SizeHold.convertBoxedPreserves"; attribute :>> producerAnchor="signed-boundary"; attribute :>> obligationId="ownership-preservation"; }
part route8:RouteRow { attribute :>> component="ffi-conversion"; attribute :>> actionName="size_family_hold_balance.convertImmediate"; attribute :>> lemma="SizeHold.convertImmediatePreserves"; attribute :>> producerAnchor="signed-boundary"; attribute :>> obligationId="ownership-preservation"; }
part route9:RouteRow { attribute :>> component="ffi-conversion"; attribute :>> actionName="size_family_hold_balance.conversionFailure"; attribute :>> lemma="SizeHold.conversionFailurePreserves"; attribute :>> producerAnchor="emit-scope"; attribute :>> obligationId="ownership-preservation"; }
part route10:RouteRow { attribute :>> component="ffi-conversion"; attribute :>> actionName="size_family_hold_balance.publishRoot"; attribute :>> lemma="SizeHold.publishRootPreserves"; attribute :>> producerAnchor="emit-scope"; attribute :>> obligationId="ownership-preservation"; }
part route11:RouteRow { attribute :>> component="ffi-conversion"; attribute :>> actionName="size_family_hold_balance.captureArgument"; attribute :>> lemma="SizeHold.captureArgumentPreserves"; attribute :>> producerAnchor="emit-scope"; attribute :>> obligationId="ownership-preservation"; }
part route12:RouteRow { attribute :>> component="ffi-conversion"; attribute :>> actionName="size_family_hold_balance.finishNative"; attribute :>> lemma="SizeHold.finishNativePreserves"; attribute :>> producerAnchor="emit-scope"; attribute :>> obligationId="ownership-preservation"; }
part route13:RouteRow { attribute :>> component="ffi-conversion"; attribute :>> actionName="size_family_hold_balance.enterDrop"; attribute :>> lemma="SizeHold.enterDropPreserves"; attribute :>> producerAnchor="emit-scope"; attribute :>> obligationId="ownership-preservation"; }
part route14:RouteRow { attribute :>> component="ffi-conversion"; attribute :>> actionName="size_family_hold_balance.physicalDrop"; attribute :>> lemma="SizeHold.physicalDropPreserves"; attribute :>> producerAnchor="physical-effect"; attribute :>> obligationId="ownership-preservation"; }
part route15:RouteRow { attribute :>> component="ffi-conversion"; attribute :>> actionName="size_family_hold_balance.commitDrop"; attribute :>> lemma="SizeHold.commitDropPreserves"; attribute :>> producerAnchor="physical-effect"; attribute :>> obligationId="ownership-preservation"; }
part route16:RouteRow { attribute :>> component="ffi-conversion"; attribute :>> actionName="size_family_hold_balance.loseReply"; attribute :>> lemma="SizeHold.loseReplyPreserves"; attribute :>> producerAnchor="emit-scope"; attribute :>> obligationId="ownership-preservation"; }
part route17:RouteRow { attribute :>> component="ffi-conversion"; attribute :>> actionName="size_family_hold_balance.recoverReply"; attribute :>> lemma="SizeHold.recoverReplyPreserves"; attribute :>> producerAnchor="emit-scope"; attribute :>> obligationId="ownership-preservation"; }
part route18:RouteRow { attribute :>> component="ffi-conversion"; attribute :>> actionName="size_family_hold_balance.dropCapture"; attribute :>> lemma="SizeHold.dropCapturePreserves"; attribute :>> producerAnchor="emit-scope"; attribute :>> obligationId="ownership-preservation"; }
part route19:RouteRow { attribute :>> component="ffi-conversion"; attribute :>> actionName="size_family_hold_balance.dropRoot"; attribute :>> lemma="SizeHold.dropRootPreserves"; attribute :>> producerAnchor="emit-scope"; attribute :>> obligationId="ownership-preservation"; }
part route20:RouteRow { attribute :>> component="ffi-conversion"; attribute :>> actionName="size_family_hold_balance.beginGc"; attribute :>> lemma="SizeHold.beginGcPreserves"; attribute :>> producerAnchor="gc-roots"; attribute :>> obligationId="ownership-preservation"; }
part route21:RouteRow { attribute :>> component="ffi-conversion"; attribute :>> actionName="size_family_hold_balance.finishGc"; attribute :>> lemma="SizeHold.finishGcPreserves"; attribute :>> producerAnchor="gc-roots"; attribute :>> obligationId="ownership-preservation"; }
part def GainRow { attribute key:String; attribute benefit:String; attribute cost:String; attribute condition:String; attribute refutation:String; }
part gain0:GainRow { attribute :>> key="retained-native-holds"; attribute :>> benefit="B successful boxed conversions can discharge B extra holds"; attribute :>> cost="one release decision per N conversions; B physical decrements"; attribute :>> condition="same object; unique owner; no explicit manual double drop"; attribute :>> refutation="no boxed conversions B=0; arbitrary user-owned decrements admitted"; }
part gain1:GainRow { attribute :>> key="GC-root-pressure"; attribute :>> benefit="remove B accidental native roots after true last use"; attribute :>> cost="language roots/captured continuations still scanned as required"; attribute :>> condition="otherwise unreachable objects; k later collections gives at most B*k avoided root visits"; attribute :>> refutation="live captured objects cannot be skipped; not a time or RSS estimate"; }
part gain2:GainRow { attribute :>> key="generated-contract"; attribute :>> benefit="one direction-aware plan replaces six inconsistent size-family END responsibilities"; attribute :>> cost="success/failure/root/escape metadata and generator validation"; attribute :>> condition="producer and consumer same ABI; all generated users migrated"; attribute :>> refutation="old modules or handwritten converters bypass plan"; }
part gain3:GainRow { attribute :>> key="language-choice"; attribute :>> benefit="C23 solves this ownership defect without a second runtime language"; attribute :>> cost="guard and root/GC integration remain explicit in C or Zig"; attribute :>> condition="required modern C mainline"; attribute :>> refutation="Zig syntax or no-GC property does not discharge Scheme holds"; }
part def ContractRow { attribute fromNode:String; attribute toNode:String; attribute custody:String; }
part contract0:ContractRow { attribute :>> fromNode="Scheme type registry"; attribute :>> toNode="Direction-aware conversion plan"; attribute :>> custody="name + type bounds + effect summary"; }
part contract1:ContractRow { attribute :>> fromNode="Direction-aware conversion plan"; attribute :>> toNode="C23 SFUN input"; attribute :>> custody="native hold through final native use"; }
part contract2:ContractRow { attribute :>> fromNode="Direction-aware conversion plan"; attribute :>> toNode="C23 CFUN result"; attribute :>> custody="publish PSR1 as live root before drop"; }
part contract3:ContractRow { attribute :>> fromNode="C23 SFUN input"; attribute :>> toNode="Stable completion guard"; attribute :>> custody="escape transfers exact attempt identity"; }
part contract4:ContractRow { attribute :>> fromNode="C23 CFUN result"; attribute :>> toNode="Stable completion guard"; attribute :>> custody="guard registered before abandonment boundary"; }
part contract5:ContractRow { attribute :>> fromNode="Stable completion guard"; attribute :>> toNode="Physical drop"; attribute :>> custody="GC-excluded non-abandonable effect and record"; }
part contract6:ContractRow { attribute :>> fromNode="Physical drop"; attribute :>> toNode="Receipt ledger"; attribute :>> custody="query same attempt after lost reply; never repeat decrement"; }
part contract7:ContractRow { attribute :>> fromNode="Receipt ledger"; attribute :>> toNode="GC roots and sweep"; attribute :>> custody="zero native hold; language roots keep captured values live"; }
part def ReleaserRow { attribute key:String; attribute effect:String; attribute identity:String; attribute decision:String; }
part releaser0:ReleaserRow { attribute :>> key="release_scmobj"; attribute :>> effect="still count decrement; immediate/permanent no-op"; attribute :>> identity="the exact converted object"; attribute :>> decision="required on successful native-held conversion"; }
part releaser1:ReleaserRow { attribute :>> key="raw still refcount dec"; attribute :>> effect="unconditional decrement"; attribute :>> identity="only same still object and explicit owner"; attribute :>> decision="not safe for fixnum; duplicate/manual drops forbidden"; }
part releaser2:ReleaserRow { attribute :>> key="generated END"; attribute :>> effect="three SFUN close-only + three CFUN empty"; attribute :>> identity="same converted object"; attribute :>> decision="missing effect in closed generated scope"; }
part releaser3:ReleaserRow { attribute :>> key="SFUN_ARG / CFUN_RESULT / backend return"; attribute :>> effect="root assignment / GC map / register reload"; attribute :>> identity="converted value"; attribute :>> decision="does not decrement native hold"; }
part releaser4:ReleaserRow { attribute :>> key="GC setup / sweep"; attribute :>> effect="nonzero held objects remain roots; unmarked freed"; attribute :>> identity="same still object"; attribute :>> decision="cannot fix leaked count1"; }
part releaser5:ReleaserRow { attribute :>> key="marker invalidation"; attribute :>> effect="marker decrement"; attribute :>> identity="distinct marker identity"; attribute :>> decision="cannot settle numeric argument"; }
part releaser6:ReleaserRow { attribute :>> key="cleanup_rc / release_rc"; attribute :>> effect="RC payload/free linked native cell"; attribute :>> identity="different allocation/header"; attribute :>> decision="cannot settle numeric bignum"; }
part releaser7:ReleaserRow { attribute :>> key="foreign release callback"; attribute :>> effect="foreign subtype destructor"; attribute :>> identity="bignum has no foreign payload"; attribute :>> decision="cannot settle numeric bignum"; }
part releaser8:ReleaserRow { attribute :>> key="free_still_objs"; attribute :>> effect="whole storage teardown"; attribute :>> identity="all remaining still objects"; attribute :>> decision="ends VM lifetime, not per-call balance"; }
part releaser9:ReleaserRow { attribute :>> key="custom C / Scheme decrement"; attribute :>> effect="arbitrary explicit effect"; attribute :>> identity="identity must be proven"; attribute :>> decision="exclude or transfer single ownership; open-world aliases unresolved"; }
part def NeedRow { attribute key:String; attribute status:String; attribute condition:String; }
part need0:NeedRow { attribute :>> key="numeric-boundaries"; attribute :>> status="conditional formal"; attribute :>> condition="named LP64 profile; actual predefines/overrides unobserved"; }
part need1:NeedRow { attribute :>> key="closed-source-mismatch"; attribute :>> status="source path argument"; attribute :>> condition="nonnull ps boxed success and no explicit manual owner; not native leak test"; }
part need2:NeedRow { attribute :>> key="ownership-preservation"; attribute :>> status="formal"; attribute :>> condition="one stable attempt; critical section cannot be abandoned; root publication truthful"; }
part need3:NeedRow { attribute :>> key="native-guard-issuer"; attribute :>> status="unresolved"; attribute :>> condition="actual guard must survive unwind and own scanner-visible root"; }
part need4:NeedRow { attribute :>> key="C23-GC-exclusion"; attribute :>> status="unresolved"; attribute :>> condition="plain old counter not atomic; root freeze/GC and owner thread handshake required"; }
part need5:NeedRow { attribute :>> key="generated-cohort"; attribute :>> status="unresolved"; attribute :>> condition="current header/runtime/generated binary not proven same cohort"; }
part need6:NeedRow { attribute :>> key="all-custom-writers"; attribute :>> status="unresolved"; attribute :>> condition="public/custom FFI may manually change count"; }
part need7:NeedRow { attribute :>> key="retirement"; attribute :>> status="unresolved"; attribute :>> condition="descriptors/code/live captures/old modules must drain before removal"; }
}
