package GambitStorageIndexTransactions { private import ScalarValues::*;
part def Owner { attribute componentId:String; }
part storageOwner:Owner { attribute :>> componentId="storage"; }
part def SourceRow { attribute key:String; attribute path:String; attribute needle:String; attribute obligation:String; }
part source0:SourceRow { attribute :>> key="tcl-call"; attribute :>> path="vendor/gambit/examples/tcltk/tcltk.scm"; attribute :>> needle="char *result = tcltk_call"; attribute :>> obligation="Raw data_rc copy before generated entry; no explicit lease here"; }
part source1:SourceRow { attribute :>> key="tcl-delete-native"; attribute :>> path="vendor/gambit/examples/tcltk/tcltk.scm"; attribute :>> needle="___EXT(___release_rc) (___CAST(void*,client_data));"; attribute :>> obligation="Delete adapter must close admission and defer physical release while leased"; }
part source2:SourceRow { attribute :>> key="tcl-install"; attribute :>> path="vendor/gambit/examples/tcltk/tcltk.scm"; attribute :>> needle="___EXT(___set_data_rc) (cd, vect);"; attribute :>> obligation="Tcl caller initializes payload before command publication; raw setter remains public"; }
part source3:SourceRow { attribute :>> key="rc-register"; attribute :>> path="vendor/gambit/lib/_mem/rc-allocation.inc"; attribute :>> needle="tail->next = h;"; attribute :>> obligation="Plain list insertion requires owner and collector exclusion"; }
part source4:SourceRow { attribute :>> key="rc-free"; attribute :>> path="vendor/gambit/lib/_mem/rc-allocation.inc"; attribute :>> needle="if (--h->refcount == 0)"; attribute :>> obligation="Nonatomic decrement and unlink are not safe arbitrary-thread admission"; }
part source5:SourceRow { attribute :>> key="rc-write"; attribute :>> path="vendor/gambit/lib/_mem/rc-allocation.inc"; attribute :>> needle="h->data = val;"; attribute :>> obligation="All semantic writers must join freeze/generation protocol or deny admission"; }
part source6:SourceRow { attribute :>> key="rc-cleanup"; attribute :>> path="vendor/gambit/lib/_mem/rc-allocation.inc"; attribute :>> needle="___HIDDEN void cleanup_rc"; attribute :>> obligation="Bulk cleanup frees chain independent of per-entry leases"; }
part source7:SourceRow { attribute :>> key="rc-scan"; attribute :>> path="vendor/gambit/lib/_mem/rc-roots.inc"; attribute :>> needle="mark_array (work, &h->data, 1);"; attribute :>> obligation="Actual GC slot update; target private carrier is not implicitly scanned"; }
part source8:SourceRow { attribute :>> key="retire-refuse"; attribute :>> path="vendor/gambit/lib/_mem/capacity-resize.inc"; attribute :>> needle="return 0; /* no freeze receipt for external RC/native borrowers */"; attribute :>> obligation="Current processor retirement refuses nonempty RC rather than manufacturing a lease"; }
part source9:SourceRow { attribute :>> key="setter-export"; attribute :>> path="vendor/gambit/lib/setup.c"; attribute :>> needle="= ___set_data_rc;"; attribute :>> obligation="Public GSTATE function pointer permits indirect/out-of-tree callers; lexical sites do not close writer authority"; }
part source10:SourceRow { attribute :>> key="view-drain"; attribute :>> path="vendor/gambit/lib/_mem/collection-round.inc"; attribute :>> needle="BARRIER(); /* no worker may retain a stopped root view past this cut */"; attribute :>> obligation="Root view grace cut precedes ordinary execution"; }
part source11:SourceRow { attribute :>> key="task-claim-body"; attribute :>> path="vendor/gambit/include/_gambit/vm_state.h.in"; attribute :>> needle="t->incarnation != t->origin->incarnation"; attribute :>> obligation="Claim dereferences descriptor/origin before CAS; not a safe retain of freed storage"; }
part source12:SourceRow { attribute :>> key="cas-sync-builtins"; attribute :>> path="vendor/gambit/include/_gambit/activity_log.h.in"; attribute :>> needle="__sync_val_compare_and_swap(p,oldval,newval)"; attribute :>> obligation="One alternative implementation; effective Darwin selection remains open"; }
part source13:SourceRow { attribute :>> key="header-config"; attribute :>> path="vendor/gambit/include/makefile.in"; attribute :>> needle="HEADER_CONFIG ="; attribute :>> obligation="Ordered configured header composition; generated artifact provenance open"; }
part source14:SourceRow { attribute :>> key="mem-order"; attribute :>> path="vendor/gambit/lib/mem.c"; attribute :>> needle="#include \"_mem/rc-allocation.inc\""; attribute :>> obligation="Bind new implementation inclusion path/order"; }
part source15:SourceRow { attribute :>> key="rc-layout"; attribute :>> path="vendor/gambit/include/_gambit/memory_state.h.in"; attribute :>> needle="typedef struct ___rc_header_struct"; attribute :>> obligation="Links/refcount/data do not contain VM storage identity or extent"; }
part source16:SourceRow { attribute :>> key="rc-allocation"; attribute :>> path="vendor/gambit/lib/_mem/rc-allocation.inc"; attribute :>> needle="___ALLOC_MEM(bytes + sizeof (___rc_header))"; attribute :>> obligation="Allocation lacks durable identity and checked-extent receipt"; }
part def BindingRow { attribute actionName:String; attribute lemma:String; }
part binding0:BindingRow { attribute :>> actionName="storage_index_transactions.chooseAdjacent"; attribute :>> lemma="StorageIndex.chooseAdjacentPreserves"; }
part binding1:BindingRow { attribute :>> actionName="storage_index_transactions.observeA"; attribute :>> lemma="StorageIndex.observeAPreserves"; }
part binding2:BindingRow { attribute :>> actionName="storage_index_transactions.reserveA"; attribute :>> lemma="StorageIndex.reserveAPreserves"; }
part binding3:BindingRow { attribute :>> actionName="storage_index_transactions.prepareA"; attribute :>> lemma="StorageIndex.prepareAPreserves"; }
part binding4:BindingRow { attribute :>> actionName="storage_index_transactions.publishA"; attribute :>> lemma="StorageIndex.publishAPreserves"; }
part binding5:BindingRow { attribute :>> actionName="storage_index_transactions.queryA"; attribute :>> lemma="StorageIndex.queryAPreserves"; }
part binding6:BindingRow { attribute :>> actionName="storage_index_transactions.borrowA"; attribute :>> lemma="StorageIndex.borrowAPreserves"; }
part binding7:BindingRow { attribute :>> actionName="storage_index_transactions.returnA"; attribute :>> lemma="StorageIndex.returnAPreserves"; }
part binding8:BindingRow { attribute :>> actionName="storage_index_transactions.scanA"; attribute :>> lemma="StorageIndex.scanAPreserves"; }
part binding9:BindingRow { attribute :>> actionName="storage_index_transactions.finishScanA"; attribute :>> lemma="StorageIndex.finishScanAPreserves"; }
part binding10:BindingRow { attribute :>> actionName="storage_index_transactions.revokeA"; attribute :>> lemma="StorageIndex.revokeAPreserves"; }
part binding11:BindingRow { attribute :>> actionName="storage_index_transactions.drainA"; attribute :>> lemma="StorageIndex.drainAPreserves"; }
part binding12:BindingRow { attribute :>> actionName="storage_index_transactions.abortA"; attribute :>> lemma="StorageIndex.abortAPreserves"; }
part binding13:BindingRow { attribute :>> actionName="storage_index_transactions.settleA"; attribute :>> lemma="StorageIndex.settleAPreserves"; }
part binding14:BindingRow { attribute :>> actionName="storage_index_transactions.rejectOldA"; attribute :>> lemma="StorageIndex.rejectOldAPreserves"; }
part binding15:BindingRow { attribute :>> actionName="storage_index_transactions.observeB"; attribute :>> lemma="StorageIndex.observeBPreserves"; }
part binding16:BindingRow { attribute :>> actionName="storage_index_transactions.reserveB"; attribute :>> lemma="StorageIndex.reserveBPreserves"; }
part binding17:BindingRow { attribute :>> actionName="storage_index_transactions.prepareB"; attribute :>> lemma="StorageIndex.prepareBPreserves"; }
part binding18:BindingRow { attribute :>> actionName="storage_index_transactions.publishB"; attribute :>> lemma="StorageIndex.publishBPreserves"; }
part binding19:BindingRow { attribute :>> actionName="storage_index_transactions.queryB"; attribute :>> lemma="StorageIndex.queryBPreserves"; }
part binding20:BindingRow { attribute :>> actionName="storage_index_transactions.borrowB"; attribute :>> lemma="StorageIndex.borrowBPreserves"; }
part binding21:BindingRow { attribute :>> actionName="storage_index_transactions.returnB"; attribute :>> lemma="StorageIndex.returnBPreserves"; }
part binding22:BindingRow { attribute :>> actionName="storage_index_transactions.scanB"; attribute :>> lemma="StorageIndex.scanBPreserves"; }
part binding23:BindingRow { attribute :>> actionName="storage_index_transactions.finishScanB"; attribute :>> lemma="StorageIndex.finishScanBPreserves"; }
part binding24:BindingRow { attribute :>> actionName="storage_index_transactions.revokeB"; attribute :>> lemma="StorageIndex.revokeBPreserves"; }
part binding25:BindingRow { attribute :>> actionName="storage_index_transactions.drainB"; attribute :>> lemma="StorageIndex.drainBPreserves"; }
part binding26:BindingRow { attribute :>> actionName="storage_index_transactions.abortB"; attribute :>> lemma="StorageIndex.abortBPreserves"; }
part binding27:BindingRow { attribute :>> actionName="storage_index_transactions.settleB"; attribute :>> lemma="StorageIndex.settleBPreserves"; }
part binding28:BindingRow { attribute :>> actionName="storage_index_transactions.rejectOldB"; attribute :>> lemma="StorageIndex.rejectOldBPreserves"; }
part binding29:BindingRow { attribute :>> actionName="storage_index_transactions.sourceWrite"; attribute :>> lemma="StorageIndex.sourceWritePreserves"; }
part binding30:BindingRow { attribute :>> actionName="storage_index_transactions.closeIndex"; attribute :>> lemma="StorageIndex.closeIndexPreserves"; }
part binding31:BindingRow { attribute :>> actionName="storage_index_transactions.reuse"; attribute :>> lemma="StorageIndex.reusePreserves"; }
part def RouteRow { attribute component:String; attribute actionName:String; attribute lemma:String; attribute producerAnchor:String; attribute obligationId:String; }
part route0:RouteRow { ref :>> owner = storageOwner; attribute :>> actionName="storage_index_transactions.chooseAdjacent"; attribute :>> lemma="StorageIndex.chooseAdjacentPreserves"; attribute :>> producerAnchor="rc-register"; attribute :>> obligationId="ST-storage"; }
part route1:RouteRow { ref :>> owner = storageOwner; attribute :>> actionName="storage_index_transactions.observeA"; attribute :>> lemma="StorageIndex.observeAPreserves"; attribute :>> producerAnchor="rc-register"; attribute :>> obligationId="ST-storage"; }
part route2:RouteRow { ref :>> owner = storageOwner; attribute :>> actionName="storage_index_transactions.reserveA"; attribute :>> lemma="StorageIndex.reserveAPreserves"; attribute :>> producerAnchor="rc-register"; attribute :>> obligationId="ST-storage"; }
part route3:RouteRow { ref :>> owner = storageOwner; attribute :>> actionName="storage_index_transactions.prepareA"; attribute :>> lemma="StorageIndex.prepareAPreserves"; attribute :>> producerAnchor="rc-register"; attribute :>> obligationId="ST-storage"; }
part route4:RouteRow { ref :>> owner = storageOwner; attribute :>> actionName="storage_index_transactions.publishA"; attribute :>> lemma="StorageIndex.publishAPreserves"; attribute :>> producerAnchor="rc-register"; attribute :>> obligationId="ST-storage"; }
part route5:RouteRow { ref :>> owner = storageOwner; attribute :>> actionName="storage_index_transactions.queryA"; attribute :>> lemma="StorageIndex.queryAPreserves"; attribute :>> producerAnchor="rc-cleanup"; attribute :>> obligationId="ST-lifetime"; }
part route6:RouteRow { ref :>> owner = storageOwner; attribute :>> actionName="storage_index_transactions.borrowA"; attribute :>> lemma="StorageIndex.borrowAPreserves"; attribute :>> producerAnchor="tcl-call"; attribute :>> obligationId="ST-execution"; }
part route7:RouteRow { ref :>> owner = storageOwner; attribute :>> actionName="storage_index_transactions.returnA"; attribute :>> lemma="StorageIndex.returnAPreserves"; attribute :>> producerAnchor="tcl-call"; attribute :>> obligationId="ST-execution"; }
part route8:RouteRow { ref :>> owner = storageOwner; attribute :>> actionName="storage_index_transactions.scanA"; attribute :>> lemma="StorageIndex.scanAPreserves"; attribute :>> producerAnchor="rc-scan"; attribute :>> obligationId="ST-roots"; }
part route9:RouteRow { ref :>> owner = storageOwner; attribute :>> actionName="storage_index_transactions.finishScanA"; attribute :>> lemma="StorageIndex.finishScanAPreserves"; attribute :>> producerAnchor="rc-scan"; attribute :>> obligationId="ST-roots"; }
part route10:RouteRow { ref :>> owner = storageOwner; attribute :>> actionName="storage_index_transactions.revokeA"; attribute :>> lemma="StorageIndex.revokeAPreserves"; attribute :>> producerAnchor="rc-cleanup"; attribute :>> obligationId="ST-lifetime"; }
part route11:RouteRow { ref :>> owner = storageOwner; attribute :>> actionName="storage_index_transactions.drainA"; attribute :>> lemma="StorageIndex.drainAPreserves"; attribute :>> producerAnchor="rc-cleanup"; attribute :>> obligationId="ST-lifetime"; }
part route12:RouteRow { ref :>> owner = storageOwner; attribute :>> actionName="storage_index_transactions.abortA"; attribute :>> lemma="StorageIndex.abortAPreserves"; attribute :>> producerAnchor="rc-cleanup"; attribute :>> obligationId="ST-lifetime"; }
part route13:RouteRow { ref :>> owner = storageOwner; attribute :>> actionName="storage_index_transactions.settleA"; attribute :>> lemma="StorageIndex.settleAPreserves"; attribute :>> producerAnchor="rc-cleanup"; attribute :>> obligationId="ST-lifetime"; }
part route14:RouteRow { ref :>> owner = storageOwner; attribute :>> actionName="storage_index_transactions.rejectOldA"; attribute :>> lemma="StorageIndex.rejectOldAPreserves"; attribute :>> producerAnchor="rc-cleanup"; attribute :>> obligationId="ST-lifetime"; }
part route15:RouteRow { ref :>> owner = storageOwner; attribute :>> actionName="storage_index_transactions.observeB"; attribute :>> lemma="StorageIndex.observeBPreserves"; attribute :>> producerAnchor="rc-register"; attribute :>> obligationId="ST-storage"; }
part route16:RouteRow { ref :>> owner = storageOwner; attribute :>> actionName="storage_index_transactions.reserveB"; attribute :>> lemma="StorageIndex.reserveBPreserves"; attribute :>> producerAnchor="rc-register"; attribute :>> obligationId="ST-storage"; }
part route17:RouteRow { ref :>> owner = storageOwner; attribute :>> actionName="storage_index_transactions.prepareB"; attribute :>> lemma="StorageIndex.prepareBPreserves"; attribute :>> producerAnchor="rc-register"; attribute :>> obligationId="ST-storage"; }
part route18:RouteRow { ref :>> owner = storageOwner; attribute :>> actionName="storage_index_transactions.publishB"; attribute :>> lemma="StorageIndex.publishBPreserves"; attribute :>> producerAnchor="rc-register"; attribute :>> obligationId="ST-storage"; }
part route19:RouteRow { ref :>> owner = storageOwner; attribute :>> actionName="storage_index_transactions.queryB"; attribute :>> lemma="StorageIndex.queryBPreserves"; attribute :>> producerAnchor="rc-cleanup"; attribute :>> obligationId="ST-lifetime"; }
part route20:RouteRow { ref :>> owner = storageOwner; attribute :>> actionName="storage_index_transactions.borrowB"; attribute :>> lemma="StorageIndex.borrowBPreserves"; attribute :>> producerAnchor="tcl-call"; attribute :>> obligationId="ST-execution"; }
part route21:RouteRow { ref :>> owner = storageOwner; attribute :>> actionName="storage_index_transactions.returnB"; attribute :>> lemma="StorageIndex.returnBPreserves"; attribute :>> producerAnchor="tcl-call"; attribute :>> obligationId="ST-execution"; }
part route22:RouteRow { ref :>> owner = storageOwner; attribute :>> actionName="storage_index_transactions.scanB"; attribute :>> lemma="StorageIndex.scanBPreserves"; attribute :>> producerAnchor="rc-scan"; attribute :>> obligationId="ST-roots"; }
part route23:RouteRow { ref :>> owner = storageOwner; attribute :>> actionName="storage_index_transactions.finishScanB"; attribute :>> lemma="StorageIndex.finishScanBPreserves"; attribute :>> producerAnchor="rc-scan"; attribute :>> obligationId="ST-roots"; }
part route24:RouteRow { ref :>> owner = storageOwner; attribute :>> actionName="storage_index_transactions.revokeB"; attribute :>> lemma="StorageIndex.revokeBPreserves"; attribute :>> producerAnchor="rc-cleanup"; attribute :>> obligationId="ST-lifetime"; }
part route25:RouteRow { ref :>> owner = storageOwner; attribute :>> actionName="storage_index_transactions.drainB"; attribute :>> lemma="StorageIndex.drainBPreserves"; attribute :>> producerAnchor="rc-cleanup"; attribute :>> obligationId="ST-lifetime"; }
part route26:RouteRow { ref :>> owner = storageOwner; attribute :>> actionName="storage_index_transactions.abortB"; attribute :>> lemma="StorageIndex.abortBPreserves"; attribute :>> producerAnchor="rc-cleanup"; attribute :>> obligationId="ST-lifetime"; }
part route27:RouteRow { ref :>> owner = storageOwner; attribute :>> actionName="storage_index_transactions.settleB"; attribute :>> lemma="StorageIndex.settleBPreserves"; attribute :>> producerAnchor="rc-cleanup"; attribute :>> obligationId="ST-lifetime"; }
part route28:RouteRow { ref :>> owner = storageOwner; attribute :>> actionName="storage_index_transactions.rejectOldB"; attribute :>> lemma="StorageIndex.rejectOldBPreserves"; attribute :>> producerAnchor="rc-cleanup"; attribute :>> obligationId="ST-lifetime"; }
part route29:RouteRow { ref :>> owner = storageOwner; attribute :>> actionName="storage_index_transactions.sourceWrite"; attribute :>> lemma="StorageIndex.sourceWritePreserves"; attribute :>> producerAnchor="rc-write"; attribute :>> obligationId="ST-writers"; }
part route30:RouteRow { ref :>> owner = storageOwner; attribute :>> actionName="storage_index_transactions.closeIndex"; attribute :>> lemma="StorageIndex.closeIndexPreserves"; attribute :>> producerAnchor="rc-register"; attribute :>> obligationId="ST-storage"; }
part route31:RouteRow { ref :>> owner = storageOwner; attribute :>> actionName="storage_index_transactions.reuse"; attribute :>> lemma="StorageIndex.reusePreserves"; attribute :>> producerAnchor="rc-free"; attribute :>> obligationId="ST-storage"; }
part def NeedRow { attribute key:String; attribute kind:String; attribute path:String; attribute scope:String; ref owner:Owner; }
part need0:NeedRow { attribute :>> key="ST-formal"; attribute :>> kind="formal"; attribute :>> path="dev/refactoring/modern-c/models/quint/storage_index_transactions.qnt"; attribute :>> scope="two fixed operation identities; alias leases; two storage generations; safety only";  ref :>> owner = storageOwner; }
part need1:NeedRow { attribute :>> key="ST-bridge"; attribute :>> kind="bridge"; attribute :>> path="dev/refactoring/modern-c/models/lean/StorageIndex.lean"; attribute :>> scope="restricted typed IR all-step induction; trusted parser and emitter";  ref :>> owner = storageOwner; }
part need2:NeedRow { attribute :>> key="ST-storage"; attribute :>> kind="native"; attribute :>> path="vendor/gambit/lib/_mem/rc-allocation.inc"; attribute :>> scope="complete allocator provenance and overlap transaction issuer absent";  ref :>> owner = storageOwner; }
part need3:NeedRow { attribute :>> key="ST-roots"; attribute :>> kind="native"; attribute :>> path="vendor/gambit/lib/_mem/rc-roots.inc"; attribute :>> scope="private-root protection and every-round registry scan product unproved";  ref :>> owner = storageOwner; }
part need4:NeedRow { attribute :>> key="ST-writers"; attribute :>> kind="native"; attribute :>> path="vendor/gambit/lib/setup.c"; attribute :>> scope="indirect exported setters and all native borrowers not closed";  ref :>> owner = storageOwner; }
part need5:NeedRow { attribute :>> key="ST-platform"; attribute :>> kind="native"; attribute :>> path="vendor/gambit/include/_gambit/activity_log.h.in"; attribute :>> scope="effective Darwin C23 mutex and atomic ABI unqualified";  ref :>> owner = storageOwner; }
part need6:NeedRow { attribute :>> key="ST-lifetime"; attribute :>> kind="native"; attribute :>> path="vendor/gambit/lib/_mem/memory-lifecycle.inc"; attribute :>> scope="unknown-result custodian and real cleanup retirement signer absent";  ref :>> owner = storageOwner; }
part need7:NeedRow { attribute :>> key="ST-execution"; attribute :>> kind="native"; attribute :>> path="vendor/gambit/examples/tcltk/tcltk.scm"; attribute :>> scope="nested callbacks continuation and exception completion guard product open";  ref :>> owner = storageOwner; }
part def ContractRow { attribute fromNode:String; attribute toNode:String; attribute custody:String; }
part contract0:ContractRow { attribute :>> fromNode="CallerA"; attribute :>> toNode="OwnerTransaction"; attribute :>> custody="reserve A after exact revision and generation validation"; }
part contract1:ContractRow { attribute :>> fromNode="CallerB"; attribute :>> toNode="OwnerTransaction"; attribute :>> custody="reserve B checks pending live and draining intervals"; }
part contract2:ContractRow { attribute :>> fromNode="OwnerTransaction"; attribute :>> toNode="Reserved"; attribute :>> custody="commit interval plus exact lease custody"; }
part contract3:ContractRow { attribute :>> fromNode="Reserved"; attribute :>> toNode="RootPreparation"; attribute :>> custody="keep source rooted through allocation"; }
part contract4:ContractRow { attribute :>> fromNode="RootPreparation"; attribute :>> toNode="LiveBundle"; attribute :>> custody="publish complete bundle and operation result atomically"; }
part contract5:ContractRow { attribute :>> fromNode="LiveBundle"; attribute :>> toNode="LostReply"; attribute :>> custody="response may be absent; commit remains"; }
part contract6:ContractRow { attribute :>> fromNode="LostReply"; attribute :>> toNode="ExactQuery"; attribute :>> custody="same immutable request and OperationId"; }
part contract7:ContractRow { attribute :>> fromNode="ExactQuery"; attribute :>> toNode="Closing"; attribute :>> custody="observed result permits coordinated revoke"; }
part contract8:ContractRow { attribute :>> fromNode="LiveBundle"; attribute :>> toNode="Closing"; attribute :>> custody="close new lookups; retain accepted readers"; }
part contract9:ContractRow { attribute :>> fromNode="Closing"; attribute :>> toNode="Drain"; attribute :>> custody="reader scan and lookup grace"; }
part contract10:ContractRow { attribute :>> fromNode="Drain"; attribute :>> toNode="LeaseSettlement"; attribute :>> custody="known result plus exact generation and LeaseId"; }
part contract11:ContractRow { attribute :>> fromNode="LeaseSettlement"; attribute :>> toNode="Unlinked"; attribute :>> custody="atomic lease return and occupancy removal"; }
part contract12:ContractRow { attribute :>> fromNode="Unlinked"; attribute :>> toNode="Reuse"; attribute :>> custody="all storage users native pins and GC grace settled"; }
part contract13:ContractRow { attribute :>> fromNode="Reuse"; attribute :>> toNode="StaleRejection"; attribute :>> custody="advance without wrap; keep old result tombstones"; }
part contract14:ContractRow { attribute :>> fromNode="LiveBundle"; attribute :>> toNode="GCScanner"; attribute :>> custody="pinned descriptor; exclusive update slot ownership"; }
part def GainRow { attribute key:String; attribute avoided:String; attribute added:String; attribute condition:String; }
part gain0:GainRow { attribute :>> key="overlap-authority"; attribute :>> avoided="duplicate physical slot identities and duplicate scan writes"; attribute :>> added="one owner transaction per reserve and unlink; O(n) reference overlap search"; attribute :>> condition="all allocation and view authorities participate; current native retirements zero"; }
part gain1:GainRow { attribute :>> key="lost-reply"; attribute :>> avoided="duplicate allocation registration and premature source release on retry"; attribute :>> added="one stable operation record per request; exact query; replay tombstone storage"; attribute :>> condition="same request identity; no process-crash recovery promised"; }
part gain2:GainRow { attribute :>> key="source-writer"; attribute :>> avoided="holding source after a proved independent copy is covered"; attribute :>> added="alias path blocks writes for full lifetime; copy adds roots and storage"; attribute :>> condition="copy branch inherited only from parent; not proved in new product"; }
part gain3:GainRow { attribute :>> key="parallelism"; attribute :>> avoided="serial preparation of disjoint rooted candidates"; attribute :>> added="serialized metadata mutation and contention; no fairness guarantee"; attribute :>> condition="only preparation outside lock; physical non-overlap and isolated root slots proved"; }
part gain4:GainRow { attribute :>> key="cleanup"; attribute :>> avoided="processor-local cleanup guessing whether shared header is live"; attribute :>> added="VM owner drain and retained unknown-result work"; attribute :>> condition="cleanup_rc bypass must retire only after all exported callers migrate"; }
part gain5:GainRow { attribute :>> key="language-choice"; attribute :>> avoided="duplicating registry ownership across C and Zig"; attribute :>> added="Zig would still need allocator index GC bridge transaction ledger and FFI admission"; attribute :>> condition="no demonstrated incremental Zig benefit over shared modern C contract"; }
part def MemoryRow { attribute key:String; attribute publication:String; attribute observation:String; attribute obligation:String; attribute overhead:String; }
part memory0:MemoryRow { attribute :>> key="mutex"; attribute :>> publication="initialize candidate outside owner lock under scan-visible source root"; attribute :>> observation="lock owner then revalidate revision generation extent and request identity"; attribute :>> obligation="no Scheme callback allocator or GC safepoint while holding index lock; unlock synchronizes later successful lock"; attribute :>> overhead="short serialized reserve commit unlink operations"; }
part memory1:MemoryRow { attribute :>> key="publication"; attribute :>> publication="single owner transaction publishes immutable descriptor plus root-cell registration and result"; attribute :>> observation="scanner and lookup use same lock or proved acquire-load pinned snapshot"; attribute :>> obligation="release/acquire only publishes initialization; does not pin storage or synchronize moving GC cell writes"; attribute :>> overhead="bundle root plus descriptor pin and GC round participation"; }
part memory2:MemoryRow { attribute :>> key="CAS-alternative"; attribute :>> publication="CAS whole pinned snapshot with exact expected revision"; attribute :>> observation="failed CAS updates expected; inspect only after acquire and lifetime protection"; attribute :>> obligation="cannot CAS separate list root and receipt independently; retry overlap check; no weak CAS failure interpreted as rejection"; attribute :>> overhead="snapshot allocation retries reclamation and possible contention"; }
part memory3:MemoryRow { attribute :>> key="settlement"; attribute :>> publication="same owner transaction validates exact lease then removes occupancy and records completed result"; attribute :>> observation="old or duplicate token returns already-settled or stale without decrement"; attribute :>> obligation="never decrement then independently record; cancellation no nonlocal exit inside commit; stable owner retains unknown outcome"; attribute :>> overhead="one exact ledger mutation no blind counter decrement"; }
part memory4:MemoryRow { attribute :>> key="generation"; attribute :>> publication="close drain unpublish grace then advance checked generation"; attribute :>> observation="all old keys and operation receipts compare complete identity"; attribute :>> obligation="generation is not index revision or semantic payload version; exhaust refuses new issuance"; attribute :>> overhead="checked counters tombstones delayed reuse"; }
part memory5:MemoryRow { attribute :>> key="GC"; attribute :>> publication="candidate source pin precedes first movable allocation; descriptor registered before visible publication"; attribute :>> observation="one canonical physical slot per round; GC updates through registered cell"; attribute :>> obligation="alias metadata immutability does not make root cell immutable; no duplicate scanner writes"; attribute :>> overhead="root enumeration pin scan ownership; integration unresolved"; }
part def ProofRow { attribute key:String; attribute lemma:String; }
part proof0:ProofRow { attribute :>> key="checkedInsert"; attribute :>> lemma="StorageIndexAlgebra.checkedInsert"; }
part proof1:ProofRow { attribute :>> key="overlapRejects"; attribute :>> lemma="StorageIndexAlgebra.overlapRejects"; }
part proof2:ProofRow { attribute :>> key="intervalAdjacency"; attribute :>> lemma="StorageIndexAlgebra.intervalAdjacency"; }
part proof3:ProofRow { attribute :>> key="differentGenerationDifferentLease"; attribute :>> lemma="StorageIndexAlgebra.differentGenerationDifferentLease"; }
part proof4:ProofRow { attribute :>> key="differentOperationDifferentLease"; attribute :>> lemma="StorageIndexAlgebra.differentOperationDifferentLease"; }
part proof5:ProofRow { attribute :>> key="settlementCannotConsumeNew"; attribute :>> lemma="StorageIndexAlgebra.settlementCannotConsumeNew"; }
}
