package GambitHashIndexOwnership {
  private import ScalarValues::*;
  ref part collectorRole = GambitRuntimeRoleRealization::cut0;
  attribute runtimeAdmitted : Boolean = false;
  part def Contract { attribute id:String; attribute route:String; attribute invariant:String; attribute benefit:String; attribute cost:String; }
  part creation:Contract { attribute :>> id="producer"; attribute :>> route="_system.scm make-table-aux checks-done -> table flags -> table-get-gcht/allocate"; attribute :>> invariant="test-fn=false selects C identity index; a Scheme test/hash selects persistent SCHEME_INDEX bit 128. Same existing flags word; never infer ownership from KEY_MOVED or weak-key bits."; attribute :>> benefit="Native layout records the semantic algorithm owner before collector sees a table"; attribute :>> cost="One constructor flag decision; no extra table field or root word"; }
  part repair:Contract { attribute :>> id="reference-repair"; attribute :>> route="mem.c scan -> process_gc_hash_tables -> repaired key/value references and owner dispatch"; attribute :>> invariant="Collector transports references. Scheme hashes must be stable for unchanged semantic keys across GC. Clear only address-driven KEY_MOVED for Scheme indexes; preserve pre-existing NEED_REHASH. Never call Scheme from GC or replace its index with the C address hash."; attribute :>> benefit="Eliminate wrong C rehash and its full-table traversal for Scheme-owned indexes; avoid adding a first-reader mutation after ordinary GC"; attribute :>> cost="One owner branch per reached GC table. Correctness depends on hash stability; arbitrary physical-address-dependent custom hashes are not qualified."; }
  part identity:Contract { attribute :>> id="native-index"; attribute :>> route="Native identity tables and union/find -> existing eager SMP rehasher"; attribute :>> invariant="Physical-address indexes rehash with the native algorithm after movement. New owner branch does not globally disable eager reconstruction."; attribute :>> benefit="Preserve existing C identity lookup and shared-read preparation"; attribute :>> cost="Existing native rehash work retained; concurrent mutation and raw misuse remain separate contracts"; }
  part scheme:Contract { attribute :>> id="scheme-index"; attribute :>> route="_system.scm table-access -> recorded test/hash -> existing resize/reinsert for explicit reconstruction debt"; attribute :>> invariant="Ordinary GC does not create Scheme rebuild debt for stable hashes. Deserialization NEED_REHASH still blocks direct indexed lookup until Scheme reconstructs. GC never executes user hash callbacks."; attribute :>> benefit="Semantic key/index agreement and no extra Scheme O(n) rebuild after every collection"; attribute :>> cost="Existing explicit rebuild may allocate/call user hash. Same-table mutating reentrancy and simultaneous reconstruction are not proved by this cut."; }
  part lifetime:Contract { attribute :>> id="owner-lifetime"; attribute :>> route="gc-hash-table-resize flag retention; table-copy -> make-table-aux; serialize/deserialize flags"; attribute :>> invariant="Ownership survives allocation, resize, copy and current-format roundtrip. Older serialized images without owner metadata and external raw flag writers remain unqualified."; attribute :>> benefit="Owner is a persistent native contract, not a GC-mode switch or an exception for GSC"; attribute :>> cost="Additional serialization/FFI producer inventory and native tests required; no compatibility inference"; }
  part witness:Contract { attribute :>> id="witness"; attribute :>> route="new target gsc default heap -> full two-pass bootstrap -> compiled map/multishot/GC and hash-index-owner controls"; attribute :>> invariant="Default profile, real new runtime, both Scheme and native indexes. Large-heap and flag-intervention diagnostics explain failure but cannot confer acceptance."; attribute :>> benefit="Check actual generator, runtime index ownership, collector and repeatable control consumers together"; attribute :>> cost="Full native and source-refinement gates; first target link is insufficient"; }
  part def Edge { ref part producer:Contract; ref part consumer:Contract; }
  part e0:Edge { ref part :>> producer=creation; ref part :>> consumer=repair; }
  part e1:Edge { ref part :>> producer=repair; ref part :>> consumer=identity; }
  part e2:Edge { ref part :>> producer=repair; ref part :>> consumer=scheme; }
  part e3:Edge { ref part :>> producer=creation; ref part :>> consumer=lifetime; }
  part e4:Edge { ref part :>> producer=lifetime; ref part :>> consumer=witness; }
  part e5:Edge { ref part :>> producer=scheme; ref part :>> consumer=witness; }
  part def Proof { ref part component:Contract; attribute id:String; attribute method:String; attribute artifact:String; attribute premise:String; }
  part qnt:Proof { ref part :>> component=repair; attribute :>> id="HI-QNT"; attribute :>> method="quint"; attribute :>> artifact="dev/refactoring/modern-c/models/quint/hash_index_owner.qnt"; attribute :>> premise="Finite two-owner relocation, lookup/debt guards and four retained counterexamples; stable semantic hash is an assumption"; }
  part lean:Proof { ref part :>> component=scheme; attribute :>> id="HI-LEAN"; attribute :>> method="lean"; attribute :>> artifact="dev/refactoring/modern-c/models/lean/HashIndexOwner.lean"; attribute :>> premise="Conditional semantic transport, native rebuild, incompatible-algorithm counter-law and debt guard; not a C pointer or complete hasher proof"; }
  part native:Proof { ref part :>> component=witness; attribute :>> id="HI-NATIVE"; attribute :>> method="native"; attribute :>> artifact="evidence/research/modern-c-bootstrap/hash-index-bootstrap.recipe.json"; attribute :>> premise="Whole target cohort, real default-heap official bootstrap and compiled semantic fixtures; retain all failures and stage/source identities"; }
  part ownership:Proof { ref part :>> component=lifetime; attribute :>> id="HI-REFINE"; attribute :>> method="source-refinement"; attribute :>> artifact="vendor/gambit/lib/_system.scm"; attribute :>> premise="Trace all active C-target constructors, copies, resizing, serialization and raw producers; old images, reentrant mutation and concurrent reconstruction remain open"; }
}
