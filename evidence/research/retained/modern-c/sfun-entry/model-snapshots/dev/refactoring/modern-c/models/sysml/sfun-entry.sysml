package GambitSfunEntry {
 private import ScalarValues::*;
 attribute stage:String="generated-sfun-activation";
 attribute baseline:String="a9b896c46dc781b4967e2d826e5cd29bb910bd6a";
 attribute scope:String="One complete generated SFUN activation: noncollecting entry/root-span publication, raw SCMOBJ prefix, marker and conversion, complete frame handoff, nested/exceptional physical exit. Existing raw marker APIs, general foreign-thread admission and dormant role-record rename remain separate.";
 attribute formalDuty:String="Existing native_entry_admission.qnt owns publication/freeze/logical-versus-physical retirement; add marker revocation and converted-store permission. settleKnown maps only to last C use. RootSpan.lean proves five arbitrary-count size/address/count facts with no lifecycle actions; old Lean state proofs are not counted again. C pointer provenance, source loops and locks remain conditional refinement, not a C memory-model theorem.";
 attribute sourceCases:String="caller-prefix;span-publication;scan-census;frame-handoff;physical-exit;abi-custody;baseline-attribution";
 attribute requiredCases:String="constructors;production-pbt;nonzero;continuation;frame-layout;old-module;official-population;cost";
 ref part acceptedEntryAuthority=GambitBindingActivation::context;
 ref part acceptedFreezeAuthority=GambitBindingActivation::roots;
 attribute dependencyBoundary:String="Reuse the accepted base context/RootTask authority and verify its actual generated-entry use. This is a component dependency, not fresh acceptance of every predecessor workload or a transfer of its performance numbers to a changed layout.";
 part def Component { attribute source:String; attribute owns:String; attribute contract:String; }
 part admissionComponent:Component {
  attribute :>> source="vendor/gambit/lib/_c_intf/sfun-entry.inc;vendor/gambit/lib/_setup/vm-registry.inc";
  attribute :>> owns="Reuse the activation record and lifecycle entry. Tagged kind replaces the startup word: rooted/permanent preparation, active and revoked. Rooted arguments use one bank; zero-argument known-PERM code needs none.";
  attribute :>> contract="Authenticate before allocation or source load. The existing PERM predicate qualifies only zero arguments with retained code/VM lifetime. Kind prevents interpreting a pre-marker permanent procedure as a vector. Otherwise initialize span/false slots before RC membership publication; copy procedure and generated raw arguments before the first collecting call. Allocation failure releases only acquired resources. Native allocation/locks do not execute Scheme or asynchronously abandon the prefix.";
 }
 part writerComponent:Component {
  attribute :>> source="vendor/gambit/include/_gambit/foreign_conversion.h.in;vendor/gambit/lib/_c_intf/sfun-entry.inc";
  attribute :>> owns="Generated raw-root flags are byte metadata, not copied Scheme addresses; conversions share the same RC domain owner gate.";
  attribute :>> contract="Each raw SCMOBJ input is installed once before marker allocation. Later converted arguments populate the same span. No per-argument allocation or stale raw-input reload; private stores require actual PSTATE, the matching domain, OPEN phase, no joined round and the retained bank borrow.";
 }
 part scanComponent:Component {
  attribute :>> source="vendor/gambit/lib/_mem/rc-roots.inc;vendor/gambit/lib/_mem/copy-planning.inc;vendor/gambit/include/_gambit/memory_state.h.in";
  attribute :>> owns="The existing RC RootOrigin/RootTask owns procedure plus immutable-count argument span. No seventh root domain or carrier-index scanner.";
  attribute :>> contract="Under the source gate and frozen scan lease, census and scan enumerate the same procedure cell and root_count payload cells. Publish root_count/false cells before membership release. Owner stores and scanning are mutually excluded; moving GC updates canonical cells, not C-local addresses.";
 }
 part frameComponent:Component {
  attribute :>> source="vendor/gambit/lib/_c_intf/sfun-entry.inc;vendor/gambit/lib/setup.c";
  attribute :>> owns="One final noncollecting argument-frame handoff to the existing call/trampoline.";
  attribute :>> contract="All conversions finish before copying the span to the existing reserved argument area. No poll, Scheme call or GC observes a partial prefix. The existing generated arity/call-frame reserve remains a premise; this cut does not redesign whole-round physical capacity.";
 }
 part exitComponent:Component {
  attribute :>> source="vendor/gambit/lib/_setup/vm-registry.inc;vendor/gambit/lib/_setup/vm-lifecycle.inc;vendor/gambit/include/_gambit/foreign_conversion.h.in";
  attribute :>> owns="Last C use kills marker, returns the bank borrow, releases its owner and drops the retained lifecycle entry.";
  attribute :>> contract="Logical Scheme handler/continuation restoration does not certify physical C quiescence. Keep record/entry and any bank through nested restoration/GC; exact STARTUP kind alone grants existing terminal handoff; only generated catcher landing or actual terminal owner teardown can release it. Unknown join or timeout grants no terminal authority. Multi-shot Scheme continuations remain valid subject to the existing prohibition on returning into a killed C marker.";
 }
 attribute refinements:String="prefixMap;writerMap;scanMap;revokeMap;exitMap;unknownMap";
 part def Refinement { attribute actions:String; attribute source:String; attribute guard:String; attribute obligation:String; attribute quint:String default="dev/refactoring/modern-c/models/quint/native_entry_admission.qnt"; attribute leanDuty:String default="No lifecycle proof in Lean. RootSpan.lean proves only size bounds, address extent/injectivity, primary separation and root count for arbitrary Nat length."; }
 part prefixMap:Refinement { attribute :>> actions="pinSource;reserveCarrier;qualifyHost;publishCarrier;jointIssue;writeEntryState;allocateMarker"; attribute :>> source="___begin_sfun;___alloc_rc_roots;___SFUN_ROOT_ARG;___sfun_marker"; attribute :>> guard="Registered actual owner and rooted caller/C-closure source; metadata prefix cannot collect or abandon. Publish false-initialized span under RC gate, then seal raw values before first marker/converter GC. Native intrinsics are not an arbitrary foreign-thread entry API."; attribute :>> obligation="SFUN-PREFIX"; }
 part writerMap:Refinement { attribute :>> actions="populateConverted"; attribute :>> source="___SFUN_ARG;___sfun_arg;___call_sfun"; attribute :>> guard="Generated program point supplies pre/post-marker phase; RC gate checks current owner, OPEN/not joined and unique bank borrow. Raw flags skip stale C locals. Completed conversion precedes no-poll frame copy. Arbitrary calls to private intrinsics out of generated order are outside this refinement."; attribute :>> obligation="SFUN-HANDOFF"; }
 part scanMap:Refinement { attribute :>> actions="freezeWriters;scanBoth;scanCarrier;thawWriters"; attribute :>> source="RC RootTask scan lease;mark_rc;census_array"; attribute :>> guard="Existing cooperative collective parks writers. The same immutable count and canonical cells are enumerated by census and scan while source gate/lease remains held; no extra carrier scanner or memory-order oracle."; attribute :>> obligation="SFUN-COVERAGE"; }
 part revokeMap:Refinement { attribute :>> actions="revokeMarker"; attribute :>> source="___lifecycle_marker_kill"; attribute :>> guard="Only marker permission is revoked; roots, bank borrow, activation and lifecycle entry remain until last C use. Source-bound pre-fix control reproduces premature-drop failure; badDropOnRevoke is a negative model control, never in step."; attribute :>> obligation="SFUN-EXIT"; }
 part exitMap:Refinement { attribute :>> actions="recordOutcome;settleKnown;closeScanAdmission;confirmGrace;retireCarrier"; attribute :>> source="___END_SFUN;___end_sfun;___lifecycle_marker_abort"; attribute :>> guard="Resumed Scheme handler is not settleKnown. The actual last-use catcher landing or proven terminal owner releases only its own marker/borrow/bank/entry. RootTask scan and unregister use the existing source gate; no C frame resumes after terminal teardown."; attribute :>> obligation="SFUN-EXIT"; }
 part unknownMap:Refinement { attribute :>> actions="loseRegistrationAck;loseCompletion;recoverRecorded"; attribute :>> source="existing lifecycle activation list and synchronous generated C extent"; attribute :>> guard="These broader QNT histories are not concrete recovery-service acceptance. This cut requires a non-abandoning registration prefix; nonlocal escapes retain actual activation custody until known landing/terminal exit. No unknown native response authorizes a second constructor, forged stop receipt or root reclamation."; attribute :>> obligation="SFUN-SOURCE"; }
 part def Obligation { attribute id:String; attribute status:String; attribute premise:String; }
 attribute obligations:String="prefix;coverage;handoff;exitProof;property;cost;modelsProof;sourceProof;officialProof";
 part officialProof:Obligation { attribute :>> id="SFUN-OFFICIAL"; attribute :>> status="CLOSED"; attribute :>> premise="Retain complete original-population runs and unchanged120s limit. Final current candidate completes408 cases in92.157s,393 pass/15 fail. Historical exact baseline393/408 plus fresh baseline prefix account for observed failure names, not identical causes. Earlier candidate/baseline timeouts remain failed; no whole-SMP pass or unexecuted-case qualification."; }
 part prefix:Obligation { attribute :>> id="SFUN-PREFIX"; attribute :>> status="CLOSED"; attribute :>> premise="Actual generated macros register raw inputs before marker/converter GC; narrow bank/marker failure controls exercise acquired-only cleanup."; }
 part coverage:Obligation { attribute :>> id="SFUN-COVERAGE"; attribute :>> status="CLOSED"; attribute :>> premise="Actual moving GC and nonzero-origin execution; census and scan cover the same immutable span under existing RootTask lease."; }
 part handoff:Obligation { attribute :>> id="SFUN-HANDOFF"; attribute :>> status="CLOSED"; attribute :>> premise="Existing generated conversion/arity/reserve contract and uninterrupted final copy; no whole allocator redesign claim."; }
 part exitProof:Obligation { attribute :>> id="SFUN-EXIT"; attribute :>> status="CLOSED"; attribute :>> premise="The actual handler retains inner bank across GC; returning through an outer native marker drains both. Unknown/foreign asynchronous abandonment retains custody and is not admitted recovery."; }
 part property:Obligation { attribute :>> id="SFUN-PBT"; attribute :>> status="CLOSED"; attribute :>> premise="Reuse existing Scheme replay/shrink against unmodified production runtime, separate from the c_intf callout-control image. Keep incorrect immediate-decrement oracle as a source-bound counterexample."; }
 part cost:Obligation { attribute :>> id="SFUN-COST"; attribute :>> status="CLOSED"; attribute :>> premise="Actual zero/one/many raw-input populations and allocation/layout bounds. Initial zero-argument regression remains history; known-PERM zero needs no bank, moving procedures still do. Metadata on all RC nodes and extra scanned cells remain costs; no full-workflow speedup or unmeasured C-closure trampoline claim."; }
 part modelsProof:Obligation { attribute :>> id="SFUN-MODELS"; attribute :>> status="CLOSED"; attribute :>> premise="Native OpenSysML SDK drives exact source obligations and ASCENT missing/stale controls. Existing QNT actions and distinct Lean duties; labels alone grant no acceptance."; }
 part sourceProof:Obligation { attribute :>> id="SFUN-SOURCE"; attribute :>> status="CLOSED"; attribute :>> premise="Same persistent cache, exact generated cohort and C23/Bazel profile; no pending role rename, raw writer prototype, scheduler or unrelated allocator hunk imported."; }
 part submission:GambitCommitGates::SubmissionUnit { attribute :>> kind="integration"; attribute :>> result="generated-sfun-activation"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="SFUN-TESTS"; attribute :>> method="native"; attribute :>> artifact="evidence/research/retained/modern-c/sfun-entry/qualification.json"; attribute :>> scope="Full declared production/failure/root/continuation/layout/old-module and original population; retain baseline failures without relabeling them."; }
 part learning:Need { ref part :>> gate=GambitCommitGates::learning; attribute :>> id="SFUN-LEARNING"; attribute :>> method="source-analysis"; attribute :>> artifact="dev/refactoring/modern-c/sfun-entry.org"; attribute :>> scope="Raw-prefix root coverage, physical C lifetime versus logical escape, necessary zero-argument cost and failed oracle history."; }
 part process:Need { ref part :>> gate=GambitCommitGates::process; attribute :>> id="SFUN-PROCESS"; attribute :>> method="source-analysis"; attribute :>> artifact="dev/refactoring/modern-c/sfun-entry.org"; attribute :>> scope="One complete generated-entry owner; foundation4/4 and independent SMP1/12 unchanged; broad CFFI/role rename is separate."; }
 part models:Need { ref part :>> gate=GambitCommitGates::models; attribute :>> id="SFUN-FORMAL"; attribute :>> method="native"; attribute :>> artifact="evidence/research/retained/modern-c/sfun-entry/qualification.json"; attribute :>> scope="Actual existing QNT scenarios, SDK projection and conditional C source/lock refinement. No duplicated Lean proof."; }
 part questions:Need { ref part :>> gate=GambitCommitGates::questions; attribute :>> id="SFUN-QUESTIONS"; attribute :>> method="source-analysis"; attribute :>> artifact="dev/refactoring/modern-c/sfun-entry.org"; attribute :>> scope="Actual no-poll/root source assumptions, zero/one/wide input cost, explicit scan overhead and ABI consumers; never infer universal benefit."; }
}
