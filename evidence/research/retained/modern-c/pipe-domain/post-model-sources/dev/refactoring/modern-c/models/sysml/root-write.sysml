package GambitRootWrite {
 private import ScalarValues::*;
 attribute stage:String="root-write-authority";
 attribute baseline:String="13104c8a6e99dd5e474fa08b7ab329b7a800fbd1";
 attribute scope:String="One complete RC-domain mutation contract: actual live source owner, primary/span writes, borrow admission, cooperative freeze and physical exit. Reuse the accepted producers/scanners/last-use consumers, preserve VM/public C layout and existing names. VM/token-table/code-object retirement is a separate BLOCKED contract; general arbitrary foreign entry and asynchronous owner-death recovery remain outside.";
 attribute formalDuty:String="Existing native_entry_admission.qnt owns generated-entry/freeze/physical-exit interleavings; root_store_projection.qnt owns canonical aliases, parked borrowing and storage lifetime. RootSpan.lean owns only size/address arithmetic; reuse exact unchanged proof, do not duplicate state machines or claim a C memory-model theorem.";
 attribute sourceCases:String="issuer-inheritance;primary-span-gate;freeze-and-borrow;physical-exit;abi-reuse;source-transition";
 attribute requiredCases:String="entry-and-rc;nonzero;continuation;layout;old-module;official-population;cost;framework";
 ref part activation=GambitSfunEntry::admissionComponent;
 ref part rootSource=GambitSfunEntry::scanComponent;
 ref part physicalExit=GambitSfunEntry::exitComponent;
 attribute dependencyBoundary:String="Use the actual accepted component contracts, recompile/retest their changed C consumers. No inheritance of predecessor performance numbers or full-SMP acceptance.";
 part primary:GambitSfunEntry::Component {
  attribute :>> source="vendor/gambit/lib/rc.h;vendor/gambit/lib/_mem/rc-allocation.inc";
  attribute :>> owns="One checked source operation: ___store_rc_root; ordinary void setter and fallible primary setter retain their names/contracts.";
  attribute :>> contract="Actual PSTATE, matching live domain, owner, OPEN/not joined, positive native ownership and index bound precede any mutation under the existing RC mutex. Borrowed primary identity is immutable; an identical no-op performs no store. Positive span index requires one activation borrow. No allocation, poll, callback or new permit table.";
 }
 part span:GambitSfunEntry::Component {
  attribute :>> source="vendor/gambit/lib/_c_intf/sfun-entry.inc;vendor/gambit/include/_gambit/foreign_conversion.h.in";
  attribute :>> owns="Generated SFUN argument stores delegate to the same RC writer; the activation, canonical roots and final complete frame remain their actual owners.";
  attribute :>> contract="Retain actual owner/scope and finite generated arity. Caller reloads canonical values after any GC; the store itself cannot collect. Final call-frame copy remains noncollecting and source-gated. Do not add a second activation or claim arbitrary direct misuse of private intrinsics is admitted.";
 }
 part deferredLayout:GambitSfunEntry::Component {
  attribute status:String="BLOCKED_NEW_FAILURE";
  attribute :>> source="evidence/research/retained/modern-c/root-write/boundary-decision.json;vendor/gambit/include/_gambit/vm_state.h.in;vendor/gambit/lib/native_scope.c";
  attribute :>> owns="Separate VM layout/code-object retirement; not part of current RC write admission.";
  attribute :>> contract="Combined proposal has an unattributed division failure not reproduced by two exact baseline populations. Writer-only contrast restores both layout and retired objects and does not prove the cause. Preserve the combined source/model/raw failures; claim neither512-byte savings nor table retirement in the current unit.";
 }
 attribute refinements:String="writerMap;freezeMap;exitMap";
 part def Refinement { attribute actions:String; attribute source:String; attribute guard:String; attribute obligation:String; attribute quint:String; attribute leanDuty:String default="Reuse unchanged RootSpan.lean arithmetic only; no repeated lifecycle proof."; }
 part writerMap:Refinement { attribute :>> actions="populateConverted;beginWriter;finishWriter"; attribute :>> source="___sfun_arg;___store_rc_root;___try_set_data_rc;___set_data_rc"; attribute :>> guard="Actual cooperative owner and live storage. Root mutex excludes scan/write; bound checked before pointer arithmetic. Primary identity cannot rebind while borrowed; span has exactly one activation borrow. Stronger C guards restrict the abstract permitted actions; the model does not attest native pointers."; attribute :>> obligation="ROOT-WRITER"; attribute :>> quint="dev/refactoring/modern-c/models/quint/native_entry_admission.qnt;dev/refactoring/modern-c/models/quint/root_store_projection.qnt"; }
 part freezeMap:Refinement { attribute :>> actions="borrowCell;parkBorrow;freeze;scan;restore;reloadBorrow;returnBorrow"; attribute :>> source="___borrow_rc_root;root_writer_open;RC RootTask census/scan and restore"; attribute :>> guard="Borrow retains storage, not a stale Scheme address or execution permission. Existing collective parks mutators; no waiting for borrowed roots to drain during scanning. The confined frozen-phase refusal control is not independent GC-phase qualification; actual moving GC comes from production histories."; attribute :>> obligation="ROOT-FREEZE"; attribute :>> quint="dev/refactoring/modern-c/models/quint/root_store_projection.qnt"; }
 part exitMap:Refinement { attribute :>> actions="revokeMarker;recordOutcome;settleKnown;retireCarrier"; attribute :>> source="___lifecycle_marker_kill;___end_sfun;___lifecycle_marker_abort"; attribute :>> guard="Revocation is not physical C quiescence. Last generated C use or proven terminal owner may release roots/entry; failed or unknown join grants neither permission. These consumers remain the existing owner, not token-table release bits."; attribute :>> obligation="ROOT-EXIT"; attribute :>> quint="dev/refactoring/modern-c/models/quint/native_entry_admission.qnt"; }

 part def Obligation { attribute id:String; attribute status:String; attribute premise:String; }
 attribute obligations:String="writer;borrow;freeze;exitProof;coverage;layout;property;cost;sourceProof";
 part writer:Obligation { attribute :>> id="ROOT-WRITER"; attribute :>> status="CLOSED"; attribute :>> premise="Primary/span stores share one source gate and preserve primary borrowed identity; bound before pointer arithmetic."; }
 part borrow:Obligation { attribute :>> id="ROOT-BORROW"; attribute :>> status="CLOSED"; attribute :>> premise="Same actual owner/OPEN gate; zero-reference borrowed storage remains owned; release does not invent terminal permission."; }
 part freeze:Obligation { attribute :>> id="ROOT-FREEZE"; attribute :>> status="CLOSED"; attribute :>> premise="Confined phase refusal plus actual GC histories; models are interleaving specifications, not C weak-memory or asynchronous stop proofs."; }
 part exitProof:Obligation { attribute :>> id="ROOT-EXIT"; attribute :>> status="CLOSED"; attribute :>> premise="Nested, conversion-error and revoked-marker paths retain roots until actual physical exit; same existing owner, no new bitmap."; }
 part coverage:Obligation { attribute :>> id="ROOT-COVERAGE"; attribute :>> status="CLOSED"; attribute :>> premise="All primary and SFUN payload mutator stores delegate to the same RC policy. Constructor false initialization and privileged collector relocation retain their distinct admitted source phases; globals/other root domains are not forced into this RC mutex."; }
 part layout:Obligation { attribute :>> id="ROOT-LAYOUT"; attribute :>> status="CLOSED"; attribute :>> premise="Native sizeof, frame/root consumers and exact previous-module baseline/current reuse and older-ABI refusal; same-ABI old module and public SFUN callback execute unchanged; older ABI is refused. No fresh whole-Gerbil build claim."; }
 part property:Obligation { attribute :>> id="ROOT-PBT"; attribute :>> status="CLOSED"; attribute :>> premise="Production SFUN replay/shrink/nonzero and existing RC stateful histories execute actual stores. Observer-mutation shrink is not a minimized runtime bug."; }
 part cost:Obligation { attribute :>> id="ROOT-COST"; attribute :>> status="CLOSED"; attribute :>> premise="Paired full zero/one/eight workloads, actual VM/GSTATE bytes and per-store work. Metadata saving is not heap/peak/cold-build or universal latency saving."; }
 part sourceProof:Obligation { attribute :>> id="ROOT-SOURCE"; attribute :>> status="CLOSED"; attribute :>> premise="Same cache/profile, exact source selection and native reuse; full original population and explicit baseline attribution. No tests weakened or unrelated staged source admitted."; }
 part submission:GambitCommitGates::SubmissionUnit { attribute :>> kind="integration"; attribute :>> result="root-write-authority"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="ROOT-WRITE-TESTS"; attribute :>> method="native"; attribute :>> artifact="evidence/research/retained/modern-c/root-write/qualification.json"; attribute :>> scope="Complete declared current native consumers, old-module controls, original population and matched costs; preserve known failures."; }
 part learning:Need { ref part :>> gate=GambitCommitGates::learning; attribute :>> id="ROOT-WRITE-LEARNING"; attribute :>> method="source-analysis"; attribute :>> artifact="dev/refactoring/modern-c/root-write.org"; attribute :>> scope="Actual producer/gate/scan/exit ownership unifies mutation and borrowing; token-table retirement remains blocked; explicit costs and refusal boundaries."; }
 part process:Need { ref part :>> gate=GambitCommitGates::process; attribute :>> id="ROOT-WRITE-PROCESS"; attribute :>> method="source-analysis"; attribute :>> artifact="dev/refactoring/modern-c/root-write.org"; attribute :>> scope="One complete authority source cut; rejected prototypes and original pending queue remain separately audited; no independent SMP promotion."; }
 part models:Need { ref part :>> gate=GambitCommitGates::models; attribute :>> id="ROOT-WRITE-MODELS"; attribute :>> method="native"; attribute :>> artifact="evidence/research/retained/modern-c/root-write/qualification.json"; attribute :>> scope="Native SDK/ASCENT, existing QNT interleavings and exact reused Lean arithmetic have disjoint duties; C refinement is conditional."; }
 part questions:Need { ref part :>> gate=GambitCommitGates::questions; attribute :>> id="ROOT-WRITE-QUESTIONS"; attribute :>> method="source-analysis"; attribute :>> artifact="dev/refactoring/modern-c/root-write.org"; attribute :>> scope="No new VM/token capacity; byte savings versus actual peak, per-store work, ABI rebuild and known failure attribution explicitly answered."; }
}
