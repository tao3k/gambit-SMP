package GambitOrderedFallback {
 private import ScalarValues::*;
 attribute stage:String="ordered-word-fallback";
 attribute baseline:String="5c0ff48959d612752705f324df7b0913069c43a5";
 attribute scope:String="Complete existing POSIX emulated word service: same-address mutex RMW, encoded-word wrap, actual module construction/drain and meaningful standalone fence. Qualify real standalone fallback units without mixed conditional ABI; production GCC builtin profile unchanged. No whole emulated Scheme VM or CAS-less machine admission.";
 attribute formalDuty:String="Reuse root result_mutex_ticket_grant_tests.qnt and visibility model for conditional grant-completion ordering. Current mutex-backed CAS already supplies an acquire; its old empty fence is not a claimed current ticket failure. C23 primitive arithmetic/representation and fence semantics are source premises, not duplicated Lean/QNT proofs. No native weak-memory/fairness theorem.";
 attribute sourceCases:String="word-law;source-mutex;lifecycle;fence;backend-isolation;source-custody";
 attribute requiredCases:String="strict-baseline;real-emulated;native-profile;litmus;emitted-code;production-pbt;model;aa-cost";
 part def Component { attribute source:String; attribute owns:String; attribute contract:String; }
 part word:Component { attribute :>> source="vendor/gambit/lib/os_thread.c: ___emulated_compare_and_swap_word / ___emulated_fetch_and_add_word / ___emulated_fetch_and_clear_word"; attribute :>> owns="Existing address-hashed mutex supplies RMW atomicity and same-address visibility. Addition uses unsigned modulo arithmetic and reconstructs the signed word representation with memcpy before the volatile store."; attribute :>> contract="No signed overflow or out-of-range signed cast dependence. Managed word has matching width/representation, C23 two's complement. Lock covers read/transform/write; no new mutex bucket, metadata or namespace. Current production -fwrapv is preserved; its old behavior is not mislabeled a native-profile UB failure."; }
 part fence:Component { attribute :>> source="vendor/gambit/lib/os_thread.c: ___emulated_shared_memory_barrier; C23 stdatomic.h"; attribute :>> owns="Replace empty hope-for-the-best implementation with sequentially consistent atomic_thread_fence."; attribute :>> contract="Fence orders eligible accesses; it does not stop a thread, repair a C data race or alone grant payload ownership. C23 atomic support is a managed prerequisite; actual arm64 code must emit a barrier. RMW publication still uses existing same-source mutex."; }
 part testBoundary:Component { attribute :>> source="vendor/gambit/tests/ordered-sync.c;vendor/gambit/tests/makefile.in;actual os_thread/os_base/os_setup source units"; attribute :>> owns="Native builtin and actual POSIX emulated constructors/RMW/ticket/fence consumers. Suppress compiler capability macros only for an isolated standalone test, never link the production archive across that conditional ABI."; attribute :>> contract="Existing queued fixture referred to nonexistent sync-slot macros; remove that unqualified assumption, not an official test. Test real current primitives and race-free atomic litmus. GNU/Clang POSIX native test variant uses existing build link-option parameter; production configuration/flags unchanged. Strict UBSan mode deliberately disables -fwrapv as a separate diagnostic."; }
 attribute refinements:String="rmwMap;grantMap;fenceMap";
 part def Refinement { attribute actions:String; attribute source:String; attribute guard:String; attribute obligation:String; attribute quint:String; attribute leanDuty:String default="No new arithmetic law proved in Lean; C23 primitive/representation premise and native boundary checks explicit. No duplicated protocol proof."; }
 part rmwMap:Refinement { attribute :>> actions="reserveTicket;acceptGrant"; attribute :>> source="Real CAS/add/clear word functions under address-hashed mutex; unchanged ordered word macros"; attribute :>> guard="Aligned valid word and live initialized thread module; all concurrent accesses use the same service, no racing raw word store. Unsigned wrap plus valid representation; no proof for arbitrary foreign memory."; attribute :>> obligation="WORD-LAW"; attribute :>> quint="models/gambit/result_mutex_ticket_grant_tests.qnt"; }
 part grantMap:Refinement { attribute :>> actions="acceptGrant;claimB;executeB"; attribute :>> source="Current ticket lock uses WORD_LOAD_ACQUIRE/CAS mutex handoff"; attribute :>> guard="Acquire at actual grant completion; bounded outstanding tickets and physical owner remain existing premises. Root model old-noop negative is an abstract missing-order scenario, not a reproduced current native CAS failure."; attribute :>> obligation="WORD-ORDER"; attribute :>> quint="models/gambit/result_mutex_ticket_visibility.qnt"; }
 part fenceMap:Refinement { attribute :>> actions="acceptGrant"; attribute :>> source="Actual standalone emulated fence and C23 atomic litmus"; attribute :>> guard="Sequentially consistent fence semantics are normative source premise; emitted dmb and4096 litmus observations do not prove all C weak-memory executions or GC stop."; attribute :>> obligation="WORD-FENCE"; attribute :>> quint="models/gambit/result_mutex_ticket_grant_tests.qnt"; }
 part def Obligation { attribute id:String; attribute status:String; attribute premise:String; }
 attribute obligations:String="law;order;fenceProof;life;isolation;reuse;costProof";
 part law:Obligation { attribute :>> id="WORD-LAW"; attribute :>> status="CLOSED"; attribute :>> premise="Actual parent strict diagnostic detects overflow; candidate actual word boundary/CAS/clear and wrap pass, no narrowing cast."; }
 part order:Obligation { attribute :>> id="WORD-ORDER"; attribute :>> status="CLOSED"; attribute :>> premise="Real native/emulated ticket updates and two trylock controls preserve current source mutex/grant ordering."; }
 part fenceProof:Obligation { attribute :>> id="WORD-FENCE"; attribute :>> status="CLOSED"; attribute :>> premise="Old function empty, new sequentially consistent fence emits arm64 dmb and race-free litmus passes; no full memory-model theorem."; }
 part life:Obligation { attribute :>> id="WORD-LIFECYCLE"; attribute :>> status="CLOSED"; attribute :>> premise="Real thread-module setup and cleanup surround all users; constructor rollback code unchanged, no unknown-join permission."; }
 part isolation:Obligation { attribute :>> id="WORD-ISOLATION"; attribute :>> status="CLOSED"; attribute :>> premise="Standalone emulated variant links only consistent actual source units; no production archive with mismatched conditional ABI. No CAS-less host/whole-emulated-VM admission."; }
 part reuse:Obligation { attribute :>> id="WORD-REUSE"; attribute :>> status="CLOSED"; attribute :>> premise="Same production profile/cache, identical GSI/GSC/seed,51 generated products reused; real new archive serves SFUN/PBT."; }
 part costProof:Obligation { attribute :>> id="WORD-COST"; attribute :>> status="CLOSED"; attribute :>> premise="Zero new production storage, unchanged builtin executable code. Exact same-executable A/A costs measure noise, not an algorithm speedup; old1-arg attribution remains conditional."; }
 part submission:GambitCommitGates::SubmissionUnit { attribute :>> kind="integration"; attribute :>> result="ordered-word-fallback"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="WORD-TESTS"; attribute :>> method="native"; attribute :>> artifact="evidence/research/retained/modern-c/ordered-fallback/qualification.json"; attribute :>> scope="Actual parent strict negative, native/emulated Make targets, fence output/litmus and new archive SFUN/PBT consumer; identity reuse distinct."; }
 part learning:Need { ref part :>> gate=GambitCommitGates::learning; attribute :>> id="WORD-LEARNING"; attribute :>> method="source-analysis"; attribute :>> artifact="dev/refactoring/modern-c/ordered-fallback.org"; attribute :>> scope="Primitive service owns wrap and order, not an unrelated compiler flag or empty fence. Capability-test ABI isolation explicit."; }
 part process:Need { ref part :>> gate=GambitCommitGates::process; attribute :>> id="WORD-PROCESS"; attribute :>> method="source-analysis"; attribute :>> artifact="dev/refactoring/modern-c/ordered-fallback.org"; attribute :>> scope="Two original queued paths retire; original nine groups retain eight nonempty owners and41 paths. Shared Make future hunks remain."; }
 part models:Need { ref part :>> gate=GambitCommitGates::models; attribute :>> id="WORD-MODELS"; attribute :>> method="native"; attribute :>> artifact="evidence/research/retained/modern-c/ordered-fallback/qualification.json"; attribute :>> scope="Native SDK→ASCENT seven duties/three real adapters; root QNT reused with conditional acquire premises. No duplicate Lean law."; }
 part questions:Need { ref part :>> gate=GambitCommitGates::questions; attribute :>> id="WORD-QUESTIONS"; attribute :>> method="source-analysis"; attribute :>> artifact="dev/refactoring/modern-c/ordered-fallback.org"; attribute :>> scope="Unsigned/signed representation, actual backend, no mixed ABI, race freedom, physical last use, no heap change and A/A cost attribution explicit."; }
}
