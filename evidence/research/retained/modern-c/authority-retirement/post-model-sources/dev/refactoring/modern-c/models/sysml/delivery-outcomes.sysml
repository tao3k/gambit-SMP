package GambitModernCOutcomes {
  private import ScalarValues::*;
  ref part catalogue=GambitModernCDeliveryPlan::roots;
  ref part queue=GambitPendingCuts::borrowDelivery;
  attribute policy:String="Four integration results own architecture progress. Thirteen stages are a responsibility catalogue; fifteen review units and dotted source tasks are internal work indexes. A small REV or support/documentation fix advances neither architecture-result nor SMP-family counters. Report actual results, blocking evidence and next integration exit, not commit totals.";
  attribute currentSourceScope:String="The currentSource attribute identifies the first-three-results qualification period, not the new1b387add fourth-runtime ABI or the dirty checkout. The execution result is the registry owner. Detailed fourth-result admission lives in GambitRequestProduct::revisionAdmission and refers back to this registry; the registry must not import that feature model or make the first three results depend on it.";
  attribute currentSource:String="f8c028ca1a64a062efe7dbb8b1efb48b58e774b4";
  attribute reporting:String="Three managed C-target integration results locally qualified:3/4,1 remains. Frozen roots, independent collector/restoration and complete owned lifecycle have current source/native evidence. Independent SMP stays1/12,11 families open. No repair-line, scheduler, complete CFFI, runtime-performance or remote CI credit is transferred.";
  attribute submission:String="The third complete22-obligation lifecycle is one integration REV including its two predecessor programmes,5 source adapters and8 native categories. Request/service/FIFO and complete product qualification remain result4. Preserve unrelated prototypes and current independent SMP failures.";
  attribute entryBoundary:String="Result1 includes native argument/root registration, writer exclusion and root cleanup needed to freeze a source. Result3 includes affine-resource effects, delayed destructors and unknown-owner retirement. These can be different hunks in the same primary-owned entry files. Do not create a roots -> whole FFI -> retirement -> roots dependency cycle or imply that every CFFI semantic feature must ship in result1.";
  attribute supportPolicy:String="Header/layout, C23/Darwin, incremental build and CI work accompany their actual consumers. Only required ABI/header hunks gate result1; unrelated lossless modularization remains support. Generated C attaches to its exact Scheme producer. Preserve official names, one cache/profile and fixed limits; no support-only work counts as a modern SMP outcome.";
  attribute gambitAmplification:String="Use Gambit's existing explicit safe points and GVM live-root/frame knowledge to publish complete frozen views, instead of assuming a count or stopped carrier suffices. Preserve and strengthen shared multi-shot continuation frames, logical identity versus moved addresses, tail dispatch and C portability through one source/runtime contract. No one-shot restriction, per-actor private heap model or automatic generational-GC/LLVM speedup follows. Actual reduced scan/copy/control work and added barriers/metadata must be measured on matched complete consumers.";
  part def ReviewNeed { ref part gate:GambitCommitGates::Gate; attribute id:String; attribute method:String; attribute artifact:String; attribute scope:String; }
  part reviewTests:ReviewNeed { ref part :>> gate=GambitCommitGates::tests; attribute :>> id="PLAN-TESTS"; attribute :>> method="plan-validation"; attribute :>> artifact="evidence/research/retained/modern-c/integration-plan/receipt.json"; attribute :>> scope="Actual native SysML/ASCENT projection,127 current paths/15 primary owners,14 source-context scenarios and native planning tests. No runtime implementation or integration-result acceptance."; }
  part reviewLearning:ReviewNeed { ref part :>> gate=GambitCommitGates::learning; attribute :>> id="PLAN-LEARNING"; attribute :>> method="source-analysis"; attribute :>> artifact="dev/refactoring/modern-c/delivery-outcomes.org"; attribute :>> scope="Explain why leaf/support commits did not close complete ownership results; group real replacements, measurable exits, extra cost and falsifiers."; }
  part reviewProcess:ReviewNeed { ref part :>> gate=GambitCommitGates::process; attribute :>> id="PLAN-PROCESS"; attribute :>> method="source-analysis"; attribute :>> artifact="dev/refactoring/modern-c/delivery-outcomes.org"; attribute :>> scope="Publish the complete Changes plan without runtime prototypes;0/4 integration results and independent1/12 families remain honest. Bound early entry-root versus late resource effects without dependency cycles."; }
  part reviewModels:ReviewNeed { ref part :>> gate=GambitCommitGates::models; attribute :>> id="PLAN-MODELS"; attribute :>> method="source-refinement"; attribute :>> artifact="dev/refactoring/modern-c/delivery-outcomes.org"; attribute :>> scope="Native SysML typed unit/result/family routes drive actual ASCENT non-promotion and dependency checks. Existing QNT/Lean semantic duties remain unchanged and are not rerun."; }
  part reviewQuestions:ReviewNeed { ref part :>> gate=GambitCommitGates::questions; attribute :>> id="PLAN-QUESTIONS"; attribute :>> method="source-analysis"; attribute :>> artifact="dev/refactoring/modern-c/delivery-outcomes.org"; attribute :>> scope="Answer what first coherent root delivery replaces, which127 paths belong where, why shared counts are not frozen writers, when source consumers count and why prior/current SMP failures still require evidence."; }
  part def Result { attribute countAxis:String default = "foundation"; attribute id:String; attribute title:String; attribute replacement:String; attribute validation:String; attribute falsifier:String; attribute benefit:String; attribute cost:String; attribute deliveryStatus:String; }
  part roots:Result { attribute :>> deliveryStatus="QUALIFIED_C_TARGET"; attribute :>> id="frozen-roots"; attribute :>> title="Frozen root population and writer lifetime"; attribute :>> replacement="Replace implicit carrier/current-thread roots by the complete RootOrigin -> RootTask contract for six admitted root kinds, canonical aliases, all managed writers/borrows and entry root obligations. Retire old scan entry paths only after all real callers are replaced."; attribute :>> validation="Generated/reflected globals, RC nonzero processor, stack/bank/multi-shot continuation, symbol/keyword and VM roots, real close/store races, root relocation, exit/failure custody and real implementation replay/shrink. Run complete applicable original GSI/GSC consumers; any scoped baseline disposition requires its own actual source proof."; attribute :>> falsifier="A raw admitted writer, unpinned alias, incomplete frame or late store remains; a missing or related failure cannot be dismissed as baseline."; attribute :>> benefit="An explicit frozen root union can be scanned independently of a running carrier; no completed leaf count proves that union."; attribute :>> cost="Actual authority acquisitions, root metadata, retained borrows and scan work must be counted; throughput and RSS remain unmeasured."; }
  part collector:Result { attribute :>> deliveryStatus="QUALIFIED_C_TARGET"; attribute :>> id="independent-collector"; attribute :>> title="Physical copy capacity and independent collector/restoration"; attribute :>> replacement="Replace carrier-index work arenas and local-count assumptions with unique copy authority, complete source/frame census, physical interval packing, worker-owned arenas and R-context restoration by W workers."; attribute :>> validation="W<R and other declared topologies, reserve/refund/CAS-loss, batch/Tail custody, GC/root relocation and real map multi-shot restore. Bound physical peak and every failure/unknown result without adding heap or waits."; attribute :>> falsifier="A worker still borrows carrier-local allocation identity, one object scans twice, a copy lacks contiguous capacity or a context lacks its first restore interval."; attribute :>> benefit="Worker count becomes independent from execution contexts and root sources; remove repeated scanning/copy work only with measured counts."; attribute :>> cost="Census/packing, reservations, physical slack and root/restore metadata; no invented peak-memory or throughput gain."; }
  part lifetime:Result { attribute :>> deliveryStatus="QUALIFIED_C_TARGET"; attribute :>> id="owned-lifetime"; attribute :>> title="Startup, retirement and deferred effects"; attribute :>> replacement="Replace member-publication/join/global-cleanup coupling by rooted startup requests, initialized physical reservations, explicit member acceptance and resource-specific ownership transfer/retirement. Separate root entry cleanup from affine native resource effects."; attribute :>> validation="Partial create/rollback/retry, join failure/unknown, nested entry/exit, delayed destructors/shutdown drain and healthy VM continuing GC under an isolated unknown join; full registry/lifecycle/GC-FFI inventories."; attribute :>> falsifier="Unknown join is treated as death, metadata is freed with remaining roots/readers, or healthy VMs wait for an unrelated unknown owner."; attribute :>> benefit="Local uncertainty retains explicit custody and need not stop unrelated healthy VMs."; attribute :>> cost="Retained unknown-owner storage, queues, tickets and accounting; quantify bounds from actual usage."; }
  part execution:Result { attribute :>> deliveryStatus="OPEN_INTEGRATION"; attribute :>> id="request-product"; attribute :>> title="Request execution and complete product qualification"; attribute :>> replacement="Replace waiting-thread/service-activation confusion and unowned shared FIFO publication by explicit request/message ownership, stable execution boundaries and exact completed native/Gerbil product consumers."; attribute :>> validation="Complete original interpreted/compiled, PR and stress manifests, ordered shared values, repeated multi-shot control, complete Gerbil build/tests and matched release latency/throughput/peak populations on the final source."; attribute :>> falsifier="Repair9 work merely moves, repeat continuation materialization persists, original populations shrink, or final product/CI/performance evidence is absent."; attribute :>> benefit="Amplify Scheme/tail-call/multi-shot control with owned service execution and actual parallel consumers; prove reductions in repeated work on matched populations."; attribute :>> cost="Queue/admission/GC/control overhead remains explicit; performance stays unmeasured until matched evidence exists."; }
  part def Depends { ref part predecessor:Result; ref part successor:Result; }
  part rootsToCollector:Depends { ref part :>> predecessor=roots; ref part :>> successor=collector; }
  part collectorToLifetime:Depends { ref part :>> predecessor=collector; ref part :>> successor=lifetime; }
  part lifetimeToExecution:Depends { ref part :>> predecessor=lifetime; ref part :>> successor=execution; }
  part def Need { ref part result:Result; attribute id:String; attribute condition:String; }
  part rootsNeed0:Need { ref part :>> result=roots; attribute :>> id="ROOT-SOURCE-UNION"; attribute :>> condition="Complete canonical source/writer/borrow census including generator, reflection, setup and admitted native entries; actual C freeze/store/refusal refinement."; }
  part rootsNeed1:Need { ref part :>> result=roots; attribute :>> id="ROOT-NATIVE-UNION"; attribute :>> condition="Real composed six-kind root/relocation/multi-shot/exit PBT, independent controls and exported replay/shrink on the complete candidate."; }
  part rootsNeed2:Need { ref part :>> result=roots; attribute :>> id="ROOT-CONSUMERS"; attribute :>> condition="Complete applicable original consumers with unchanged manifests/limits; classify any retained failure through actual source evidence, never by name."; }
  part collectorNeed0:Need { ref part :>> result=collector; attribute :>> id="COPY-PHYSICAL"; attribute :>> condition="Complete census, packing, continuous capacity, unique copy ownership and CAS-loss refunds with actual endpoints."; }
  part collectorNeed1:Need { ref part :>> result=collector; attribute :>> id="WORKER-RESTORE"; attribute :>> condition="Real W!=R work/Tail handoff and every R-context restoration/refusal with physical space ownership."; }
  part collectorNeed2:Need { ref part :>> result=collector; attribute :>> id="COLLECTOR-CONSUMERS"; attribute :>> condition="Full applicable producer/GC/control consumers, actual work/peak accounting and preserved failures."; }
  part lifetimeNeed0:Need { ref part :>> result=lifetime; attribute :>> id="MEMBER-OWNERSHIP"; attribute :>> condition="Rooted startup/init/publication and generation/isolation with complete real failure endpoints."; }
  part lifetimeNeed1:Need { ref part :>> result=lifetime; attribute :>> id="RETIREMENT-EFFECTS"; attribute :>> condition="Actual join/unknown/deferred destructor/root and resource ownership transfer, callback/stop/drain contracts."; }
  part lifetimeNeed2:Need { ref part :>> result=lifetime; attribute :>> id="LIFETIME-CONSUMERS"; attribute :>> condition="Complete registry/lifecycle/GC-FFI consumers; healthy VM continues GC with isolated unknown join."; }
  part executionNeed0:Need { ref part :>> result=execution; attribute :>> id="REQUEST-OWNERSHIP"; attribute :>> condition="Actual service/waiter/FIFO publication and request activation paths replace repeated control capture with explicit ownership."; }
  part executionNeed1:Need { ref part :>> result=execution; attribute :>> id="COMPLETE-PRODUCT"; attribute :>> condition="All original GSI/GSC/PR/stress and Gerbil product consumers on the final current producer; real CI scope explicit."; }
  part executionNeed2:Need { ref part :>> result=execution; attribute :>> id="MATCHED-RELEASE"; attribute :>> condition="Matched full-workload latency/throughput/peak/build observations; no assumed speedup, relaxed limit or inherited repair credit."; }
  // One post-foundation replacement, not a fifth foundation result or SMP pass.
  part bindingActivation:Result {
    attribute :>> countAxis="post-foundation";
    attribute :>> id="binding-read-activation";
    attribute :>> title="Lifecycle-owned generated binding reads";
    attribute :>> replacement="Context/module admission, current-directory reads, cooperative freeze and last-entry drain as one owner; no per-host admission/cache or duplicate permit/epoch state.";
    attribute :>> validation="Full declared p1 consumer/ABI/PBT/failure-publication cohort, explicit baseline default-SMP attribution and matched complete request/composed measurements.";
    attribute :>> falsifier="An unauthenticated host, stale VM identity, premature fixup descriptor or early context reclamation can execute; a known failure is relabeled pass.";
    attribute :>> benefit="Remove repeated raw-native owner checks from admitted generated reads while preserving current values, multi-shot frames and C portability.";
    attribute :>> cost="One native VM identity per configured context slot and one fixup word per module. Stable runtime speedup is not established; p1 request -2.299% and composed +0.298% overlap.";
    attribute :>> deliveryStatus="QUALIFIED_C_TARGET";
  }
  part bindingNeed0:Need { ref part :>> result=bindingActivation; attribute :>> id="BINDING-OWNER"; attribute :>> condition="Complete caller/read/publication/freeze/drain refinement and source-selected native evidence; no full CFFI or scheduler promotion."; }
  part bindingNeed1:Need { ref part :>> result=bindingActivation; attribute :>> id="BINDING-COST"; attribute :>> condition="Actual source-bound full populations and added memory, including rejected designs and no universal speedup claim."; }
  part sfunEntry:Result {
    attribute :>> countAxis="post-foundation";
    attribute :>> id="generated-sfun-activation";
    attribute :>> title="Generated SFUN physical activation and root span";
    attribute :>> replacement="Replace per-raw-argument RC blocks and separate marker cleanup with one activation-owned span, aligned census/scan, final frame handoff and last-use/terminal cleanup.";
    attribute :>> validation="Production replay/shrink, bank/marker callout failures, moving GC before marker, all SFUN result forms, actual processor1, map multi-shot restoration and original ABI/layout/population controls.";
    attribute :>> falsifier="Logical handler restoration frees a still-live physical C bank, an argument escapes census/scan, stale raw C locals overwrite moved roots, or baseline failure is relabeled passing.";
    attribute :>> benefit="One lifetime owner for entry, raw/conversion writes, scanner coverage and physical exit; eliminate repeated root-node allocations for many raw inputs.";
    attribute :>> cost="Known-PERM zero arguments use no bank; moving zero procedures retain one. RC header+8 bytes, activation+8, this-profile GSTATE+40. Final4096-call medians zero -1.325%, one +10.370%, eight -29.618%; small noisy samples, no universal speedup.";
    attribute :>> deliveryStatus="QUALIFIED_C_TARGET";
  }
  part sfunNeed0:Need { ref part :>> result=sfunEntry; attribute :>> id="SFUN-OWNER"; attribute :>> condition="Complete generated-entry/span/writer/GC/frame/physical-exit source refinement and actual consumers; not whole foreign-thread/CFFI admission."; }
  part sfunNeed1:Need { ref part :>> result=sfunEntry; attribute :>> id="SFUN-COST"; attribute :>> condition="Source-matched zero/one/eight raw-input measurements and actual layout/accounting; preserve regressions and state conditional benefit."; }
  part rootWrite:Result {
    attribute :>> countAxis="post-foundation";
    attribute :>> id="root-write-authority";
    attribute :>> title="One RC-domain mutation/borrow source contract, stable ABI";
    attribute :>> replacement="Unify ordinary primary and generated SFUN span stores plus borrow admission at the existing RC source gate; reuse accepted constructors/scanners/physical-exit owners. VM/token-table layout retirement is separate and blocked.";
    attribute :>> validation="Actual SFUN/RC stateful and nonzero histories, owner/frozen/borrow refusal, nested/multi-shot GC and exit, current frames/layout, same-ABI old module reuse and older-ABI refusal, original full population and paired costs.";
    attribute :>> falsifier="A primary/span mutator bypasses its source, borrowed primary identity rebinds, frozen/wrong-owner/shared-borrow spans admit writes, logical revocation releases physical ownership, ABI reuse is inferred without actual execution, or known failures are labeled passing.";
    attribute :>> benefit="One actual RC source mutation policy instead of separately maintained primary/span/partial-borrow guards; one future native-root barrier seam without extra metadata, permits or new native namespace. Preserve native consumer ABI for implementation-only changes.";
    attribute :>> cost="One index/borrow-mode decision and an additional source call boundary; no new root/context/VM storage or allocation. Measure full paired workloads; no universal speedup. Deferred combined proposal512-byte savings are explicitly not a benefit of this ABI-stable cut.";
    attribute :>> deliveryStatus="PUBLISHED";
  }
  part rootWriteNeed0:Need { ref part :>> result=rootWrite; attribute :>> id="ROOT-WRITE-OWNER"; attribute :>> condition="Complete RC primary/span writer and borrow source contract, actual scan/exit consumers and preserved ABI; no arbitrary CFFI or independent SMP promotion."; }
  part rootWriteNeed1:Need { ref part :>> result=rootWrite; attribute :>> id="ROOT-WRITE-COST"; attribute :>> condition="Exact unchanged role layouts and paired zero/one/eight workloads; preserve regressions, no deferred storage or whole-workflow speedup credit."; }
  part pipeDomain:Result {
    attribute :>> countAxis="post-foundation";
    attribute :>> id="pipe-domain-owner";
    attribute :>> title="One shared pipe domain across endpoint construction, I/O, wait and close";
    attribute :>> replacement="Replace endpoint-local mutex creation for peer-shared FIFO/cursors/close state with one constructor-published Scheme mutex for vector/string/u8 pipe pairs; reuse existing methods and public names.";
    attribute :>> validation="Actual endpoint identities,12 histories408 actions,3 timeout exits, pinned processor1 with768 values, replay/shrink, original I/O and multi-shot/root consumers, explicit generation closure and matched costs.";
    attribute :>> falsifier="Peer endpoints have distinct guards, any aliased writer uses another lock, waiting retains ownership, timeout exit leaks ownership, close loses wake, or native/model evidence promotes whole SMP.";
    attribute :>> benefit="One mutex allocation per pair instead of two; a single real source domain excludes concurrent peer mutation without introducing permit tables or address caches.";
    attribute :>> cost="Peer directions now contend on their actual shared state. Optional internal constructor argument and generation/consumer proof maintenance remain; throughput/peak claims require actual paired measurements.";
    attribute :>> deliveryStatus="QUALIFIED_C_TARGET";
  }
  part pipeNeed0:Need { ref part :>> result=pipeDomain; attribute :>> id="PIPE-OWNER-RESULT"; attribute :>> condition="Complete source construction/write/wait/close/exit owner and actual native consumers, not only an identity assertion or one setter."; }
  part pipeNeed1:Need { ref part :>> result=pipeDomain; attribute :>> id="PIPE-COST-RESULT"; attribute :>> condition="Matched4096-pair cost and explicit predecessor SFUN mechanism/noise attribution. No universal runtime speedup or peak-memory credit."; }
  part entryAdmission:Result {
    attribute :>> countAxis="post-foundation";
    attribute :>> id="rc-entry-admission";
    attribute :>> title="RC source and activation-owned argument admission";
    attribute :>> replacement="One source gate covers registration/write/borrow; positive SFUN span mutation requires a live prepared/active record rather than a borrow count. Logical revoke retains physical roots without mutation permission.";
    attribute :>> validation="Exact retained-scope baseline negative, native replay/shrink/GC/exception/nonzero consumers, source-matched0/1/8 cost and actual linked code.";
    attribute :>> falsifier="Raw span writes or revoked records can mutate; registration bypasses freeze; roots leave before physical end; arbitrary positive speedup is inferred from fewer calls.";
    attribute :>> benefit="Close actual activation/source ownership bypasses without a new permit table or metadata layout; shared policy colocation can remove a forwarding call.";
    attribute :>> cost="Extra kind/identity checks; native net timing remains conditional and must be measured. No general CFFI or whole-SMP claim.";
    attribute :>> deliveryStatus="QUALIFIED_C_TARGET";
  }
  part entryNeed0:Need { ref part :>> result=entryAdmission; attribute :>> id="ENTRY-OWNER-RESULT"; attribute :>> condition="Complete actual source/activation/borrow/scan/physical-exit consumers, not a single setter."; }
  part entryNeed1:Need { ref part :>> result=entryAdmission; attribute :>> id="ENTRY-COST-RESULT"; attribute :>> condition="Exact linked call structure and paired workloads; preserve negative timing and no whole-mode promotion."; }
  part authorityRetirement:Result {
    attribute :>> countAxis="post-foundation";
    attribute :>> id="authority-service-retirement";
    attribute :>> title="Retire obsolete parallel authority service";
    attribute :>> replacement="Actual lifecycle/RC source authority replaces the old actor/tag/role service; retire code, initializer, archive/private header/distribution and synthetic self-test together.";
    attribute :>> validation="Exact old API witness and candidate refusal; archive member/symbol removal; full native current authority/root/exception/multi-shot consumers, unchanged layout and paired/frozen-binary costs.";
    attribute :>> falsifier="Old service still has real production callers or appears in the archive; current writer/borrow semantics are weakened; ABI layout savings or stable speedup are fabricated.";
    attribute :>> benefit="One actual authority owner, five fewer queued paths, one fewer native compilation/archive unit and no competing private protocol API.";
    attribute :>> cost="Dormant public representation remains deferred debt; no512-byte savings. Whole-SMP/default/compiler attribution and stable net timing remain separate.";
    attribute :>> deliveryStatus="QUALIFIED_C_TARGET";
  }
  part retireNeed0:Need { ref part :>> result=authorityRetirement; attribute :>> id="RETIRE-OWNER-RESULT"; attribute :>> condition="Whole old service caller/build/private-API retirement and actual authority consumers; no alias or merely renamed owner."; }
  part retireNeed1:Need { ref part :>> result=authorityRetirement; attribute :>> id="RETIRE-COST-RESULT"; attribute :>> condition="Measured source/code/storage bounds and paired/frozen1-arg regression evidence; no untested512-byte or universal timing claim."; }
  part def Route { ref part unit:GambitPendingCuts::Delivery; attribute target:String; attribute disposition:String; }
  part route0:Route { ref part :>> unit=GambitPendingCuts::headerDelivery; attribute :>> target="support"; attribute :>> disposition="Only ABI/layout hunks transitively required by each result;46 primary paths are not46 approved files."; }
  part route1:Route { ref part :>> unit=GambitPendingCuts::borrowDelivery; attribute :>> target="frozen-roots"; attribute :>> disposition="Complete admitted native root borrow/callback responsibilities feed result1."; }
  part route2:Route { ref part :>> unit=GambitPendingCuts::writerDelivery; attribute :>> target="frozen-roots"; attribute :>> disposition="Ordinary globals3.5.3.1 is internal work; complete writer population, not one guarded setter."; }
  part route3:Route { ref part :>> unit=GambitPendingCuts::censusDelivery; attribute :>> target="frozen-roots"; attribute :>> disposition="Compose all root kinds, source lifetime and actual freeze/scan/exit."; }
  part route4:Route { ref part :>> unit=GambitPendingCuts::censusCapacity; attribute :>> target="independent-collector"; attribute :>> disposition="Complete object/frame physical census, not an isolated bound check."; }
  part route5:Route { ref part :>> unit=GambitPendingCuts::packingDelivery; attribute :>> target="independent-collector"; attribute :>> disposition="Reservations, intervals, refunds and restore capacity form one result."; }
  part route6:Route { ref part :>> unit=GambitPendingCuts::arenaDelivery; attribute :>> target="independent-collector"; attribute :>> disposition="Independent worker resources and unique scan/copy/Tail ownership."; }
  part route7:Route { ref part :>> unit=GambitPendingCuts::restoreDelivery; attribute :>> target="independent-collector"; attribute :>> disposition="Restore every root context using admitted worker tails and complete frames."; }
  part route8:Route { ref part :>> unit=GambitPendingCuts::retirementDelivery; attribute :>> target="owned-lifetime"; attribute :>> disposition="Startup/member/exit custody and unknown-result isolation."; }
  part route9:Route { ref part :>> unit=GambitPendingCuts::activationDelivery; attribute :>> target="frozen-roots"; attribute :>> disposition="Early root parameter/write/exit obligations feed result1; affine resource effects and unknown-owner retirement feed result3 as separate hunks in these files."; }
  part route10:Route { ref part :>> unit=GambitPendingCuts::schedulerDelivery; attribute :>> target="request-product"; attribute :>> disposition="Request/waiter/service ownership and actual whole workload consumers."; }
  part route11:Route { ref part :>> unit=GambitPendingCuts::toolchainDelivery; attribute :>> target="support"; attribute :>> disposition="Existing C23/profile support; no new profile layer or SMP credit."; }
  part route12:Route { ref part :>> unit=GambitPendingCuts::buildDelivery; attribute :>> target="support"; attribute :>> disposition="One persistent workspace, exact product reuse and actual consumer boundaries; no main-result credit."; }
  part route13:Route { ref part :>> unit=GambitPendingCuts::distributionDelivery; attribute :>> target="support"; attribute :>> disposition="Attach generated C to its exact producing source; never a standalone generated-code REV."; }
  part route14:Route { ref part :>> unit=GambitPendingCuts::ciDelivery; attribute :>> target="support"; attribute :>> disposition="CI follows real submitted source and consumers; support success does not certify whole SMP."; }
  part def Impact { ref part result:Result; ref part family:GambitModernCDeliveryPlan::AcceptanceFamily; attribute meaning:String; }
  part rootsImpact2:Impact { ref part :>> result=roots; ref part :>> family=GambitModernCDeliveryPlan::a2; attribute :>> meaning="Impact/reuse route only; not a family admission or guaranteed increment."; }
  part rootsImpact3:Impact { ref part :>> result=roots; ref part :>> family=GambitModernCDeliveryPlan::a3; attribute :>> meaning="Impact/reuse route only; not a family admission or guaranteed increment."; }
  part rootsImpact8:Impact { ref part :>> result=roots; ref part :>> family=GambitModernCDeliveryPlan::a8; attribute :>> meaning="Impact/reuse route only; not a family admission or guaranteed increment."; }
  part rootsImpact10:Impact { ref part :>> result=roots; ref part :>> family=GambitModernCDeliveryPlan::a10; attribute :>> meaning="Impact/reuse route only; not a family admission or guaranteed increment."; }
  part collectorImpact6:Impact { ref part :>> result=collector; ref part :>> family=GambitModernCDeliveryPlan::a6; attribute :>> meaning="Impact/reuse route only; not a family admission or guaranteed increment."; }
  part collectorImpact7:Impact { ref part :>> result=collector; ref part :>> family=GambitModernCDeliveryPlan::a7; attribute :>> meaning="Impact/reuse route only; not a family admission or guaranteed increment."; }
  part collectorImpact10:Impact { ref part :>> result=collector; ref part :>> family=GambitModernCDeliveryPlan::a10; attribute :>> meaning="Impact/reuse route only; not a family admission or guaranteed increment."; }
  part collectorImpact12:Impact { ref part :>> result=collector; ref part :>> family=GambitModernCDeliveryPlan::a12; attribute :>> meaning="Impact/reuse route only; not a family admission or guaranteed increment."; }
  part lifetimeImpact8:Impact { ref part :>> result=lifetime; ref part :>> family=GambitModernCDeliveryPlan::a8; attribute :>> meaning="Impact/reuse route only; not a family admission or guaranteed increment."; }
  part lifetimeImpact9:Impact { ref part :>> result=lifetime; ref part :>> family=GambitModernCDeliveryPlan::a9; attribute :>> meaning="Impact/reuse route only; not a family admission or guaranteed increment."; }
  part lifetimeImpact10:Impact { ref part :>> result=lifetime; ref part :>> family=GambitModernCDeliveryPlan::a10; attribute :>> meaning="Impact/reuse route only; not a family admission or guaranteed increment."; }
  part executionImpact2:Impact { ref part :>> result=execution; ref part :>> family=GambitModernCDeliveryPlan::a2; attribute :>> meaning="Impact/reuse route only; not a family admission or guaranteed increment."; }
  part executionImpact3:Impact { ref part :>> result=execution; ref part :>> family=GambitModernCDeliveryPlan::a3; attribute :>> meaning="Impact/reuse route only; not a family admission or guaranteed increment."; }
  part executionImpact4:Impact { ref part :>> result=execution; ref part :>> family=GambitModernCDeliveryPlan::a4; attribute :>> meaning="Impact/reuse route only; not a family admission or guaranteed increment."; }
  part executionImpact5:Impact { ref part :>> result=execution; ref part :>> family=GambitModernCDeliveryPlan::a5; attribute :>> meaning="Impact/reuse route only; not a family admission or guaranteed increment."; }
  part executionImpact6:Impact { ref part :>> result=execution; ref part :>> family=GambitModernCDeliveryPlan::a6; attribute :>> meaning="Impact/reuse route only; not a family admission or guaranteed increment."; }
  part executionImpact7:Impact { ref part :>> result=execution; ref part :>> family=GambitModernCDeliveryPlan::a7; attribute :>> meaning="Impact/reuse route only; not a family admission or guaranteed increment."; }
  part executionImpact11:Impact { ref part :>> result=execution; ref part :>> family=GambitModernCDeliveryPlan::a11; attribute :>> meaning="Impact/reuse route only; not a family admission or guaranteed increment."; }
  part executionImpact12:Impact { ref part :>> result=execution; ref part :>> family=GambitModernCDeliveryPlan::a12; attribute :>> meaning="Impact/reuse route only; not a family admission or guaranteed increment."; }
}
