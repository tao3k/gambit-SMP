package GambitAuthorityRetirement {
 private import ScalarValues::*;
 attribute stage:String="authority-service-retirement";
 attribute baseline:String="3ab1444b532c045051c9aa636527006754aaaa23";
 attribute scope:String="Retire the entire obsolete native_scope code/initializer/build/private-header/self-test service. Existing lifecycle/RC authority is the replacement. Keep exact current VM/public layout; two unqualified header-layout deltas remain independent BLOCKED work, with no512-byte saving claim.";
 attribute formalDuty:String="Reuse existing native_entry_admission.qnt and root_store_projection.qnt for actual source/activation/borrow/physical-exit semantics. No new state machine or Lean theorem for deleting an unused alternative implementation. Source caller closure, archive/link/header and real runtime consumers supply refinement evidence.";
 attribute sourceCases:String="caller-closure;build-retirement;actual-authority;layout-boundary;artifact-custody";
 attribute requiredCases:String="baseline-api;retired-api;production-pbt;nonzero;continuation;original-consumers;model;cost;source-custody";
 part def Component { attribute source:String; attribute owns:String; attribute contract:String; }
 part oldService:Component { attribute :>> source="vendor/gambit/lib/native_scope.c;vendor/gambit/lib/native_scope.h;vendor/gambit/lib/setup.c;vendor/gambit/lib/makefile.in;vendor/gambit/tests/native-scope.c;vendor/gambit/tests/makefile.in"; attribute :>> owns="Remove obsolete initialization, object/header/distribution dependency, all private tag/actor/role APIs and synthetic test target. Actual public generated entry names remain."; attribute :>> contract="Old baseline witness calls the actual API successfully. Candidate no longer contains its archive member/exported symbols or private header. Old private callers must fail; no shim or parallel namespace. Existing official test1–12 and their limits remain unchanged."; }
 part actualOwner:Component { attribute :>> source="vendor/gambit/lib/_mem/rc-allocation.inc;vendor/gambit/lib/_c_intf/sfun-entry.inc;vendor/gambit/lib/_setup/vm-registry.inc;vendor/gambit/lib/_setup/vm-lifecycle.inc"; attribute :>> owns="Already qualified actual source/activation authority, canonical roots and physical last-use drain. This retirement adds no new admission owner or scheme semantics."; attribute :>> contract="Old service is not an owner of these real writes. Native tests still exercise exact source, wrong-owner/frozen/revoked refusal, constructor/exception/GC/multi-shot and RC p2. Preserve failed or unknown join responsibility; no new terminal permission from deleting a table API."; }
 part representation:Component { attribute :>> source="vendor/gambit/include/_gambit/vm_state.h.in;vendor/gambit/include/_gambit/write_authority.h.in"; attribute :>> owns="Existing layout remains byte-identical. Dormant field/type is explicit deferred representation debt, not an active permission table or a new padding field."; attribute :>> contract="Do not apply the two pending template deletions. Historical combined division failure is not attributed away. No512-byte reduction, changed ABI or total VM memory saving is admitted. Real old public modules/callbacks must execute."; }
 attribute refinements:String="callerMap;ownerMap;exitMap";
 part def Refinement { attribute actions:String; attribute source:String; attribute guard:String; attribute obligation:String; attribute quint:String; attribute leanDuty:String default="No new arithmetic/address law or duplicated lifecycle proof."; }
 part callerMap:Refinement { attribute :>> actions="qualifyHost;publishCarrier;jointIssue"; attribute :>> source="setup_vmstate and removal of old native_scope initializer; NORMAL_C/H/O and actual archive producer"; attribute :>> guard="Actual source caller closure and generated build/distribution lists, not absence from one name search. Archive rebuilt by existing Make removes old members; header layout stays exact."; attribute :>> obligation="RETIRE-CALLERS"; attribute :>> quint="dev/refactoring/modern-c/models/quint/native_entry_admission.qnt"; }
 part ownerMap:Refinement { attribute :>> actions="writeEntryState;populateConverted;borrowCell;freeze;scan"; attribute :>> source="Actual lifecycle/RC source and SFUN adapter from3ab1444b"; attribute :>> guard="Same actual authorization/roots implementation and ABI; native tests prove consumers still use it. No renewed permission from dormant storage."; attribute :>> obligation="RETIRE-OWNER"; attribute :>> quint="dev/refactoring/modern-c/models/quint/native_entry_admission.qnt;dev/refactoring/modern-c/models/quint/root_store_projection.qnt"; }
 part exitMap:Refinement { attribute :>> actions="revokeMarker;recordOutcome;settleKnown;retireCarrier"; attribute :>> source="Existing ___end_sfun / lifecycle physical exit and RC borrow return"; attribute :>> guard="Existing physical last-use and cooperative-stop assumptions. No changed thread/join behavior; unknown joins are not independently solved by unused-code deletion."; attribute :>> obligation="RETIRE-EXIT"; attribute :>> quint="dev/refactoring/modern-c/models/quint/native_entry_admission.qnt"; }
 part def Obligation { attribute id:String; attribute status:String; attribute premise:String; }
 attribute obligations:String="callers;build;owner;exitProof;layout;reuse;costProof";
 part callers:Obligation { attribute :>> id="RETIRE-CALLERS"; attribute :>> status="CLOSED"; attribute :>> premise="Old code has only initializer/build/self-test consumers; all retire together with private API refusal."; }
 part build:Obligation { attribute :>> id="RETIRE-BUILD"; attribute :>> status="CLOSED"; attribute :>> premise="No archive member/export/private header/test/distribution dependency survives."; }
 part owner:Obligation { attribute :>> id="RETIRE-OWNER"; attribute :>> status="CLOSED"; attribute :>> premise="Actual source and activation authority still owns writes/borrows/GC with zero new runtime records."; }
 part exitProof:Obligation { attribute :>> id="RETIRE-EXIT"; attribute :>> status="CLOSED"; attribute :>> premise="Logical revoke retains canonical roots through GC and physical exit; real exceptions/nesting/multi-shot consumers pass."; }
 part layout:Obligation { attribute :>> id="RETIRE-LAYOUT"; attribute :>> status="CLOSED"; attribute :>> premise="Exact header bytes and five native layouts unchanged, old public consumers execute; no512-byte saving."; }
 part reuse:Obligation { attribute :>> id="RETIRE-REUSE"; attribute :>> status="CLOSED"; attribute :>> premise="Same cache/profile,51 unchanged generated artifacts; old seed preserved and archive genuinely rebuilt."; }
 part costProof:Obligation { attribute :>> id="RETIRE-COST"; attribute :>> status="CLOSED"; attribute :>> premise="Fixed4096-call paired cohorts plus exact frozen-binary repeat of1-argument regression; preserve every sample and uncertainty."; }
 part submission:GambitCommitGates::SubmissionUnit { attribute :>> kind="integration"; attribute :>> result="authority-service-retirement"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="RETIRE-TESTS"; attribute :>> method="native"; attribute :>> artifact="evidence/research/retained/modern-c/authority-retirement/qualification.json"; attribute :>> scope="Actual old API baseline/refusal and full existing RC/SFUN/frame consumers, disjoint model checks and matched costs."; }
 part learning:Need { ref part :>> gate=GambitCommitGates::learning; attribute :>> id="RETIRE-LEARNING"; attribute :>> method="source-analysis"; attribute :>> artifact="dev/refactoring/modern-c/authority-retirement.org"; attribute :>> scope="Actual activation/source authority replaces unused role protocol; code-service retirement and ABI representation are distinct."; }
 part process:Need { ref part :>> gate=GambitCommitGates::process; attribute :>> id="RETIRE-PROCESS"; attribute :>> method="source-analysis"; attribute :>> artifact="dev/refactoring/modern-c/authority-retirement.org"; attribute :>> scope="Retire five queued paths plus owned Make hunks; nine owners remain with43 original paths, no unrelated group admission."; }
 part models:Need { ref part :>> gate=GambitCommitGates::models; attribute :>> id="RETIRE-MODELS"; attribute :>> method="native"; attribute :>> artifact="evidence/research/retained/modern-c/authority-retirement/qualification.json"; attribute :>> scope="Native SDK→ASCENT binds seven obligations/three adapters; exact existing QNT/Lean reused, no proof duplication."; }
 part questions:Need { ref part :>> gate=GambitCommitGates::questions; attribute :>> id="RETIRE-QUESTIONS"; attribute :>> method="source-analysis"; attribute :>> artifact="dev/refactoring/modern-c/authority-retirement.org"; attribute :>> scope="Caller closure, private API removal, dormant layout, archive custody, old modules and1-arg performance attribution addressed explicitly."; }
}
