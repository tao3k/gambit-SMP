package GambitRootWrite {
 private import ScalarValues::*;
 attribute stage:String="root-write-authority";
 attribute baseline:String="13104c8a6e99dd5e474fa08b7ab329b7a800fbd1";
 attribute scope:String="One complete mutation-authority consolidation: actual lifecycle entry and RC source gate own primary/span writes, borrow admission, cooperative freeze and physical exit. Retire the unused VM token table, its build object and synthetic check; keep actual generated-entry/RC consumers. General arbitrary foreign entry and asynchronous owner-death recovery remain outside.";
 attribute formalDuty:String="Existing native_entry_admission.qnt owns generated-entry/freeze/physical-exit interleavings; root_store_projection.qnt owns canonical aliases, parked borrowing and storage lifetime. RootSpan.lean owns only size/address arithmetic; reuse exact unchanged proof, do not duplicate state machines or claim a C memory-model theorem.";
 attribute sourceCases:String="issuer-inheritance;primary-span-gate;freeze-and-borrow;physical-exit;retirement-consumers;source-transition";
 attribute requiredCases:String="entry-and-rc;nonzero;continuation;layout;old-module;official-population;cost;framework";
 ref part entry=GambitSfunEntry::admissionComponent;
 ref part rootSource=GambitSfunEntry::scanComponent;
 ref part physicalExit=GambitSfunEntry::exitComponent;
 attribute dependencyBoundary:String="Use the actual accepted component contracts, recompile/retest their changed C consumers. No inheritance of predecessor performance numbers or full-SMP acceptance.";
 part primary:GambitSfunEntry::Component {
  attribute :>> source="vendor/gambit/lib/rc.h;vendor/gambit/lib/_mem/rc-allocation.inc";
  attribute :>> owns="One checked source operation: ___store_rc_root; ordinary void setter and fallible primary setter retain their names/contracts.";
  attribute :>> contract="Actual PSTATE, matching live domain, owner, OPEN/not joined, positive native ownership and index bound precede any mutation under the existing RC mutex. Borrowed primary identity is immutable; an identical no-op performs no store. Positive span index requires one activation borrow. No allocation, poll, callback or new permit table.";
 }
 part span:GambitSfunEntry::Component {
  attribute :>> source="vendor/gambit/lib/_c_intf/sfun-entry.inc;vendor/gambit/include/_gambit/foreign_conversion.h.in";
  attribute :>> owns="Generated SFUN argument stores delegate to the same RC writer; the activation, canonical roots and final complete frame remain their actual owners.";
  attribute :>> contract="Retain actual owner/scope and finite generated arity. Caller reloads canonical values after any GC; the store itself cannot collect. Final call-frame copy remains noncollecting and source-gated. Do not add a second activation or claim arbitrary direct misuse of private intrinsics is admitted.";
 }
 part retirement:GambitSfunEntry::Component {
  attribute :>> source="vendor/gambit/include/_gambit/write_authority.h.in;vendor/gambit/include/_gambit/vm_state.h.in;vendor/gambit/lib/setup.c;vendor/gambit/lib/makefile.in;vendor/gambit/tests/makefile.in";
  attribute :>> owns="Retire the64-word native_scope table whose production use was initialization only; no replacement bitmap or alias namespace.";
  attribute :>> contract="Verify full selected Git-tree caller inventory and actual archive symbol absence. Drop its source/header/object, initializer, VM field and synthetic test. The existing real SFUN consumer replaces that check; distribute its Scheme/C source. Reject unintegrated rename/invalid void-return prototypes without crediting them as runtime work.";
 }
 attribute refinements:String="writerMap;freezeMap;exitMap;retirementMap";
 part def Refinement { attribute actions:String; attribute source:String; attribute guard:String; attribute obligation:String; attribute quint:String; attribute leanDuty:String default="Reuse unchanged RootSpan.lean arithmetic only; no repeated lifecycle proof."; }
 part writerMap:Refinement { attribute :>> actions="populateConverted;beginWriter;finishWriter"; attribute :>> source="___sfun_arg;___store_rc_root;___try_set_data_rc;___set_data_rc"; attribute :>> guard="Actual cooperative owner and live storage. Root mutex excludes scan/write; bound checked before pointer arithmetic. Primary identity cannot rebind while borrowed; span has exactly one activation borrow. Stronger C guards restrict the abstract permitted actions; the model does not attest native pointers."; attribute :>> obligation="ROOT-WRITER"; attribute :>> quint="dev/refactoring/modern-c/models/quint/native_entry_admission.qnt;dev/refactoring/modern-c/models/quint/root_store_projection.qnt"; }
 part freezeMap:Refinement { attribute :>> actions="borrowCell;parkBorrow;freeze;scan;restore;reloadBorrow;returnBorrow"; attribute :>> source="___borrow_rc_root;root_writer_open;RC RootTask census/scan and restore"; attribute :>> guard="Borrow retains storage, not a stale Scheme address or execution permission. Existing collective parks mutators; no waiting for borrowed roots to drain during scanning. The confined frozen-phase refusal control is not independent GC-phase qualification; actual moving GC comes from production histories."; attribute :>> obligation="ROOT-FREEZE"; attribute :>> quint="dev/refactoring/modern-c/models/quint/root_store_projection.qnt"; }
 part exitMap:Refinement { attribute :>> actions="revokeMarker;recordOutcome;settleKnown;retireCarrier"; attribute :>> source="___lifecycle_marker_kill;___end_sfun;___lifecycle_marker_abort"; attribute :>> guard="Revocation is not physical C quiescence. Last generated C use or proven terminal owner may release roots/entry; failed or unknown join grants neither permission. These consumers remain the existing owner, not token-table release bits."; attribute :>> obligation="ROOT-EXIT"; attribute :>> quint="dev/refactoring/modern-c/models/quint/native_entry_admission.qnt"; }
 part retirementMap:Refinement { attribute :>> actions="No runtime transition attributed to the retired unused table"; attribute :>> source="selected Git tree; NORMAL_C/H/O/RCFILES; source initializer; actual archive"; attribute :>> guard="The old table had zero production acquisitions/closures; its synthetic protocol tests did not guard actual root stores. The actual entry/RC tests replace the synthetic check. No claim that abstract historical role-table research proves this C path."; attribute :>> obligation="ROOT-RETIRE"; attribute :>> quint="No extra protocol model; mechanically inventory the retired consumers and independently execute actual consumers."; }
 part def Obligation { attribute id:String; attribute status:String; attribute premise:String; }
 attribute obligations:String="writer;borrow;freeze;exitProof;retire;layout;property;cost;sourceProof";
 part writer:Obligation { attribute :>> id="ROOT-WRITER"; attribute :>> status="OPEN"; attribute :>> premise="Primary/span stores share one source gate and preserve primary borrowed identity; bound before pointer arithmetic."; }
 part borrow:Obligation { attribute :>> id="ROOT-BORROW"; attribute :>> status="OPEN"; attribute :>> premise="Same actual owner/OPEN gate; zero-reference borrowed storage remains owned; release does not invent terminal permission."; }
 part freeze:Obligation { attribute :>> id="ROOT-FREEZE"; attribute :>> status="OPEN"; attribute :>> premise="Confined phase refusal plus actual GC histories; models are interleaving specifications, not C weak-memory or asynchronous stop proofs."; }
 part exitProof:Obligation { attribute :>> id="ROOT-EXIT"; attribute :>> status="OPEN"; attribute :>> premise="Nested, conversion-error and revoked-marker paths retain roots until actual physical exit; same existing owner, no new bitmap."; }
 part retire:Obligation { attribute :>> id="ROOT-RETIRE"; attribute :>> status="OPEN"; attribute :>> premise="Source caller inventory, native archive, build/distribution and real check all exclude the unused table; pending prototypes explicitly rejected."; }
 part layout:Obligation { attribute :>> id="ROOT-LAYOUT"; attribute :>> status="OPEN"; attribute :>> premise="Native sizeof, frame/root consumers and exact previous-module positive/current refusal; native modules require recompilation; no fresh whole-Gerbil build claim."; }
 part property:Obligation { attribute :>> id="ROOT-PBT"; attribute :>> status="OPEN"; attribute :>> premise="Production SFUN replay/shrink/nonzero and existing RC stateful histories execute actual stores. Observer-mutation shrink is not a minimized runtime bug."; }
 part cost:Obligation { attribute :>> id="ROOT-COST"; attribute :>> status="OPEN"; attribute :>> premise="Paired full zero/one/eight workloads, actual VM/GSTATE bytes and per-store work. Metadata saving is not heap/peak/cold-build or universal latency saving."; }
 part sourceProof:Obligation { attribute :>> id="ROOT-SOURCE"; attribute :>> status="OPEN"; attribute :>> premise="Same cache/profile, exact source retirement and native reuse; full original population and explicit baseline attribution. No tests weakened or unrelated staged source admitted."; }
 part submission:GambitCommitGates::SubmissionUnit { attribute :>> kind="integration"; attribute :>> result="root-write-authority"; attribute :>> progressDelta=1; attribute :>> supportPaths=""; }
 part def Need { ref part gate:GambitCommitGates::Gate; attribute id:String; attribute method:String; attribute artifact:String; attribute scope:String; }
 part tests:Need { ref part :>> gate=GambitCommitGates::tests; attribute :>> id="ROOT-WRITE-TESTS"; attribute :>> method="native"; attribute :>> artifact="evidence/research/retained/modern-c/root-write/qualification.json"; attribute :>> scope="Complete declared current native consumers, old-module controls, original population and matched costs; preserve known failures."; }
 part learning:Need { ref part :>> gate=GambitCommitGates::learning; attribute :>> id="ROOT-WRITE-LEARNING"; attribute :>> method="source-analysis"; attribute :>> artifact="dev/refactoring/modern-c/root-write.org"; attribute :>> scope="Actual producer/gate/scan/exit ownership replaces an unintegrated token table; explicit costs and refusal boundaries."; }
 part process:Need { ref part :>> gate=GambitCommitGates::process; attribute :>> id="ROOT-WRITE-PROCESS"; attribute :>> method="source-analysis"; attribute :>> artifact="dev/refactoring/modern-c/root-write.org"; attribute :>> scope="One complete authority source cut; rejected prototypes and original pending queue remain separately audited; no independent SMP promotion."; }
 part models:Need { ref part :>> gate=GambitCommitGates::models; attribute :>> id="ROOT-WRITE-MODELS"; attribute :>> method="native"; attribute :>> artifact="evidence/research/retained/modern-c/root-write/qualification.json"; attribute :>> scope="Native SDK/ASCENT, existing QNT interleavings and exact reused Lean arithmetic have disjoint duties; C refinement is conditional."; }
 part questions:Need { ref part :>> gate=GambitCommitGates::questions; attribute :>> id="ROOT-WRITE-QUESTIONS"; attribute :>> method="source-analysis"; attribute :>> artifact="dev/refactoring/modern-c/root-write.org"; attribute :>> scope="No new VM/token capacity; byte savings versus actual peak, per-store work, ABI rebuild and known failure attribution explicitly answered."; }
}
