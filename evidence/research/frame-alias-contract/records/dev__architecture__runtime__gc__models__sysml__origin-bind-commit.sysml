/* Modern C semantic authority; design and models only. */
package GambitOriginBindCommit { private import ScalarValues::*;
part history:GambitAssuranceRouting::ModelNeed { ref part :>> owner=GambitRuntimeAssurance::roots.component;
attribute :>> obligationId="OB-H";
attribute :>> kind="interleaving";
attribute :>> subjectPath="models/gambit/origin_bind_commit.qnt";
attribute :>> subjectScope="origin_bind_commit:one-port-one-slot-competitor-two-fields-one-GC;seed17";
attribute :>> premise="Decomposed intent/CAS/data/log/locator/root/commit actions, one owner/helper and one GC; registered source and verified stop receipts external; bounded sampling not exhaustive or native proof.";
}
part induction:GambitAssuranceRouting::ModelNeed { ref part :>> owner=GambitRuntimeAssurance::roots.component;
attribute :>> obligationId="OB-I";
attribute :>> kind="induction";
attribute :>> subjectPath="models/gambit/lean/OriginBindCommit.lean";
attribute :>> subjectScope="GambitSMP.OriginBindCommit:conditional-admission-stop-repair-and-root-laws";
attribute :>> premise="Selective first-admission, split writer-stop, idempotent private repair, moved-root preservation and recycling laws; not complete QNT/source/C induction.";
}
part firstDuty:GambitAssuranceRouting::ModelNeed { ref part :>> owner=GambitRuntimeAssurance::roots.component;
attribute :>> obligationId="OB-FIRST";
attribute :>> kind="source-refinement";
attribute :>> subjectPath="models/gambit/lean/OriginBindCommit.lean";
attribute :>> subjectScope="OB-FIRST:preinstalled-empty-port-and-first-registered-source";
attribute :>> premise="VM root ports precede Scheme payload/processor exposure. CFUN full frame, main startup exclusive root publication, worker rooted startup descriptor and fresh-host registered source have distinct receipts; marker allocation comes later.";
}
part claimDuty:GambitAssuranceRouting::ModelNeed { ref part :>> owner=GambitRuntimeAssurance::roots.component;
attribute :>> obligationId="OB-CLAIM";
attribute :>> kind="source-refinement";
attribute :>> subjectPath="models/gambit/lean/OriginBindCommit.lean";
attribute :>> subjectScope="OB-CLAIM:immutable-intent-before-slot-owner-CAS-and-reconcile";
attribute :>> premise="Fixed origin journal records candidate/expected header/token before ownership CAS. Unknown response retains intent/source; only full control-stop and data-stop allow authoritative header reconciliation; never mutate competing owner.";
}
part initDuty:GambitAssuranceRouting::ModelNeed { ref part :>> owner=GambitRuntimeAssurance::roots.component;
attribute :>> obligationId="OB-INIT";
attribute :>> kind="source-refinement";
attribute :>> subjectPath="models/gambit/lean/OriginBindCommit.lean";
attribute :>> subjectScope="OB-INIT:private-field-stores-progress-lag-and-locator";
attribute :>> premise="Separate actual metadata stores from progress bits and locator publication; stopped exclusive helper may replay only idempotent control fields from immutable intent, not allocation/destruction or collector-updated root payload.";
}
part rootDuty:GambitAssuranceRouting::ModelNeed { ref part :>> owner=GambitRuntimeAssurance::roots.component;
attribute :>> obligationId="OB-ROOT";
attribute :>> kind="source-refinement";
attribute :>> subjectPath="models/gambit/lean/OriginBindCommit.lean";
attribute :>> subjectScope="OB-ROOT:root-admission-close-cut-and-final-commit";
attribute :>> premise="Keep pending root cell safe false; old frozen source view covers GC until canonical root-admission accepts current value. Slot owns initialized scan contract before close; final commit publishes only control after full root/metadata validation.";
}
part stopDuty:GambitAssuranceRouting::ModelNeed { ref part :>> owner=GambitRuntimeAssurance::roots.component;
attribute :>> obligationId="OB-STOP";
attribute :>> kind="source-refinement";
attribute :>> subjectPath="models/gambit/lean/OriginBindCommit.lean";
attribute :>> subjectScope="OB-STOP:control-and-data-close-with-real-owner-exit-producers";
attribute :>> premise="Observed exit, close request, join error or timeout is not quiescence. Actual generated normal/nonlocal exit or verified thread/helper drain produces separate no-future/no-inflight control and data receipts before helper/recycle.";
}
part orderDuty:GambitAssuranceRouting::ModelNeed { ref part :>> owner=GambitRuntimeAssurance::work.component;
attribute :>> obligationId="OB-ORDER";
attribute :>> kind="native-memory-order";
attribute :>> subjectPath="models/gambit/lean/OriginBindCommit.lean";
attribute :>> subjectScope="OB-ORDER:atomic-owner-header-progress-ready-and-GC-C-order";
attribute :>> premise="Claim header atomic encoding and generation limits, release/acquire publication and plain-field exclusion; async owner-death help needs qualified lock-free header or explicit platform stop. Portable mutex fallback admits only covered cooperative exits.";
}
ref part priorOrigin=GambitActivationVmRouting::originDuty;
ref part priorRouter=GambitActivationVmRouting::routerDuty;
ref part priorAck=GambitBootstrapRootRecovery::ackDuty;
ref part priorExit=GambitBootstrapRootRecovery::unwindDuty;
ref part priorGate=GambitResizeBootstrapAdmission::gate;
ref part priorMembers=GambitResizeBootstrapAdmission::membership;
part dependency0:GambitAssuranceRouting::NeedDependency { ref part :>> dependent=firstDuty; ref part :>> prerequisite=history; }
part dependency1:GambitAssuranceRouting::NeedDependency { ref part :>> dependent=firstDuty; ref part :>> prerequisite=induction; }
part dependency2:GambitAssuranceRouting::NeedDependency { ref part :>> dependent=claimDuty; ref part :>> prerequisite=history; }
part dependency3:GambitAssuranceRouting::NeedDependency { ref part :>> dependent=claimDuty; ref part :>> prerequisite=induction; }
part dependency4:GambitAssuranceRouting::NeedDependency { ref part :>> dependent=initDuty; ref part :>> prerequisite=history; }
part dependency5:GambitAssuranceRouting::NeedDependency { ref part :>> dependent=initDuty; ref part :>> prerequisite=induction; }
part dependency6:GambitAssuranceRouting::NeedDependency { ref part :>> dependent=rootDuty; ref part :>> prerequisite=history; }
part dependency7:GambitAssuranceRouting::NeedDependency { ref part :>> dependent=rootDuty; ref part :>> prerequisite=induction; }
part dependency8:GambitAssuranceRouting::NeedDependency { ref part :>> dependent=stopDuty; ref part :>> prerequisite=history; }
part dependency9:GambitAssuranceRouting::NeedDependency { ref part :>> dependent=stopDuty; ref part :>> prerequisite=induction; }
part dependency10:GambitAssuranceRouting::NeedDependency { ref part :>> dependent=orderDuty; ref part :>> prerequisite=history; }
part dependency11:GambitAssuranceRouting::NeedDependency { ref part :>> dependent=orderDuty; ref part :>> prerequisite=induction; }
part dependency12:GambitAssuranceRouting::NeedDependency { ref part :>> dependent=firstDuty; ref part :>> prerequisite=priorOrigin; }
part dependency13:GambitAssuranceRouting::NeedDependency { ref part :>> dependent=firstDuty; ref part :>> prerequisite=priorRouter; }
part dependency14:GambitAssuranceRouting::NeedDependency { ref part :>> dependent=firstDuty; ref part :>> prerequisite=priorGate; }
part dependency15:GambitAssuranceRouting::NeedDependency { ref part :>> dependent=claimDuty; ref part :>> prerequisite=firstDuty; }
part dependency16:GambitAssuranceRouting::NeedDependency { ref part :>> dependent=claimDuty; ref part :>> prerequisite=stopDuty; }
part dependency17:GambitAssuranceRouting::NeedDependency { ref part :>> dependent=claimDuty; ref part :>> prerequisite=orderDuty; }
part dependency18:GambitAssuranceRouting::NeedDependency { ref part :>> dependent=initDuty; ref part :>> prerequisite=claimDuty; }
part dependency19:GambitAssuranceRouting::NeedDependency { ref part :>> dependent=initDuty; ref part :>> prerequisite=stopDuty; }
part dependency20:GambitAssuranceRouting::NeedDependency { ref part :>> dependent=rootDuty; ref part :>> prerequisite=initDuty; }
part dependency21:GambitAssuranceRouting::NeedDependency { ref part :>> dependent=rootDuty; ref part :>> prerequisite=priorGate; }
part dependency22:GambitAssuranceRouting::NeedDependency { ref part :>> dependent=rootDuty; ref part :>> prerequisite=priorAck; }
part dependency23:GambitAssuranceRouting::NeedDependency { ref part :>> dependent=stopDuty; ref part :>> prerequisite=priorExit; }
part dependency24:GambitAssuranceRouting::NeedDependency { ref part :>> dependent=stopDuty; ref part :>> prerequisite=priorMembers; }
part dependency25:GambitAssuranceRouting::NeedDependency { ref part :>> dependent=orderDuty; ref part :>> prerequisite=priorGate; }
part def CallerRow {  attribute callerId:String; attribute sourceAnchors:String; attribute actualChain:String; attribute hazard:String; attribute replacement:String; }
part caller0:CallerRow { attribute :>> callerId="CFUN-GENERATOR"; attribute :>> sourceAnchors="vendor/gambit/gsc/_ptree2.scm:2850-2874,2902-2925,3238-3251;include/gambit.h.in:10325-10404"; attribute :>> actualChain="Mapped argument alias and normal cleanup depend on conversion types"; attribute :>> hazard="Generate first RootViewPort admission plus intent/store/locator/commit and exit effects"; attribute :>> replacement="Materialized FrameSpec/PointId must cover all source roots before native publication"; }
part caller1:CallerRow { attribute :>> callerId="SELECTED-RESIZE"; attribute :>> sourceAnchors="vendor/gambit/lib/_kernel.scm:2353-2361;lib/_kernel.c:6258-6288,26338-26368,30819-30821;lib/setup.c:1155-1178"; attribute :>> actualChain="Tracked Scheme thunk uses CFUN_ARG and fs3/link2/map7, then local raw sop"; attribute :>> hazard="Pass stable source reference and journal token, not cached thunk, through resize"; attribute :>> replacement="Tracked source is not freshness/ABI proof; helper query cannot evaluate Scheme again"; }
part caller2:CallerRow { attribute :>> callerId="SFUN-MARKER"; attribute :>> sourceAnchors="vendor/gambit/include/gambit.h.in:10040-10065;lib/c_intf.c:6511-6550"; attribute :>> actualChain="SFUN macros call marker allocator before generated arguments; make marker has raw proc_or_false GC TODO"; attribute :>> hazard="Source root admission must precede marker allocation; marker receives current rooted value"; attribute :>> replacement="Fresh raw SCMOBJ with no registered parent/source refuses managed entry"; }
part caller3:CallerRow { attribute :>> callerId="MAIN-RUN"; attribute :>> sourceAnchors="vendor/gambit/lib/setup.c:3394-3423,6350-6440"; attribute :>> actualChain="Main thunk expression derives from program descriptor after VM setup and invokes run"; attribute :>> hazard="Preinstall empty root port before first GC/entry; exclusive startup cut publishes live source then marker"; attribute :>> replacement="GSTATE field existence alone is not audited root provenance; setup/producer scan closure required"; }
part caller4:CallerRow { attribute :>> callerId="WORKER-RUN"; attribute :>> sourceAnchors="vendor/gambit/lib/setup.c:763-835,905-1001"; attribute :>> actualChain="Parent may GC before startup; raw thunk goes into data_scmobj before thread create"; attribute :>> hazard="Rooted VM startup descriptor/port accepted before membership/thread exposure; reload after GC"; attribute :>> replacement="PSTATE exit/ignored join cannot destroy source or unfinished bind journal"; }
part caller5:CallerRow { attribute :>> callerId="GC-SCANNERS"; attribute :>> sourceAnchors="vendor/gambit/lib/mem.c:3898-3988,4529-4561,6845-6858"; attribute :>> actualChain="Frames/registers scanned and PSTATE fp restored; mark_rc only processor0 at selected call"; attribute :>> hazard="Pending bind refers frozen registered source; private control is not scanned as payload; accepted root uses canonical adapter"; attribute :>> replacement="Nonzero-processor RC scan remains explicit imported work, not reuse without qualification"; }
part caller6:CallerRow { attribute :>> callerId="NATIVE-CATCHER"; attribute :>> sourceAnchors="vendor/gambit/lib/setup.c:3276-3423;include/gambit.h.in:9979-9988"; attribute :>> actualChain="call can rethrow past normal marker cleanup; changed nonvolatile setjmp locals unsafe as sole log"; attribute :>> hazard="Stable VM journal records intent/progress/disposition before throw; writer receipts before handoff"; attribute :>> replacement="Observed owner exit alone does not close future CAS or in-flight plain store"; }
part caller7:CallerRow { attribute :>> callerId="THREAD-STOP"; attribute :>> sourceAnchors="vendor/gambit/lib/os_thread.c:546-590;lib/setup.c:930-936,966-971"; attribute :>> actualChain="thread_exit does not return; thread_join wrapper returns error but shrink caller ignores it"; attribute :>> hazard="Verify actual join/stop plus complete helper/borrower census for writer-closure receipt"; attribute :>> replacement="No portable arbitrary-thread-kill recovery inferred from pthread_join, timeout or dead flag"; }
part def PathRow {  attribute pathId:String; attribute sourceAnchors:String; attribute actualPath:String; attribute contract:String; attribute failure:String; attribute custodian:String; }
part path0:PathRow { attribute :>> pathId="FIRST-PORT"; attribute :>> sourceAnchors="_ptree2.scm:3238-3251;gambit.h.in:10043-10065"; attribute :>> actualPath="No existing stable origin service before marker; Scheme frame can already be precise root"; attribute :>> contract="Preinstall safe empty port; first admission links only a complete registered/frozen source; no new Scheme payload allocation"; attribute :>> failure="Absent/unknown source provenance refuses native effect"; attribute :>> custodian="Natural caller or admitted parent root until VM port accepts exact view"; }
part path1:PathRow { attribute :>> pathId="INTENT-CLAIM"; attribute :>> sourceAnchors="setup.c:1155-1178;proposed slot owner header"; attribute :>> actualPath="Local sop is not a recoverable ownership transaction"; attribute :>> contract="Immutable candidate/token and source lease precede CAS; header ownership is authoritative"; attribute :>> failure="Unreturned CAS may still complete until control-close receipt; do not infer free from one early read"; attribute :>> custodian="VM origin journal plus source view, even without known slot claim"; }
part path2:PathRow { attribute :>> pathId="PRIVATE-INIT"; attribute :>> sourceAnchors="gambit.h.in:10325-10404;proposed control layout"; attribute :>> actualPath="Multiple C stores and progress updates are not one atomic operation"; attribute :>> contract="Metadata fields, progress logs and locator separate; root payload stays safe false until admission"; attribute :>> failure="Helper after both stops can repair private idempotent metadata, never another owner or external effect"; attribute :>> custodian="Exact slot lease token owns initialization debt"; }
part path3:PathRow { attribute :>> pathId="ROOT-COMMIT"; attribute :>> sourceAnchors="mem.c:3898-3988,4529-4561;setup.c:1181-1205"; attribute :>> actualPath="GC close and relocation can intervene before native effect"; attribute :>> contract="Current source reload then root registration, then final control commit; accepted root can move before commit"; attribute :>> failure="Do not reset registered root to false or replay cached pre-GC SCMOBJ; query canonical root receipt"; attribute :>> custodian="Old source until accepted commit/terminal ACK; canonical root and scanner thereafter"; }
part path4:PathRow { attribute :>> pathId="EXIT-UNKNOWN"; attribute :>> sourceAnchors="setup.c:3276-3423;os_thread.c:546-590"; attribute :>> actualPath="Normal/nonlocal native exits and OS stop observations differ"; attribute :>> contract="Request close, verify control/data no-future and no-inflight, then exclusive helper epoch"; attribute :>> failure="Unknown exit retains journal/slot/source; frozen complete roots may permit GC, not necessarily physical recycle"; attribute :>> custodian="VM escrow; unfrozen or unregistered source still blocks safe handoff/collection"; }
part path5:PathRow { attribute :>> pathId="GC-CLOSE"; attribute :>> sourceAnchors="mem.c:6845-6858;setup.c:905-916"; attribute :>> actualPath="New processor/source may race fixed GC membership/close"; attribute :>> contract="During close keep source scan lease; private metadata may progress; root admission waits or uses included canonical root"; attribute :>> failure="No late source enrollment after sealed scan set and no published uninitialized payload"; attribute :>> custodian="Existing source/root scan participants, not stalled owner callback"; }
part path6:PathRow { attribute :>> pathId="RECYCLE"; attribute :>> sourceAnchors="mem.c:760-778,4928-4964;proposed source/result ACK"; attribute :>> actualPath="Physical free and root/initialization lifetime are distinct"; attribute :>> contract="Result/source ACK, scan/query/child/native reader drain and checked writer closure precede recycle"; attribute :>> failure="Competing slot ownership never reclaimed by failed claimant; lost commit response is not abort proof"; attribute :>> custodian="VM source/journal and exact owned slot until all gates close"; }
part def OrderRow {  attribute edgeId:String; attribute orderContract:String; attribute rejectedShortcut:String; }
part orderRow0:OrderRow { attribute :>> edgeId="PORT-ENROLL"; attribute :>> orderContract="Safe empty port installed with VM/root participant before payload or thread visibility; complete source view freezes before origin admission."; attribute :>> rejectedShortcut="No origin bootstrap via marker allocation that can itself GC an unprotected parameter."; }
part orderRow1:OrderRow { attribute :>> edgeId="INTENT-BEFORE-CAS"; attribute :>> orderContract="Immutable candidate/token/expected owner header and source custody published before ownership CAS can execute."; attribute :>> rejectedShortcut="Observing free header before in-flight control/future publication closes is not no-effect evidence."; }
part orderRow2:OrderRow { attribute :>> edgeId="FIELD-PROGRESS"; attribute :>> orderContract="Write private metadata, then release progress evidence; stopped helper may see actual store without progress bit and repair idempotently."; attribute :>> rejectedShortcut="Progress bit is not permission to read a partial payload; plain concurrent same-value writes are still excluded."; }
part orderRow3:OrderRow { attribute :>> edgeId="LOCATOR-COMMIT"; attribute :>> orderContract="Publish exact locator after complete metadata; root acceptance precedes final release commit; consumers acquire commit before reading private fields."; attribute :>> rejectedShortcut="Locator, normal C return and root admission are distinct facts; none alone implies whole binding committed."; }
part orderRow4:OrderRow { attribute :>> edgeId="ROOT-CLOSE"; attribute :>> orderContract="Canonical root-admission/GC-close cut owns scan-visible root word; during close pending source remains old registered view; relocation updates accepted root."; attribute :>> rejectedShortcut="Control helper never writes cached payload over GC-updated root; acquire fence does not legalize an arbitrary data race."; }
part orderRow5:OrderRow { attribute :>> edgeId="STOP-HELP"; attribute :>> orderContract="Close future control/data authority and drain both in-flight sets before exclusive helper; no release from owner-exit observation or failed join."; attribute :>> rejectedShortcut="Revocation counter alone cannot cancel already executing CAS/plain store; lock owner death cannot be repaired by unlocking blindly."; }
part orderRow6:OrderRow { attribute :>> edgeId="RECYCLE"; attribute :>> orderContract="Close original outcome, source/physical scan and reader debt, then checked epoch/owner-tag reuse; root/GC adapters outlive PSTATE cleanup."; attribute :>> rejectedShortcut="Async recovery needs qualified atomic/header/platform stop; general portable C fallback does not promise fault-tolerant progress."; }
part def CostRow {  attribute capability:String; attribute removedWork:String; attribute bound:String; attribute addedCost:String; attribute condition:String; }
part cost0:CostRow { attribute :>> capability="First origin bootstrap"; attribute :>> removedWork="Avoid recursive unprotected registration while allocating marker"; attribute :>> bound="C fixed safe root ports; 0 new Scheme value allocations required by control admission design"; attribute :>> addedCost="Per-port scan descriptor, generation/phase and bounded admission"; attribute :>> condition="Actual source registration/scan completeness and startup exclusion must be proved."; }
part cost1:CostRow { attribute :>> capability="Multi-store binding"; attribute :>> removedWork="Replace assumed all-or-nothing C block with explicit progress and ownership"; attribute :>> bound="One fixed intent record + one slot header + bounded field-progress mask per admitted bind"; attribute :>> addedCost="CAS/header checks, release/acquire log and locator publication"; attribute :>> condition="No new per-failure dictionary or retry-sized logs; metadata ABI size remains unmeasured."; }
part cost2:CostRow { attribute :>> capability="Unknown CAS/return"; attribute :>> removedWork="Prevent duplicate reserve or unsafe abort"; attribute :>> bound="At most one live claim token per origin intent; same journal reused"; attribute :>> addedCost="Hold source and perhaps slot while actual stop/commit unknown"; attribute :>> condition="No bounded latency or storage release from timeout."; }
part cost3:CostRow { attribute :>> capability="Helper reconstruction"; attribute :>> removedWork="Recover private metadata without repeating native effects"; attribute :>> bound="Two private fields in finite model; real InitSpec has finite declared write set"; attribute :>> addedCost="Stop receipts, exclusive helper epoch and idempotence validation"; attribute :>> condition="No GC-root payload reinitialization or allocator/destructor replay."; }
part cost4:CostRow { attribute :>> capability="GC coexistence"; attribute :>> removedWork="Let collector scan old complete view while metadata owner is unknown"; attribute :>> bound="0 required owner callbacks to scan already frozen/registered source by design"; attribute :>> addedCost="Temporary source plus canonical-root scan overlap; current-value reload"; attribute :>> condition="Unregistered/unfrozen source or incomplete writer census can still block GC."; }
part cost5:CostRow { attribute :>> capability="Asynchronous failure"; attribute :>> removedWork="Separate portability from stronger owner-death progress"; attribute :>> bound="One logical owner header, qualified representation and checked tags"; attribute :>> addedCost="Lock-free atomic/platform receipts for stronger profile; cooperative fallback otherwise"; attribute :>> condition="Atomic C semantics alone do not prove asynchronous thread-death recovery."; }
part cost6:CostRow { attribute :>> capability="Peak control budget"; attribute :>> removedWork="Replace hypothetical retry history with bounded support"; attribute :>> bound="Increment = C*portBytes + W*intentProgressBytes + required header/tickets if not already in Hc"; attribute :>> addedCost="Unknown source/frame/slot backing may remain pinned"; attribute :>> condition="Count embedded journals/root handles once; no total heap/CPU gain proved."; }
part cost7:CostRow { attribute :>> capability="Modern C first cut"; attribute :>> removedWork="Preserve GVM precision while replacing raw/native-effect assumptions"; attribute :>> bound="Generated entry InitSpec/effect/stop contract plus shared root/VM service"; attribute :>> addedCost="Generator, root adapters, writer census and C-memory refinements"; attribute :>> condition="No runtime path retired yet; Zig does not remove these obligations."; }
part def IdentityField { ref part need:GambitAssuranceRouting::ModelNeed; attribute fieldId:String; attribute sourceAnchors:String; attribute valueContract:String; attribute invalidShortcut:String; attribute failureCustodian:String; }
part fieldRow0:IdentityField { ref part :>> need=GambitOriginBindCommit::firstDuty; attribute :>> fieldId="ROOT-PORT"; attribute :>> sourceAnchors="c_intf.c:6511-6550;gambit.h.in:10043-10065"; attribute :>> valueContract="Preinstalled safe empty VM port plus complete registered source/epoch and producer membership"; attribute :>> invalidShortcut="Raw proc_or_false/cached CFUN_ARG is a stable root by itself"; attribute :>> failureCustodian="Old natural/parent source until accepted view receipt"; }
part fieldRow1:IdentityField { ref part :>> need=GambitOriginBindCommit::claimDuty; attribute :>> fieldId="IMMUTABLE-INTENT"; attribute :>> sourceAnchors="setup.c:1155-1178"; attribute :>> valueContract="Origin/session/serial, candidate, expected header, exact source lease and checked token"; attribute :>> invalidShortcut="Publish CAS before journal exists or invent second key after lost return"; attribute :>> failureCustodian="VM intent journal before first possible ownership effect"; }
part fieldRow2:IdentityField { ref part :>> need=GambitOriginBindCommit::claimDuty; attribute :>> fieldId="SLOT-OWNER"; attribute :>> sourceAnchors="proposed owner header"; attribute :>> valueContract="Atomic full lease/journal identity or qualified protected equivalent, matched before repair"; attribute :>> invalidShortcut="Free-looking header means no pending CAS or raw slot index is ownership"; attribute :>> failureCustodian="Exact owner token; other claimant keeps its slot"; }
part fieldRow3:IdentityField { ref part :>> need=GambitOriginBindCommit::initDuty; attribute :>> fieldId="FIELD-PROGRESS"; attribute :>> sourceAnchors="gambit.h.in:10325-10404;proposed InitSpec"; attribute :>> valueContract="Finite control fields, actual store vs logged completion, safe false root and locator"; attribute :>> invalidShortcut="Unlogged store implies absent store; identical concurrent stores are harmless"; attribute :>> failureCustodian="Unique initializer, then stopped exclusive helper"; }
part fieldRow4:IdentityField { ref part :>> need=GambitOriginBindCommit::stopDuty; attribute :>> fieldId="WRITER-STOP"; attribute :>> sourceAnchors="setup.c:3276-3423;os_thread.c:546-590"; attribute :>> valueContract="Separate data/control no-future and no-inflight receipts with complete producer census"; attribute :>> invalidShortcut="ownerExit flag, timeout, ignored join or generation bump alone"; attribute :>> failureCustodian="VM keeps unknown journal/root/slot lease"; }
part fieldRow5:IdentityField { ref part :>> need=GambitOriginBindCommit::rootDuty; attribute :>> fieldId="ROOT-RECEIPT"; attribute :>> sourceAnchors="mem.c:3898-3988,4529-4561"; attribute :>> valueContract="Canonical current root-admission/scan epoch and descriptor ownership"; attribute :>> invalidShortcut="Replay cached SCMOBJ or clear already registered root during repair"; attribute :>> failureCustodian="Root domain and original frozen source across GC"; }
part fieldRow6:IdentityField { ref part :>> need=GambitOriginBindCommit::rootDuty; attribute :>> fieldId="COMMIT-TAG"; attribute :>> sourceAnchors="_ptree2.scm:3238-3251;proposed final phase"; attribute :>> valueContract="Release publication after metadata, locator, root receipt; acquire before any effect"; attribute :>> invalidShortcut="Normal C return or locator alone proves whole binding committed"; attribute :>> failureCustodian="Canonical VM binding until separate source/result/readers close"; }
part def Transition { ref part need:GambitAssuranceRouting::ModelNeed; attribute fromPhase:String; attribute toPhase:String; attribute qntStep:String; attribute guardContract:String; attribute leanLaw:String; attribute sourceAnchors:String; }
part transition0:Transition { ref part :>> need=GambitOriginBindCommit::firstDuty; attribute :>> fromPhase="NoOrigin"; attribute :>> toPhase="SafeEmptyPort"; attribute :>> qntStep="installEmptyPort"; attribute :>> guardContract="Install before payload/thread/GC enrollment escape"; attribute :>> leanLaw="missingPortRejects"; attribute :>> sourceAnchors="setup.c:4773-4831;gambit.h.in:10043-10065"; }
part transition1:Transition { ref part :>> need=GambitOriginBindCommit::firstDuty; attribute :>> fromPhase="RegisteredSource"; attribute :>> toPhase="AdmittedFrozenView"; attribute :>> qntStep="freezeSource / admitOrigin"; attribute :>> guardContract="Complete mapped/parent/startup source; raw fresh host rejects"; attribute :>> leanLaw="admissionNeedsExistingRootView"; attribute :>> sourceAnchors="_kernel.c:26338-26368;c_intf.c:6511-6550"; }
part transition2:Transition { ref part :>> need=GambitOriginBindCommit::claimDuty; attribute :>> fromPhase="Admitted"; attribute :>> toPhase="IntentBeforeClaim"; attribute :>> qntStep="prepareIntent / beginCas"; attribute :>> guardContract="Immutable token/candidate/source before any delayed CAS"; attribute :>> leanLaw="dataCloseAloneIsNotEnough"; attribute :>> sourceAnchors="setup.c:1155-1178;proposed journal"; }
part transition3:Transition { ref part :>> need=GambitOriginBindCommit::claimDuty; attribute :>> fromPhase="CasUnknown"; attribute :>> toPhase="AuthoritativeOwnedOrOther"; attribute :>> qntStep="applyCas / noteCas / takeHelper"; attribute :>> guardContract="Actual header examined only with both writer-stop facts for final reconciliation"; attribute :>> leanLaw="competitorSlotRejectsRepair"; attribute :>> sourceAnchors="os_thread.c:546-590;proposed owner header"; }
part transition4:Transition { ref part :>> need=GambitOriginBindCommit::initDuty; attribute :>> fromPhase="OwnedPrivate"; attribute :>> toPhase="PartiallyInitialized"; attribute :>> qntStep="beginData / storeData / finishData / logA / logB"; attribute :>> guardContract="Actual store and logged completion are separate; unique writer"; attribute :>> leanLaw="repairAIdempotent"; attribute :>> sourceAnchors="gambit.h.in:10325-10404;proposed InitSpec"; }
part transition5:Transition { ref part :>> need=GambitOriginBindCommit::initDuty; attribute :>> fromPhase="StoppedPartial"; attribute :>> toPhase="ReconstructedPrivateMetadata"; attribute :>> qntStep="helperFieldA / helperFieldB / helperLocator"; attribute :>> guardContract="Exclusive helper, exact token, immutable idempotent fields only"; attribute :>> leanLaw="repairKeepsMovedRoot"; attribute :>> sourceAnchors="setup.c:3276-3423;proposed helper InitSpec"; }
part transition6:Transition { ref part :>> need=GambitOriginBindCommit::rootDuty; attribute :>> fromPhase="PendingRoot"; attribute :>> toPhase="CanonicalRootOwned"; attribute :>> qntStep="reloadSource / acceptRoot"; attribute :>> guardContract="Open/current root cut and complete source after GC; safe root shell remains false until acceptance"; attribute :>> leanLaw="staleRootRejectsCommit"; attribute :>> sourceAnchors="mem.c:3898-3988,4529-4561"; }
part transition7:Transition { ref part :>> need=GambitOriginBindCommit::rootDuty; attribute :>> fromPhase="ReadyMetadataAndRoot"; attribute :>> toPhase="Committed"; attribute :>> qntStep="commit / replayCommit"; attribute :>> guardContract="Complete fields/locator/current root; one final release tag; duplicate query not second commit"; attribute :>> leanLaw="commitNeedsCompleteRootAndMetadata"; attribute :>> sourceAnchors="_ptree2.scm:3238-3251;setup.c:1050-1112"; }
part transition8:Transition { ref part :>> need=GambitOriginBindCommit::stopDuty; attribute :>> fromPhase="OwnerExitObserved"; attribute :>> toPhase="VerifiedWriterStop"; attribute :>> qntStep="observeExit / requestClose / confirmDataStopped / confirmControlStopped"; attribute :>> guardContract="Observation is insufficient; actual no-future and no-inflight receipts mandatory"; attribute :>> leanLaw="outstandingControlRejectsHelper"; attribute :>> sourceAnchors="setup.c:930-936,3276-3423;os_thread.c:546-590"; }
part transition9:Transition { ref part :>> need=GambitOriginBindCommit::claimDuty; attribute :>> fromPhase="StoppedNoOwnedEffect"; attribute :>> toPhase="FencedTerminal"; attribute :>> qntStep="abortUnclaimed / abortPrivateOwned"; attribute :>> guardContract="No future CAS/data, no native effect; other header never mutated"; attribute :>> leanLaw="controlCloseAloneIsNotEnough"; attribute :>> sourceAnchors="proposed cancel/no-effect cut"; }
part transition10:Transition { ref part :>> need=GambitOriginBindCommit::rootDuty; attribute :>> fromPhase="GcClosed"; attribute :>> toPhase="CompleteOldViewOrMovedRoot"; attribute :>> qntStep="closeGc / collect / endGc"; attribute :>> guardContract="Keep source scan pin; accepted root updated by collector, not helper"; attribute :>> leanLaw="scannerPreventsSourceRelease"; attribute :>> sourceAnchors="mem.c:6845-6858,4529-4561"; }
part transition11:Transition { ref part :>> need=GambitOriginBindCommit::stopDuty; attribute :>> fromPhase="TerminalDebt"; attribute :>> toPhase="JournalRecyclable"; attribute :>> qntStep="ackSource / releaseSource / ackResult / unpinCell / reclaim"; attribute :>> guardContract="Result/source/scanner/readers and actual writer closures all complete; failed claimant frees no competitor slot"; attribute :>> leanLaw="unknownResultRetainsJournal"; attribute :>> sourceAnchors="mem.c:760-778,4928-4964"; }
part def SourceRoute { ref part need:GambitAssuranceRouting::ModelNeed; attribute sourceAnchors:String; attribute projection:String; attribute failureCustodian:String; attribute status:String; }
part route0:SourceRoute { ref part :>> need=GambitOriginBindCommit::firstDuty; attribute :>> sourceAnchors="_ptree2.scm:3238-3251;gambit.h.in:10043-10065"; attribute :>> projection="Preinstall safe empty port; first admission links only a complete registered/frozen source; no new Scheme payload allocation"; attribute :>> failureCustodian="Natural caller or admitted parent root until VM port accepts exact view"; attribute :>> status="source-and-C-order-refinement-open"; }
part route1:SourceRoute { ref part :>> need=GambitOriginBindCommit::claimDuty; attribute :>> sourceAnchors="setup.c:1155-1178;proposed slot owner header"; attribute :>> projection="Immutable candidate/token and source lease precede CAS; header ownership is authoritative"; attribute :>> failureCustodian="VM origin journal plus source view, even without known slot claim"; attribute :>> status="source-and-C-order-refinement-open"; }
part route2:SourceRoute { ref part :>> need=GambitOriginBindCommit::initDuty; attribute :>> sourceAnchors="gambit.h.in:10325-10404;proposed control layout"; attribute :>> projection="Metadata fields, progress logs and locator separate; root payload stays safe false until admission"; attribute :>> failureCustodian="Exact slot lease token owns initialization debt"; attribute :>> status="source-and-C-order-refinement-open"; }
part route3:SourceRoute { ref part :>> need=GambitOriginBindCommit::rootDuty; attribute :>> sourceAnchors="mem.c:3898-3988,4529-4561;setup.c:1181-1205"; attribute :>> projection="Current source reload then root registration, then final control commit; accepted root can move before commit"; attribute :>> failureCustodian="Old source until accepted commit/terminal ACK; canonical root and scanner thereafter"; attribute :>> status="source-and-C-order-refinement-open"; }
part route4:SourceRoute { ref part :>> need=GambitOriginBindCommit::stopDuty; attribute :>> sourceAnchors="setup.c:3276-3423;os_thread.c:546-590"; attribute :>> projection="Request close, verify control/data no-future and no-inflight, then exclusive helper epoch"; attribute :>> failureCustodian="VM escrow; unfrozen or unregistered source still blocks safe handoff/collection"; attribute :>> status="source-and-C-order-refinement-open"; }
part route5:SourceRoute { ref part :>> need=GambitOriginBindCommit::orderDuty; attribute :>> sourceAnchors="mem.c:6845-6858;setup.c:905-916"; attribute :>> projection="During close keep source scan lease; private metadata may progress; root admission waits or uses included canonical root"; attribute :>> failureCustodian="Existing source/root scan participants, not stalled owner callback"; attribute :>> status="source-and-C-order-refinement-open"; }
part def DiagramNode {  attribute nodeId:String; attribute labelText:String; }
part node0:DiagramNode { attribute :>> nodeId="port"; attribute :>> labelText="Preinstalled safe empty root port"; }
part node1:DiagramNode { attribute :>> nodeId="source"; attribute :>> labelText="Complete registered source frozen"; }
part node2:DiagramNode { attribute :>> nodeId="intent"; attribute :>> labelText="Immutable intent and source custody"; }
part node3:DiagramNode { attribute :>> nodeId="claim"; attribute :>> labelText="Ownership CAS may execute late"; }
part node4:DiagramNode { attribute :>> nodeId="private"; attribute :>> labelText="Private control fields and progress logs"; }
part node5:DiagramNode { attribute :>> nodeId="locator"; attribute :>> labelText="Exact locator; safe false payload"; }
part node6:DiagramNode { attribute :>> nodeId="root"; attribute :>> labelText="GC-aware current root admission"; }
part node7:DiagramNode { attribute :>> nodeId="commit"; attribute :>> labelText="Final release commit before native effect"; }
part node8:DiagramNode { attribute :>> nodeId="exit"; attribute :>> labelText="Owner exit observed: still unknown"; }
part node9:DiagramNode { attribute :>> nodeId="stop"; attribute :>> labelText="Data and control writers verifiably closed"; }
part node10:DiagramNode { attribute :>> nodeId="help"; attribute :>> labelText="Exclusive helper repairs private control only"; }
part node11:DiagramNode { attribute :>> nodeId="gc"; attribute :>> labelText="GC scans old view or canonical moved root"; }
part node12:DiagramNode { attribute :>> nodeId="ack"; attribute :>> labelText="Separate source/result/reader settlement"; }
part node13:DiagramNode { attribute :>> nodeId="free"; attribute :>> labelText="Recycle only exact owned support"; }
part def DiagramEdge { ref part producer:DiagramNode; ref part consumer:DiagramNode; attribute labelText:String; }
part edge0:DiagramEdge { ref part :>> producer=node0; ref part :>> consumer=node1; attribute :>> labelText="no marker before root coverage"; }
part edge1:DiagramEdge { ref part :>> producer=node1; ref part :>> consumer=node2; attribute :>> labelText="bounded first origin admission"; }
part edge2:DiagramEdge { ref part :>> producer=node2; ref part :>> consumer=node3; attribute :>> labelText="journal precedes possible CAS"; }
part edge3:DiagramEdge { ref part :>> producer=node3; ref part :>> consumer=node4; attribute :>> labelText="exact header lease owns init"; }
part edge4:DiagramEdge { ref part :>> producer=node4; ref part :>> consumer=node5; attribute :>> labelText="store and progress are separate"; }
part edge5:DiagramEdge { ref part :>> producer=node5; ref part :>> consumer=node6; attribute :>> labelText="current source reload after close"; }
part edge6:DiagramEdge { ref part :>> producer=node6; ref part :>> consumer=node7; attribute :>> labelText="metadata and root receipt required"; }
part edge7:DiagramEdge { ref part :>> producer=node3; ref part :>> consumer=node8; attribute :>> labelText="missing return or interrupted owner"; }
part edge8:DiagramEdge { ref part :>> producer=node4; ref part :>> consumer=node8; attribute :>> labelText="partial store outcome unknown"; }
part edge9:DiagramEdge { ref part :>> producer=node8; ref part :>> consumer=node9; attribute :>> labelText="observation is not stop proof"; }
part edge10:DiagramEdge { ref part :>> producer=node9; ref part :>> consumer=node10; attribute :>> labelText="no old control or data writes"; }
part edge11:DiagramEdge { ref part :>> producer=node10; ref part :>> consumer=node5; attribute :>> labelText="idempotent metadata; no payload replay"; }
part edge12:DiagramEdge { ref part :>> producer=node1; ref part :>> consumer=node11; attribute :>> labelText="old source remains scanned"; }
part edge13:DiagramEdge { ref part :>> producer=node6; ref part :>> consumer=node11; attribute :>> labelText="collector updates accepted root"; }
part edge14:DiagramEdge { ref part :>> producer=node7; ref part :>> consumer=node12; attribute :>> labelText="commit is not final ACK"; }
part edge15:DiagramEdge { ref part :>> producer=node11; ref part :>> consumer=node12; attribute :>> labelText="physical scan view must drain"; }
part edge16:DiagramEdge { ref part :>> producer=node12; ref part :>> consumer=node13; attribute :>> labelText="checked lease and reader closure"; }
part def ResearchGate { attribute gateId:String; }
part def GateNeed { ref part gate:ResearchGate; ref part need:GambitAssuranceRouting::ModelNeed; }
part gateRow0:ResearchGate { attribute :>> gateId="first-origin"; }
part gateNeed0:GateNeed { ref part :>> gate=gateRow0; ref part :>> need=GambitOriginBindCommit::firstDuty; }
part gateNeed1:GateNeed { ref part :>> gate=gateRow0; ref part :>> need=GambitOriginBindCommit::priorOrigin; }
part gateNeed2:GateNeed { ref part :>> gate=gateRow0; ref part :>> need=GambitOriginBindCommit::priorRouter; }
part gateNeed3:GateNeed { ref part :>> gate=gateRow0; ref part :>> need=GambitOriginBindCommit::priorGate; }
part gateRow1:ResearchGate { attribute :>> gateId="bind-recovery"; }
part gateNeed4:GateNeed { ref part :>> gate=gateRow1; ref part :>> need=GambitOriginBindCommit::claimDuty; }
part gateNeed5:GateNeed { ref part :>> gate=gateRow1; ref part :>> need=GambitOriginBindCommit::initDuty; }
part gateNeed6:GateNeed { ref part :>> gate=gateRow1; ref part :>> need=GambitOriginBindCommit::rootDuty; }
part gateNeed7:GateNeed { ref part :>> gate=gateRow1; ref part :>> need=GambitOriginBindCommit::stopDuty; }
part gateNeed8:GateNeed { ref part :>> gate=gateRow1; ref part :>> need=GambitOriginBindCommit::orderDuty; }
part gateNeed9:GateNeed { ref part :>> gate=gateRow1; ref part :>> need=GambitOriginBindCommit::priorAck; }
part gateNeed10:GateNeed { ref part :>> gate=gateRow1; ref part :>> need=GambitOriginBindCommit::priorExit; }
part gateRow2:ResearchGate { attribute :>> gateId="first-cut"; }
part gateNeed11:GateNeed { ref part :>> gate=gateRow2; ref part :>> need=GambitOriginBindCommit::firstDuty; }
part gateNeed12:GateNeed { ref part :>> gate=gateRow2; ref part :>> need=GambitOriginBindCommit::claimDuty; }
part gateNeed13:GateNeed { ref part :>> gate=gateRow2; ref part :>> need=GambitOriginBindCommit::initDuty; }
part gateNeed14:GateNeed { ref part :>> gate=gateRow2; ref part :>> need=GambitOriginBindCommit::rootDuty; }
part gateNeed15:GateNeed { ref part :>> gate=gateRow2; ref part :>> need=GambitOriginBindCommit::stopDuty; }
part gateNeed16:GateNeed { ref part :>> gate=gateRow2; ref part :>> need=GambitOriginBindCommit::orderDuty; }
part gateNeed17:GateNeed { ref part :>> gate=gateRow2; ref part :>> need=GambitOriginBindCommit::priorMembers; }
part gateNeed18:GateNeed { ref part :>> gate=gateRow2; ref part :>> need=GambitOriginBindCommit::priorGate; }
part def CommitCut { attribute portInstalled:Boolean; attribute registered:Boolean; attribute frozen:Boolean; attribute dataClosed:Boolean; attribute controlClosed:Boolean; attribute dataInFlight:Boolean; attribute controlInFlight:Boolean; attribute exactOwner:Boolean; attribute fieldsReady:Boolean; attribute locator:Boolean; attribute rootAccepted:Boolean; attribute rootCurrent:Boolean; attribute sourceReaders:Integer; attribute terminal:Boolean; attribute resultAck:Boolean; attribute queryReaders:Integer; attribute committed:Boolean default = false; attribute sourceAckRecorded:Boolean default = false; attribute sourceHeld:Boolean default = true; attribute canAdmit:Boolean=portInstalled and registered and frozen; attribute canHelp:Boolean=dataClosed and controlClosed and not dataInFlight and not controlInFlight; attribute canCommit:Boolean=exactOwner and fieldsReady and locator and rootAccepted and rootCurrent and not dataInFlight and not controlInFlight; attribute canReleaseSource:Boolean=sourceAckRecorded and sourceReaders==0 and ((committed and rootAccepted and rootCurrent) or terminal); attribute canRecycle:Boolean=terminal and resultAck and sourceAckRecorded and not sourceHeld and not rootAccepted and queryReaders==0 and sourceReaders==0 and canHelp; }
part missingPort:CommitCut { attribute :>> portInstalled=false; attribute :>> registered=true; attribute :>> frozen=true; attribute :>> dataClosed=false; attribute :>> controlClosed=false; attribute :>> dataInFlight=false; attribute :>> controlInFlight=false; attribute :>> exactOwner=false; attribute :>> fieldsReady=false; attribute :>> locator=false; attribute :>> rootAccepted=false; attribute :>> rootCurrent=false; attribute :>> sourceReaders=0; attribute :>> terminal=false; attribute :>> resultAck=false; attribute :>> queryReaders=0; }
part ownerExitOnly:CommitCut { attribute :>> portInstalled=true; attribute :>> registered=true; attribute :>> frozen=true; attribute :>> dataClosed=false; attribute :>> controlClosed=false; attribute :>> dataInFlight=false; attribute :>> controlInFlight=true; attribute :>> exactOwner=true; attribute :>> fieldsReady=false; attribute :>> locator=false; attribute :>> rootAccepted=false; attribute :>> rootCurrent=false; attribute :>> sourceReaders=0; attribute :>> terminal=false; attribute :>> resultAck=false; attribute :>> queryReaders=0; }
part dataStopOnly:CommitCut { attribute :>> portInstalled=true; attribute :>> registered=true; attribute :>> frozen=true; attribute :>> dataClosed=true; attribute :>> controlClosed=false; attribute :>> dataInFlight=false; attribute :>> controlInFlight=true; attribute :>> exactOwner=true; attribute :>> fieldsReady=false; attribute :>> locator=false; attribute :>> rootAccepted=false; attribute :>> rootCurrent=false; attribute :>> sourceReaders=0; attribute :>> terminal=false; attribute :>> resultAck=false; attribute :>> queryReaders=0; }
part bothStopped:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=false; attribute :>> locator=false; attribute :>> rootAccepted=false; attribute :>> rootCurrent=false; attribute :>> sourceReaders=0; attribute :>> terminal=false; attribute :>> resultAck=false; attribute :>> queryReaders=0; }
part rootMissing:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=true; attribute :>> locator=true; attribute :>> rootAccepted=false; attribute :>> rootCurrent=false; attribute :>> sourceReaders=0; attribute :>> terminal=false; attribute :>> resultAck=false; attribute :>> queryReaders=0; }
part commitReady:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=true; attribute :>> locator=true; attribute :>> rootAccepted=true; attribute :>> rootCurrent=true; attribute :>> sourceReaders=0; attribute :>> terminal=false; attribute :>> resultAck=false; attribute :>> queryReaders=0; }
part sourceScanHeld:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=true; attribute :>> locator=true; attribute :>> rootAccepted=true; attribute :>> rootCurrent=true; attribute :>> sourceReaders=1; attribute :>> terminal=false; attribute :>> resultAck=false; attribute :>> queryReaders=0; attribute :>> committed=true; attribute :>> sourceAckRecorded=true; }
part resultUnknown:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=true; attribute :>> locator=true; attribute :>> rootAccepted=false; attribute :>> rootCurrent=true; attribute :>> sourceReaders=0; attribute :>> terminal=true; attribute :>> resultAck=false; attribute :>> queryReaders=0; attribute :>> sourceAckRecorded=true; attribute :>> sourceHeld=false; }
part recycleReady:CommitCut { attribute :>> portInstalled=true; attribute :>> registered=true; attribute :>> frozen=true; attribute :>> dataClosed=true; attribute :>> controlClosed=true; attribute :>> dataInFlight=false; attribute :>> controlInFlight=false; attribute :>> exactOwner=true; attribute :>> fieldsReady=true; attribute :>> locator=true; attribute :>> rootAccepted=false; attribute :>> rootCurrent=true; attribute :>> sourceReaders=0; attribute :>> terminal=true; attribute :>> resultAck=true; attribute :>> queryReaders=0; attribute :>> sourceAckRecorded=true; attribute :>> sourceHeld=false; }
part def SupportCapacity { attribute rootPorts:Integer; attribute activeCells:Integer; attribute journals:Integer=rootPorts; attribute ownerHeaders:Integer=activeCells; attribute controlFieldBits:Integer; attribute requiredPostIntentControlAllocations:Integer=0; attribute historicalIdentityMaps:Integer=0; }
part finite:SupportCapacity { attribute :>> rootPorts=1; attribute :>> activeCells=1; attribute :>> controlFieldBits=2; }
part broader:SupportCapacity { attribute :>> rootPorts=8; attribute :>> activeCells=64; attribute :>> controlFieldBits=16; }
}
