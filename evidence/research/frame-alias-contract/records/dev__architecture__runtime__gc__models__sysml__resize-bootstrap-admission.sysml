/* Semantic authority: modern C resize bootstrap admission research. */
package GambitResizeBootstrapAdmission { private import ScalarValues::*;
part history:GambitAssuranceRouting::ModelNeed { ref part :>> owner=GambitRuntimeAssurance::roots.component;
attribute :>> obligationId="RB-H";
attribute :>> kind="interleaving";
attribute :>> subjectPath="models/gambit/resize_bootstrap_admission.qnt";
attribute :>> subjectScope="resize_bootstrap_admission:two-child-close-register-membership-rollback;seed17";
attribute :>> premise="Two child identities, one relocation epoch and atomic registry/snapshot/OS-result observations; environmental no-child/stop receipts. No C/source, arbitrary-N or liveness proof.";
}
part induction:GambitAssuranceRouting::ModelNeed { ref part :>> owner=GambitRuntimeAssurance::roots.component;
attribute :>> obligationId="RB-I";
attribute :>> kind="induction";
attribute :>> subjectPath="models/gambit/lean/ResizeBootstrapAdmission.lean";
attribute :>> subjectScope="GambitSMP.ResizeBootstrapAdmission:conditional-view-custody-membership-ledger-laws";
attribute :>> premise="Selected guard-preservation, root coverage, partial failure and accounting laws; no full QNT Step induction or C simulation.";
}
part rootView:GambitAssuranceRouting::ModelNeed { ref part :>> owner=GambitRuntimeAssurance::roots.component;
attribute :>> obligationId="RB-VIEW";
attribute :>> kind="source-refinement";
attribute :>> subjectPath="models/gambit/lean/ResizeBootstrapAdmission.lean";
attribute :>> subjectScope="RB-VIEW:CFUN-stack-alias-full-resize-view";
attribute :>> premise="Generator _ptree2/_t-c-1/_t-c-2/_t-c-3 and tracked _kernel.c establish exact selected CFUN shape. Preserve frame/context roots and origin across C value/sop copies; selected generated profile freshness and all raw writers remain open.";
}
part gate:GambitAssuranceRouting::ModelNeed { ref part :>> owner=GambitRuntimeAssurance::roots.component;
attribute :>> obligationId="RB-GATE";
attribute :>> kind="source-refinement";
attribute :>> subjectPath="models/gambit/lean/ResizeBootstrapAdmission.lean";
attribute :>> subjectScope="RB-GATE:closed-round-bootstrap-registration";
attribute :>> premise="Registry close and root acceptance linearize in one domain; frozen complete caller view covers closed-round deferral. Snapshot membership and relocation exclusion cannot be inferred from release/acquire alone.";
}
part membership:GambitAssuranceRouting::ModelNeed { ref part :>> owner=GambitRuntimeAssurance::work.component;
attribute :>> obligationId="RB-MEMBERS";
attribute :>> kind="source-refinement";
attribute :>> subjectPath="models/gambit/lean/ResizeBootstrapAdmission.lean";
attribute :>> subjectScope="RB-MEMBERS:prepared-routing-bound-collector-membership";
attribute :>> premise="Separate prepared capacity, stable routing descriptors, bound native children and committed collector members. Current processor_count drives barrier and GC partitioning; changing it needs a real generation transition, not a renamed scalar.";
}
part rollback:GambitAssuranceRouting::ModelNeed { ref part :>> owner=GambitRuntimeAssurance::roots.component;
attribute :>> obligationId="RB-ROLLBACK";
attribute :>> kind="source-refinement";
attribute :>> subjectPath="models/gambit/lean/ResizeBootstrapAdmission.lean";
attribute :>> subjectScope="RB-ROLLBACK:per-child-PSTATE-create-stop-settlement";
attribute :>> premise="Track each setup and OS-create attempt separately. Known failure cannot revoke siblings; unknown outcome blocks reuse, cleanup or retry. Exact setup_pstate/cleanup domains, callback effects and join/stop evidence need source refinement.";
}
part order:GambitAssuranceRouting::ModelNeed { ref part :>> owner=GambitRuntimeAssurance::roots.component;
attribute :>> obligationId="RB-ORDER";
attribute :>> kind="native-memory-order";
attribute :>> subjectPath="models/gambit/lean/ResizeBootstrapAdmission.lean";
attribute :>> subjectScope="RB-ORDER:close-register-scan-create-commit";
attribute :>> premise="Concrete lock/atomic publication, frozen-view pins, snapshot drain and generation commit; successful create does not order later root relocation. No native C-memory receipt.";
}
ref part priorReload=GambitThreadThunkActivation::reload;
ref part priorScope=GambitThreadThunkActivation::scope;
ref part priorRoot=GambitRestAllocatorRootPublication::roots;
part dependency0:GambitAssuranceRouting::NeedDependency { ref part :>> dependent=rootView; ref part :>> prerequisite=history; }
part dependency1:GambitAssuranceRouting::NeedDependency { ref part :>> dependent=rootView; ref part :>> prerequisite=induction; }
part dependency2:GambitAssuranceRouting::NeedDependency { ref part :>> dependent=gate; ref part :>> prerequisite=history; }
part dependency3:GambitAssuranceRouting::NeedDependency { ref part :>> dependent=gate; ref part :>> prerequisite=induction; }
part dependency4:GambitAssuranceRouting::NeedDependency { ref part :>> dependent=membership; ref part :>> prerequisite=history; }
part dependency5:GambitAssuranceRouting::NeedDependency { ref part :>> dependent=membership; ref part :>> prerequisite=induction; }
part dependency6:GambitAssuranceRouting::NeedDependency { ref part :>> dependent=rollback; ref part :>> prerequisite=history; }
part dependency7:GambitAssuranceRouting::NeedDependency { ref part :>> dependent=rollback; ref part :>> prerequisite=induction; }
part dependency8:GambitAssuranceRouting::NeedDependency { ref part :>> dependent=order; ref part :>> prerequisite=history; }
part dependency9:GambitAssuranceRouting::NeedDependency { ref part :>> dependent=order; ref part :>> prerequisite=induction; }
part dependency10:GambitAssuranceRouting::NeedDependency { ref part :>> dependent=gate; ref part :>> prerequisite=rootView; }
part dependency11:GambitAssuranceRouting::NeedDependency { ref part :>> dependent=gate; ref part :>> prerequisite=priorRoot; }
part dependency12:GambitAssuranceRouting::NeedDependency { ref part :>> dependent=membership; ref part :>> prerequisite=gate; }
part dependency13:GambitAssuranceRouting::NeedDependency { ref part :>> dependent=membership; ref part :>> prerequisite=rollback; }
part dependency14:GambitAssuranceRouting::NeedDependency { ref part :>> dependent=membership; ref part :>> prerequisite=order; }
part dependency15:GambitAssuranceRouting::NeedDependency { ref part :>> dependent=membership; ref part :>> prerequisite=priorReload; }
part dependency16:GambitAssuranceRouting::NeedDependency { ref part :>> dependent=rollback; ref part :>> prerequisite=gate; }
part dependency17:GambitAssuranceRouting::NeedDependency { ref part :>> dependent=rollback; ref part :>> prerequisite=order; }
part dependency18:GambitAssuranceRouting::NeedDependency { ref part :>> dependent=rootView; ref part :>> prerequisite=priorScope; }
part def CallerRow { attribute callerId:String; attribute sourceAnchors:String; attribute actualChain:String; attribute hazard:String; attribute replacement:String; }
part caller0:CallerRow { attribute :>> callerId="SCHEME-ORIGIN"; attribute :>> sourceAnchors="vendor/gambit/lib/_thread.scm:3158-3159,6892-6893;lib/_kernel.scm:2353-2361"; attribute :>> actualChain="##cvmr -> c-lambda(scheme-object,int)->scheme-object -> current_vm_resize"; attribute :>> hazard="Keep the mapped Scheme source as origin; ordinary caller passes ##startup-processor!"; attribute :>> replacement="No observed movable-thunk failure inferred from named startup procedure; direct C/embedding callers need explicit origins."; }
part caller1:CallerRow { attribute :>> callerId="FFI-GENERATOR"; attribute :>> sourceAnchors="vendor/gambit/gsc/_ptree2.scm:2499-2523,2773-2869,2902-3014;gsc/_parms.scm:383-388,569-575"; attribute :>> actualChain="scheme-object becomes CFUN_ARG alias; int converts separately; both types need no cleanup wrapper"; attribute :>> hazard="A rooted Scheme slot can be reused; entering a C value parameter or sop copy loses location identity"; attribute :>> replacement="No new per-call heap copy needed merely to manufacture a root; full view and reload remain required."; }
part caller2:CallerRow { attribute :>> callerId="FRAME-GENERATOR"; attribute :>> sourceAnchors="vendor/gambit/gsc/_t-c-2.scm:122-224;gsc/_t-c-3.scm:486-487;gsc/_t-c-1.scm:2133-2167"; attribute :>> actualChain="arity2 -> spill arguments and RA; fs3/link2/all-live mask7 -> CFUN OOL"; attribute :>> hazard="Treat generated shape and configured physical FRAME_SPACE as separate; context register resources are per-procedure"; attribute :>> replacement="Tracked _kernel.c shape is read, not regenerated or verified against an installed binary."; }
part caller3:CallerRow { attribute :>> callerId="TRACKED-OUTPUT"; attribute :>> sourceAnchors="vendor/gambit/lib/_kernel.c:6258-6288,26338-26368,30819-30821;include/gambit.h.in:10325-10404"; attribute :>> actualChain="arg1 aliases stack; PW_ALL writes FP/R0; two args and old RA spill before ADJFP(8) and CFUN_OOL"; attribute :>> hazard="Re-read mapped slot after moving GC; do not assume W_ALL writes every register for every procedure"; attribute :>> replacement="The literal ADJFP(8) is this tracked output only; no portable byte/ABI inference."; }
part caller4:CallerRow { attribute :>> callerId="SYNC-COPIES"; attribute :>> sourceAnchors="vendor/gambit/lib/setup.c:550-712,1015-1178;include/gambit.h.in:11599-11603"; attribute :>> actualChain="thunk -> C parameter -> local sop -> barrier tree sop0/1/2 -> vm_resize parameter"; attribute :>> hazard="Replace pointer-bearing sync payload with stable transaction identity or register/update every actual copy"; attribute :>> replacement="volatile WORD arg[2] is not an SCMOBJ root map; GC can occur inside resize even though resize has higher op priority than external GC."; }
part caller5:CallerRow { attribute :>> callerId="MEMBER-CREATE"; attribute :>> sourceAnchors="vendor/gambit/lib/setup.c:870-1003,4665-4755;lib/mem.c:4601-4700"; attribute :>> actualChain="capacity GC -> setup PSTATEs -> publish processor_count -> create OS children"; attribute :>> hazard="Root descriptor and staged membership before publication; per-child resource phases; child can bind before creator receives result"; attribute :>> replacement="Rollback setup loop decrements i without recomputing ps; treat as source-audit finding, not tested failure."; }
part caller6:CallerRow { attribute :>> callerId="COLLECTOR-CONSUMERS"; attribute :>> sourceAnchors="vendor/gambit/lib/setup.c:550-712,805-835;lib/mem.c:3898-3965,6590-6632,6790-6868"; attribute :>> actualChain="barrier tree count; GC global partition; per-context root scan; worker startup sync"; attribute :>> hazard="Committed membership controls both barrier and GC work; bootstrap registry scanned independently of runnable PSTATE"; attribute :>> replacement="Cannot let uncreated/unknown OS children become mandatory barrier participants."; }
part caller7:CallerRow { attribute :>> callerId="FAILURE-ENDPOINTS"; attribute :>> sourceAnchors="vendor/gambit/lib/setup.c:946-1001,4572-4596,4665-4707;lib/mem.c:4928-4935;lib/os_thread.c:493-566"; attribute :>> actualChain="setup failure returns; OS failure fatal; shrink join ignored; cleanup releases still/RC/native resources"; attribute :>> hazard="Attempt-indexed cleanup/stop receipts before physical PSTATE reuse; unknown results retain VM escrow"; attribute :>> replacement="Keep exact requested resize success semantics; partial growth is an abort/drain transaction, not silent smaller success."; }
part def PathRow { attribute pathId:String; attribute sourceAnchors:String; attribute actualPath:String; attribute contract:String; attribute failure:String; attribute custodian:String; }
part path0:PathRow { attribute :>> pathId="ROOT-VIEW"; attribute :>> sourceAnchors="_ptree2.scm:2850-2869;_t-c-2.scm:157-224;_kernel.c:26338-26368,30819-30821"; attribute :>> actualPath="Existing CFUN args/RA live in Scheme stack; C API copies thunk"; attribute :>> contract="Freeze complete location/context view; acquire origin before first sync/GC; reload source location after relocation"; attribute :>> failure="Missing slot, raw borrower or unknown owner refuses descriptor acceptance"; attribute :>> custodian="Caller view until VM descriptor accepted; then VM overlap until child activation acceptance"; }
part path1:PathRow { attribute :>> pathId="REGISTER-CLOSE"; attribute :>> sourceAnchors="setup.c:1132-1178;mem.c:6790-6868"; attribute :>> actualPath="No explicit bootstrap registration/closed-round cut exists"; attribute :>> contract="Accept-before-close enters pinned snapshot; close-before-accept leaves only safe metadata pending and frozen caller authoritative"; attribute :>> failure="Never wait for collector while holding registry lock or raw borrow; no copied stale thunk in pending metadata"; attribute :>> custodian="Frozen caller map/VM-held view pin, not unregistered native slot"; }
part path2:PathRow { attribute :>> pathId="MEMBERSHIP"; attribute :>> sourceAnchors="setup.c:655-656,941-1003;mem.c:6590-6632"; attribute :>> actualPath="Single processor_count drives routing and collection before OS creates"; attribute :>> contract="Prepare -> root/routing descriptor -> OS outcome+binding -> collective generation commit"; attribute :>> failure="Unknown child cannot enter committed membership or be treated as absent; old members keep current generation"; attribute :>> custodian="Resize transaction/VM until exact all-child ready commit or explicit abort/drain"; }
part path3:PathRow { attribute :>> pathId="PARTIAL-FAILURE"; attribute :>> sourceAnchors="setup.c:941-1003;os_thread.c:493-539"; attribute :>> actualPath="PSTATE prep failure and later OS failure have different effects"; attribute :>> contract="Per-child ledger Prepared/Creating/Success/Failure/Unknown/Stopped/Retired; cancel admission then drain known starts"; attribute :>> failure="No bulk rollback over successful siblings; do not reuse PSTATE on timeout or ignored join"; attribute :>> custodian="VM holds each successful or unknown child resource until exact stop/no-child and scanner drain"; }
part path4:PathRow { attribute :>> pathId="RELOAD-CONSUME"; attribute :>> sourceAnchors="setup.c:805-835;_kernel.c:6260-6288;gambit.h.in:10402"; attribute :>> actualPath="Mapped slot becomes raw thunk, then crosses sync/marker allocation"; attribute :>> contract="Stable transaction ID carries sync payload; worker reloads after context-ready then hands root to NativeActivationScope"; attribute :>> failure="Do not retain stack address across stack movement; use logical slot/frame identity and reacquire address"; attribute :>> custodian="VM bootstrap root -> exact activation acceptance; parent map pinned through retries"; }
part def OrderRow { attribute edgeId:String; attribute orderContract:String; attribute rejectedShortcut:String; }
part orderRow0:OrderRow { attribute :>> edgeId="VIEW"; attribute :>> orderContract="Arguments and RA spill plus materialized FP/R0 precede full-view acceptance; logical frame identity survives stack relocation."; attribute :>> rejectedShortcut="Pointer to current stack slot cannot by itself be a persistent RootHandle."; }
part orderRow1:OrderRow { attribute :>> edgeId="CLOSE"; attribute :>> orderContract="Register-vs-close arbitration and snapshot membership share a linearization domain; slots initialized before publishing."; attribute :>> rejectedShortcut="No live value accepted after snapshot closes merely because an atomic pointer store succeeds."; }
part orderRow2:OrderRow { attribute :>> edgeId="DEFER"; attribute :>> orderContract="Close winner retains pinned frozen caller view; GC updates that view; context-ready acquire and reload precede later descriptor fill."; attribute :>> rejectedShortcut="No caller raw borrow while waiting, no pending SCMOBJ copy outside scanned storage, no lock across rendezvous."; }
part orderRow3:OrderRow { attribute :>> edgeId="CREATE"; attribute :>> orderContract="Descriptor and per-child create reservation precede OS invocation; success/result and child binding are independent observations."; attribute :>> rejectedShortcut="Do not derive no-child from missing ACK, create error synchronization, or creator death."; }
part orderRow4:OrderRow { attribute :>> edgeId="COMMIT"; attribute :>> orderContract="Exact ready generation acquires root/OS/binding receipts and excludes closed GC; only then do barrier and GC consumers switch membership together."; attribute :>> rejectedShortcut="A scalar processor_count store is not the entire generation commit protocol."; }
part orderRow5:OrderRow { attribute :>> edgeId="RETIRE"; attribute :>> orderContract="Close entry admission, prove no child or exact stop, detach membership, drain scanner/descriptor readers, then cleanup/reuse exact PSTATE."; attribute :>> rejectedShortcut="No timeout, ignored join or duplicate cleanup decrements ownership debt."; }
part def CostRow { attribute capability:String; attribute removedWork:String; attribute bound:String; attribute addedCost:String; attribute condition:String; }
part cost0:CostRow { attribute :>> capability="Existing capacity lower bound"; attribute :>> removedWork="Reuse requested-count GC budgeting already present"; attribute :>> bound="2*131072=262144 words per requested processor; 2097152 bytes at8; two processors4194304 bytes"; attribute :>> addedCost="Physical allocation may be reused; struct/alignment, occupancy, history and native stacks are separate"; attribute :>> condition="Capacity contribution only, not extra allocation/RSS; cleanup_mem_pstate frees still/RC, not msections. Later contraction cannot erase an earlier round peak."; }
part cost1:CostRow { attribute :>> capability="Mapped origin reuse"; attribute :>> removedWork="Reuse two existing arg slots plus RA in selected CFUN rather than copy a Scheme thunk object"; attribute :>> bound="0 new Scheme value evaluations and 0 new Scheme object copies for origin admission"; attribute :>> addedCost="Logical frame pin/map and borrow/freeze/reload control; scan of existing view remains"; attribute :>> condition="Reusing existing root storage is allowed only after exact map and relocation-aware access proof."; }
part cost2:CostRow { attribute :>> capability="Stable sync identity"; attribute :>> removedWork="Remove movable thunk responsibility from local/tree sop copies"; attribute :>> bound="If K distinct live sync carrier locations existed, managed thunk roots can be 1 shared cell instead of K roots"; attribute :>> addedCost="One stable transaction lookup/lease and outcome ledger; message copies still occur"; attribute :>> condition="Not a measured K-fold speedup; current copied WORDs were never established safe roots."; }
part cost3:CostRow { attribute :>> capability="Closed-round registration"; attribute :>> removedWork="Avoid reopening an already closed snapshot for each late descriptor"; attribute :>> bound="Close loser adds 0 new descriptor roots to that round; existing frozen caller view supplies coverage"; attribute :>> addedCost="Deferred descriptor metadata and pinned view can increase retained memory"; attribute :>> condition="Does not remove caller scanning, round participation or guarantee wait-free registration."; }
part cost4:CostRow { attribute :>> capability="Membership separation"; attribute :>> removedWork="Remove unborn/unknown child from required GC/barrier participants"; attribute :>> bound="Committed set equals ready successful bound generation; two-child model rejects one-success/one-failure commit"; attribute :>> addedCost="Generation switch/routing adapter and per-child status checks"; attribute :>> condition="No throughput/latency proof; old algorithm retirement requires both barrier and collector consumer migration."; }
part cost5:CostRow { attribute :>> capability="Known setup failure"; attribute :>> removedWork="Clean exact successful preparation indices, not a repeated failing ps"; attribute :>> bound="For successful prepared set S, cleanup count is at most one per index in S"; attribute :>> addedCost="Phase-indexed initialization/cleanup receipts, including partial OS/memory init"; attribute :>> condition="Source audit exposes loop identity mismatch; native effect/reachability remains untested."; }
part cost6:CostRow { attribute :>> capability="Partial OS failure"; attribute :>> removedWork="Preserve sibling root/native custody rather than bulk rollback"; attribute :>> bound="For G successes, F failures, U unknowns, R never attempted: N=G+F+U+R once no call remains pending"; attribute :>> addedCost="G known children need stop/drain before abort cleanup; U native attempts stay escrowed"; attribute :>> condition="No silent partial resize success; unknown results prevent bounded reclamation without external receipts."; }
part cost7:CostRow { attribute :>> capability="Peak memory"; attribute :>> removedWork="Count disjoint backing classes during registration and rollback overlap"; attribute :>> bound="P=max_t(B_values + H_tx + N*L + V_pin + R_scan + PSTATE_unique + Stack_unique + U_extra)"; attribute :>> addedCost="Pending view and unknown child backing can dominate root-slot savings"; attribute :>> condition="U_extra excludes stacks/leases already counted. No whole-round peak reduction or bound on unknown retention proved."; }
part cost8:CostRow { attribute :>> capability="Refactor retirement"; attribute :>> removedWork="Replace implicit CFUN-to-C-copy ownership, raw sop thunk payload and single-count creation assumptions"; attribute :>> bound="One source-aware resize transaction consumed by generator/runtime/barrier/GC/activation"; attribute :>> addedCost="Generated effect/root plan plus root/membership/result services in modern C"; attribute :>> condition="No Zig-specific net support reduction established; 0 runtime paths retired in this study."; }
part def RootView { ref part need:GambitAssuranceRouting::ModelNeed; attribute viewId:String; attribute sourceAnchors:String; attribute actualLocation:String; attribute existingCoverage:String; attribute requiredAdaptation:String; }
part viewRow0:RootView { ref part :>> need=rootView; attribute :>> viewId="THUNK-SLOT"; attribute :>> sourceAnchors="_kernel.c:6260-6271;gambit.h.in:10402"; attribute :>> actualLocation="CFUN_ARG(1) Scheme stack location, aliases arg1"; attribute :>> existingCoverage="Existing precise frame map covers value; C thunk parameter is a separate copied value"; attribute :>> requiredAdaptation="Logical frame+slot identity; re-resolve address/value after GC; no unpinned stack pointer"; }
part viewRow1:RootView { ref part :>> need=rootView; attribute :>> viewId="COUNT-SLOT"; attribute :>> sourceAnchors="_kernel.c:6263-6281;_parms.scm:383-388"; attribute :>> actualLocation="CFUN_ARG(2) Scheme integer source; arg2 native int"; attribute :>> existingCoverage="Scheme source is in frame map; converted int is non-GC data"; attribute :>> requiredAdaptation="Do not register native int as SCMOBJ; preserve range/conversion error before resize"; }
part viewRow2:RootView { ref part :>> need=rootView; attribute :>> viewId="RETURN-FRAME"; attribute :>> sourceAnchors="_t-c-2.scm:157-224;_t-c-3.scm:486-487;_kernel.c:26358-26368"; attribute :>> actualLocation="Args spill, saved RA, current RA and fs/link/gcmap"; attribute :>> existingCoverage="fs=3/link=2/map=7 from generator; physical advance8 in tracked C"; attribute :>> requiredAdaptation="Full frame formation and return label metadata before independent scan; no physical ABI equality asserted"; }
part viewRow3:RootView { ref part :>> need=rootView; attribute :>> viewId="CONTEXT"; attribute :>> sourceAnchors="_kernel.c:26338-26348;gambit.h.in:10325-10369;mem.c:6511-6554"; attribute :>> actualLocation="FP/return materialization; register/saved/type-cache scan"; attribute :>> existingCoverage="PW_ALL here writes FP/R0, not all named registers; args already spilled"; attribute :>> requiredAdaptation="Retain exact owner/context binding; W_ALL is procedure-resource-specific"; }
part viewRow4:RootView { ref part :>> need=rootView; attribute :>> viewId="CONTROL-ROOTS"; attribute :>> sourceAnchors="mem.c:3898-3965,6555-6589,6854-6865;gambit.h.in:6550-6565"; attribute :>> actualLocation="Current processor/thread object, denv and captured continuation via precise roots"; attribute :>> existingCoverage="Use real graph traversal and slot maps; no separate copy of entire denv/continuation"; attribute :>> requiredAdaptation="All actual writers/borrowers and frame movement must refine complete frozen view; no arbitrary C local scan"; }
part viewRow5:RootView { ref part :>> need=gate; attribute :>> viewId="SYNC-COPIES"; attribute :>> sourceAnchors="setup.c:550-712,1070-1107,1169-1175;gambit.h.in:11599-11603"; attribute :>> actualLocation="Local sop and tree arg[0] copies"; attribute :>> existingCoverage="volatile WORD container has no automatic root registration"; attribute :>> requiredAdaptation="Prefer stable transaction identity; otherwise every live copy/update path needs explicit root coverage"; }
part viewRow6:RootView { ref part :>> need=gate; attribute :>> viewId="PENDING-ORIGIN"; attribute :>> sourceAnchors="setup.c:1132-1178;mem.c:6790-6868"; attribute :>> actualLocation="Complete frozen caller view while close winner rejects root insertion"; attribute :>> existingCoverage="Value stays in already scanned view; pending descriptor holds safe empty slot and origin identity only"; attribute :>> requiredAdaptation="Collector updates caller root; current-epoch reload before next-round acceptance; keep snapshot/view pins"; }
part viewRow7:RootView { ref part :>> need=rollback; attribute :>> viewId="NATIVE-RESOURCES"; attribute :>> sourceAnchors="setup.c:4572-4596,4665-4755;mem.c:4928-4935;os_thread.c:493-566"; attribute :>> actualLocation="PSTATE OS/memory/interrupt setup plus possible OS child"; attribute :>> existingCoverage="These are resource lifetimes, not interchangeable SCMOBJ slots"; attribute :>> requiredAdaptation="Attempt-indexed phase/owner receipts; cleanup callbacks can create further debts and cannot run under root control lock"; }
part def Transition { ref part need:GambitAssuranceRouting::ModelNeed; attribute fromPhase:String; attribute toPhase:String; attribute qntStep:String; attribute guardContract:String; attribute leanLaw:String; attribute sourceAnchors:String; }
part transition0:Transition { ref part :>> need=rootView; attribute :>> fromPhase="CallerMapped"; attribute :>> toPhase="FrozenView"; attribute :>> qntStep="freezeCaller"; attribute :>> guardContract="Complete required locations, no remaining raw borrower"; attribute :>> leanLaw="frozenViewCovers"; attribute :>> sourceAnchors="_t-c-2.scm:157-224;gambit.h.in:10325-10369"; }
part transition1:Transition { ref part :>> need=gate; attribute :>> fromPhase="FrozenView"; attribute :>> toPhase="Registered"; attribute :>> qntStep="registerOpen"; attribute :>> guardContract="Registration wins close; safe slot and current loaded origin; pinned registry membership"; attribute :>> leanLaw="registrationCovers"; attribute :>> sourceAnchors="setup.c:1132-1178;mem.c:6790-6868"; }
part transition2:Transition { ref part :>> need=gate; attribute :>> fromPhase="FrozenView"; attribute :>> toPhase="PendingClosed"; attribute :>> qntStep="deferClosed"; attribute :>> guardContract="Close wins; frozen caller retains authoritative value and origin identity"; attribute :>> leanLaw="deferPreservesCoverage"; attribute :>> sourceAnchors="same proposed registry cut; current source lacks it"; }
part transition3:Transition { ref part :>> need=gate; attribute :>> fromPhase="PendingClosed"; attribute :>> toPhase="ReloadedNextEpoch"; attribute :>> qntStep="collect / reopen / reloadSource"; attribute :>> guardContract="GC updates frozen view, snapshot drains and context becomes ready; no raw replay"; attribute :>> leanLaw="staleOriginRejected"; attribute :>> sourceAnchors="setup.c:870-916;mem.c:3898-3965"; }
part transition4:Transition { ref part :>> need=membership; attribute :>> fromPhase="Registered"; attribute :>> toPhase="PreparedRouting"; attribute :>> qntStep="prepareChild / publishRouting"; attribute :>> guardContract="All child PSTATE descriptors initialized, registered root precedes stable routing publication"; attribute :>> leanLaw="readyMemberRequiresBound"; attribute :>> sourceAnchors="setup.c:941-966"; }
part transition5:Transition { ref part :>> need=membership; attribute :>> fromPhase="PreparedRouting"; attribute :>> toPhase="Creating"; attribute :>> qntStep="beginCreate"; attribute :>> guardContract="One attempt per child generation, stable descriptor/reservation before OS call"; attribute :>> leanLaw="unknownPreventsReclaim"; attribute :>> sourceAnchors="setup.c:988-1001;os_thread.c:493-539"; }
part transition6:Transition { ref part :>> need=membership; attribute :>> fromPhase="Creating"; attribute :>> toPhase="BoundAndKnown"; attribute :>> qntStep="childEntry / createSuccess"; attribute :>> guardContract="Child binding may precede creator result; commit requires both and current root/context"; attribute :>> leanLaw="readyMemberRequiresBound"; attribute :>> sourceAnchors="setup.c:805-835"; }
part transition7:Transition { ref part :>> need=membership; attribute :>> fromPhase="BoundAndKnown"; attribute :>> toPhase="CommittedGeneration"; attribute :>> qntStep="commitMembers"; attribute :>> guardContract="All requested children ready; no unknown/failed child, GC gate open; shared generation commit"; attribute :>> leanLaw="commitPreservesMembership"; attribute :>> sourceAnchors="setup.c:655-656;mem.c:6590-6632"; }
part transition8:Transition { ref part :>> need=rollback; attribute :>> fromPhase="Creating"; attribute :>> toPhase="Aborting"; attribute :>> qntStep="createFailure / loseOutcome / beginAbort"; attribute :>> guardContract="Known failure and lost result distinct; stop further publication and Scheme entry"; attribute :>> leanLaw="siblingFailureRetainsCustody"; attribute :>> sourceAnchors="setup.c:946-1001"; }
part transition9:Transition { ref part :>> need=rollback; attribute :>> fromPhase="Aborting"; attribute :>> toPhase="StoppedOrNoChild"; attribute :>> qntStep="confirmNoChild / observeStopped"; attribute :>> guardContract="External exact-result or OS-stop receipt; no timeout inference"; attribute :>> leanLaw="unknownPreventsReclaim"; attribute :>> sourceAnchors="os_thread.c:493-566;setup.c:977-981"; }
part transition10:Transition { ref part :>> need=rollback; attribute :>> fromPhase="StoppedOrNoChild"; attribute :>> toPhase="RetiredChild"; attribute :>> qntStep="reclaimChild"; attribute :>> guardContract="No committed membership and no scan readers; cleanup exact child phase once"; attribute :>> leanLaw="reclaimGuardIsNecessary"; attribute :>> sourceAnchors="setup.c:946-951,4665-4707;mem.c:4928-4935"; }
part def MembershipRole { ref part need:GambitAssuranceRouting::ModelNeed; attribute roleId:String; attribute sourceAnchors:String; attribute currentResponsibility:String; attribute targetContract:String; attribute boundary:String; }
part memberRole0:MembershipRole { ref part :>> need=membership; attribute :>> roleId="REQUESTED-CAPACITY"; attribute :>> sourceAnchors="setup.c:892-913;mem.c:508-509,6330-6335"; attribute :>> currentResponsibility="mem.target_processor_count_ already drives GC minimum msection reservation"; attribute :>> targetContract="Keep requested capacity distinct from committed collectors; failed resize releases demand only when dependent children/loans settle"; attribute :>> boundary="Reuse existing capacity concept, add transaction/generation custody"; }
part memberRole1:MembershipRole { ref part :>> need=membership; attribute :>> roleId="PREPARED-PSTATE"; attribute :>> sourceAnchors="setup.c:941-955,4675-4755;mem.c:4601-4700"; attribute :>> currentResponsibility="PSTATE initialization and private stack/heap setup before create"; attribute :>> targetContract="Safe root/resource maps and exact setup phase before a native start can use it"; attribute :>> boundary="Prepared is not collector membership"; }
part memberRole2:MembershipRole { ref part :>> need=membership; attribute :>> roleId="BARRIER-ROUTING"; attribute :>> sourceAnchors="setup.c:550-712,962-964"; attribute :>> currentResponsibility="processor_count determines tree edges and is changed during OP_SET_PROCESSOR_COUNT"; attribute :>> targetContract="Keep old committed rendezvous intact while staging bootstrap routes; collective generation switch once requested children ready"; attribute :>> boundary="Requires barrier topology redesign; a field rename is insufficient"; }
part memberRole3:MembershipRole { ref part :>> need=membership; attribute :>> roleId="BOUND-CHILD"; attribute :>> sourceAnchors="setup.c:805-835;os_thread.c:426-439,493-512"; attribute :>> currentResponsibility="OS child sets PSTATE TLS then enters resize synchronization"; attribute :>> targetContract="Bootstrap wait is outside committed collector set; source/root epoch reloaded before Scheme entry"; attribute :>> boundary="Binding, result publication and resume readiness are independent"; }
part memberRole4:MembershipRole { ref part :>> need=membership; attribute :>> roleId="COLLECTOR-MEMBERS"; attribute :>> sourceAnchors="mem.c:6590-6632,6790-6868"; attribute :>> currentResponsibility="processor_count partitions globals and worker root/scan participation"; attribute :>> targetContract="One immutable per-round member generation with full root/worker authorization; bootstrap registry scanned independently"; attribute :>> boundary="Existing PSTATE/member-index coupling must be migrated explicitly"; }
part def SourceRoute { ref part need:GambitAssuranceRouting::ModelNeed; attribute sourceAnchors:String; attribute projection:String; attribute failureCustodian:String; attribute status:String; }
part route0:SourceRoute { ref part :>> need=rootView; attribute :>> sourceAnchors="_ptree2.scm:2850-2869;_t-c-2.scm:157-224;_kernel.c:26338-26368,30819-30821"; attribute :>> projection="Freeze complete location/context view; acquire origin before first sync/GC; reload source location after relocation"; attribute :>> failureCustodian="Caller view until VM descriptor accepted; then VM overlap until child activation acceptance"; attribute :>> status="source-and-C-order-refinement-open"; }
part route1:SourceRoute { ref part :>> need=gate; attribute :>> sourceAnchors="setup.c:1132-1178;mem.c:6790-6868"; attribute :>> projection="Accept-before-close enters pinned snapshot; close-before-accept leaves only safe metadata pending and frozen caller authoritative"; attribute :>> failureCustodian="Frozen caller map/VM-held view pin, not unregistered native slot"; attribute :>> status="source-and-C-order-refinement-open"; }
part route2:SourceRoute { ref part :>> need=membership; attribute :>> sourceAnchors="setup.c:655-656,941-1003;mem.c:6590-6632"; attribute :>> projection="Prepare -> root/routing descriptor -> OS outcome+binding -> collective generation commit"; attribute :>> failureCustodian="Resize transaction/VM until exact all-child ready commit or explicit abort/drain"; attribute :>> status="source-and-C-order-refinement-open"; }
part route3:SourceRoute { ref part :>> need=rollback; attribute :>> sourceAnchors="setup.c:941-1003;os_thread.c:493-539"; attribute :>> projection="Per-child ledger Prepared/Creating/Success/Failure/Unknown/Stopped/Retired; cancel admission then drain known starts"; attribute :>> failureCustodian="VM holds each successful or unknown child resource until exact stop/no-child and scanner drain"; attribute :>> status="source-and-C-order-refinement-open"; }
part route4:SourceRoute { ref part :>> need=order; attribute :>> sourceAnchors="setup.c:550-712;gambit.h.in:11599-11603;os_thread.c:493-566"; attribute :>> projection="VIEW/CLOSE/DEFER/CREATE/COMMIT/RETIRE actual C refinement"; attribute :>> failureCustodian="VM bootstrap root -> exact activation acceptance; parent map pinned through retries"; attribute :>> status="source-and-C-order-refinement-open"; }
part def DiagramNode { attribute nodeId:String; attribute labelText:String; }
part def DiagramEdge { ref part producer:DiagramNode; ref part consumer:DiagramNode; attribute labelText:String; }
part node0:DiagramNode { attribute :>> nodeId="rootView"; attribute :>> labelText="Generated frame and full caller view"; }
part node1:DiagramNode { attribute :>> nodeId="freeze"; attribute :>> labelText="Freeze caller and stop raw borrows"; }
part node2:DiagramNode { attribute :>> nodeId="gate"; attribute :>> labelText="Register versus GC close"; }
part node3:DiagramNode { attribute :>> nodeId="pending"; attribute :>> labelText="Frozen caller retains late descriptor"; }
part node4:DiagramNode { attribute :>> nodeId="reload"; attribute :>> labelText="GC update and source reload"; }
part node5:DiagramNode { attribute :>> nodeId="root"; attribute :>> labelText="VM bootstrap root and child ledger"; }
part node6:DiagramNode { attribute :>> nodeId="routing"; attribute :>> labelText="Prepared routing; old GC membership"; }
part node7:DiagramNode { attribute :>> nodeId="create"; attribute :>> labelText="Per-child OS creation and binding"; }
part node8:DiagramNode { attribute :>> nodeId="commit"; attribute :>> labelText="All-ready generation commit"; }
part node9:DiagramNode { attribute :>> nodeId="run"; attribute :>> labelText="Post-sync reload to activation"; }
part node10:DiagramNode { attribute :>> nodeId="abort"; attribute :>> labelText="Partial failure; close and retain"; }
part node11:DiagramNode { attribute :>> nodeId="drain"; attribute :>> labelText="Exact no-child or stop; reader drain"; }
part node12:DiagramNode { attribute :>> nodeId="retire"; attribute :>> labelText="Cleanup exact child then retire root"; }
part edge0:DiagramEdge { ref part :>> producer=node0; ref part :>> consumer=node1; attribute :>> labelText="reuse precise stack slots"; }
part edge1:DiagramEdge { ref part :>> producer=node1; ref part :>> consumer=node2; attribute :>> labelText="single admission cut"; }
part edge2:DiagramEdge { ref part :>> producer=node2; ref part :>> consumer=node3; attribute :>> labelText="close wins"; }
part edge3:DiagramEdge { ref part :>> producer=node3; ref part :>> consumer=node4; attribute :>> labelText="no raw borrow while waiting"; }
part edge4:DiagramEdge { ref part :>> producer=node4; ref part :>> consumer=node2; attribute :>> labelText="same identity retry"; }
part edge5:DiagramEdge { ref part :>> producer=node2; ref part :>> consumer=node5; attribute :>> labelText="register wins"; }
part edge6:DiagramEdge { ref part :>> producer=node5; ref part :>> consumer=node6; attribute :>> labelText="root before routing"; }
part edge7:DiagramEdge { ref part :>> producer=node6; ref part :>> consumer=node7; attribute :>> labelText="one attempt per child"; }
part edge8:DiagramEdge { ref part :>> producer=node7; ref part :>> consumer=node8; attribute :>> labelText="all requested ready"; }
part edge9:DiagramEdge { ref part :>> producer=node8; ref part :>> consumer=node9; attribute :>> labelText="shared membership generation"; }
part edge10:DiagramEdge { ref part :>> producer=node7; ref part :>> consumer=node10; attribute :>> labelText="known failure or unknown"; }
part edge11:DiagramEdge { ref part :>> producer=node10; ref part :>> consumer=node11; attribute :>> labelText="no bulk rollback"; }
part edge12:DiagramEdge { ref part :>> producer=node11; ref part :>> consumer=node12; attribute :>> labelText="only proven stopped children"; }
part edge13:DiagramEdge { ref part :>> producer=node10; ref part :>> consumer=node5; attribute :>> labelText="unknown stays VM owned"; }
part def ResearchGate { attribute gateId:String; }
part def GateNeed { ref part gate:ResearchGate; ref part need:GambitAssuranceRouting::ModelNeed; }
part gateRow0:ResearchGate { attribute :>> gateId="root-admission"; }
part gateNeed0:GateNeed { ref part :>> gate=gateRow0; ref part :>> need=GambitResizeBootstrapAdmission::rootView; }
part gateNeed1:GateNeed { ref part :>> gate=gateRow0; ref part :>> need=GambitResizeBootstrapAdmission::gate; }
part gateNeed2:GateNeed { ref part :>> gate=gateRow0; ref part :>> need=GambitResizeBootstrapAdmission::order; }
part gateNeed3:GateNeed { ref part :>> gate=gateRow0; ref part :>> need=GambitResizeBootstrapAdmission::priorRoot; }
part gateRow1:ResearchGate { attribute :>> gateId="member-commit"; }
part gateNeed4:GateNeed { ref part :>> gate=gateRow1; ref part :>> need=GambitResizeBootstrapAdmission::membership; }
part gateNeed5:GateNeed { ref part :>> gate=gateRow1; ref part :>> need=GambitResizeBootstrapAdmission::rollback; }
part gateNeed6:GateNeed { ref part :>> gate=gateRow1; ref part :>> need=GambitResizeBootstrapAdmission::priorReload; }
part gateRow2:ResearchGate { attribute :>> gateId="first-cut"; }
part gateNeed7:GateNeed { ref part :>> gate=gateRow2; ref part :>> need=GambitResizeBootstrapAdmission::rootView; }
part gateNeed8:GateNeed { ref part :>> gate=gateRow2; ref part :>> need=GambitResizeBootstrapAdmission::gate; }
part gateNeed9:GateNeed { ref part :>> gate=gateRow2; ref part :>> need=GambitResizeBootstrapAdmission::membership; }
part gateNeed10:GateNeed { ref part :>> gate=gateRow2; ref part :>> need=GambitResizeBootstrapAdmission::rollback; }
part gateNeed11:GateNeed { ref part :>> gate=gateRow2; ref part :>> need=GambitResizeBootstrapAdmission::order; }
part gateNeed12:GateNeed { ref part :>> gate=gateRow2; ref part :>> need=GambitResizeBootstrapAdmission::priorScope; }
part gateNeed13:GateNeed { ref part :>> gate=gateRow2; ref part :>> need=GambitResizeBootstrapAdmission::priorRoot; }
part gateNeed14:GateNeed { ref part :>> gate=gateRow2; ref part :>> need=GambitResizeBootstrapAdmission::priorReload; }
part def AdmissionCut { attribute completeView:Boolean; attribute frozen:Boolean; attribute sourceHeld:Boolean; attribute registered:Boolean; attribute gcClosed:Boolean; attribute includedInSnapshot:Boolean; attribute allRequestedReady:Boolean; attribute outcomeUnknown:Boolean; attribute memberCommitted:Boolean; attribute stopOrNoChild:Boolean; attribute readersDrained:Boolean; attribute canAdmitRoot:Boolean=not registered and not gcClosed and completeView and frozen and sourceHeld; attribute rootCovered:Boolean=(registered and (not gcClosed or includedInSnapshot)) or (sourceHeld and completeView and frozen); attribute canCommit:Boolean=registered and not gcClosed and allRequestedReady and not outcomeUnknown; attribute canReclaim:Boolean=not memberCommitted and not outcomeUnknown and stopOrNoChild and readersDrained; }
part openFrozen:AdmissionCut { attribute :>> completeView=true; attribute :>> frozen=true; attribute :>> sourceHeld=true; attribute :>> registered=false; attribute :>> gcClosed=false; attribute :>> includedInSnapshot=false; attribute :>> allRequestedReady=false; attribute :>> outcomeUnknown=false; attribute :>> memberCommitted=false; attribute :>> stopOrNoChild=false; attribute :>> readersDrained=false; }
part uncoveredLate:AdmissionCut { attribute :>> completeView=true; attribute :>> frozen=false; attribute :>> sourceHeld=false; attribute :>> registered=true; attribute :>> gcClosed=true; attribute :>> includedInSnapshot=false; attribute :>> allRequestedReady=false; attribute :>> outcomeUnknown=false; attribute :>> memberCommitted=false; attribute :>> stopOrNoChild=false; attribute :>> readersDrained=false; }
part lateFrozen:AdmissionCut { attribute :>> completeView=true; attribute :>> frozen=true; attribute :>> sourceHeld=true; attribute :>> registered=false; attribute :>> gcClosed=true; attribute :>> includedInSnapshot=false; attribute :>> allRequestedReady=false; attribute :>> outcomeUnknown=false; attribute :>> memberCommitted=false; attribute :>> stopOrNoChild=false; attribute :>> readersDrained=false; }
part registeredSnapshot:AdmissionCut { attribute :>> completeView=true; attribute :>> frozen=true; attribute :>> sourceHeld=false; attribute :>> registered=true; attribute :>> gcClosed=true; attribute :>> includedInSnapshot=true; attribute :>> allRequestedReady=false; attribute :>> outcomeUnknown=false; attribute :>> memberCommitted=false; attribute :>> stopOrNoChild=false; attribute :>> readersDrained=false; }
part unknownReady:AdmissionCut { attribute :>> completeView=true; attribute :>> frozen=true; attribute :>> sourceHeld=false; attribute :>> registered=true; attribute :>> gcClosed=false; attribute :>> includedInSnapshot=false; attribute :>> allRequestedReady=true; attribute :>> outcomeUnknown=true; attribute :>> memberCommitted=false; attribute :>> stopOrNoChild=false; attribute :>> readersDrained=true; }
part allReady:AdmissionCut { attribute :>> completeView=true; attribute :>> frozen=true; attribute :>> sourceHeld=false; attribute :>> registered=true; attribute :>> gcClosed=false; attribute :>> includedInSnapshot=false; attribute :>> allRequestedReady=true; attribute :>> outcomeUnknown=false; attribute :>> memberCommitted=false; attribute :>> stopOrNoChild=false; attribute :>> readersDrained=true; }
part knownStopped:AdmissionCut { attribute :>> completeView=true; attribute :>> frozen=true; attribute :>> sourceHeld=false; attribute :>> registered=true; attribute :>> gcClosed=false; attribute :>> includedInSnapshot=false; attribute :>> allRequestedReady=false; attribute :>> outcomeUnknown=false; attribute :>> memberCommitted=false; attribute :>> stopOrNoChild=true; attribute :>> readersDrained=true; }
requirement def RootCoverageLaw { subject cut:AdmissionCut; require constraint { not cut.registered or cut.rootCovered } }
part def CapacityArithmetic { attribute processors:Integer; attribute minSectionsPerProcessor:Integer=2; attribute sectionWords:Integer=131072; attribute wordBytes:Integer=8; attribute minWords:Integer=processors*minSectionsPerProcessor*sectionWords; attribute payloadBytes:Integer=minWords*wordBytes; }
part capacityOne:CapacityArithmetic { attribute :>> processors=1; }
part capacityTwo:CapacityArithmetic { attribute :>> processors=2; }
part def CarrierArithmetic { attribute carriers:Integer; attribute wordBytes:Integer=8; attribute separateBytes:Integer=carriers*wordBytes; attribute sharedBytes:Integer=wordBytes; attribute slotSavingBytes:Integer=separateBytes-sharedBytes; }
part flat:CarrierArithmetic { attribute :>> carriers=1; }
part shared:CarrierArithmetic { attribute :>> carriers=8; }
}
