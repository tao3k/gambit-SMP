package GambitVMResizeTransaction {
  private import ScalarValues::*;
  ref part baseline = GambitModernCBootstrapCohort::startupCapacity;
  ref part admission = GambitModernCCommitAdmission::tests;
  attribute runtimeAdmitted : Boolean = false;
  attribute commitAdmitted : Boolean = false;
  part def Contract { attribute id:String; attribute source:String; attribute invariant:String; attribute retired:String; attribute cost:String; }
  part census:Contract { attribute :>> id="census"; attribute :>> source="lib/setup.c ___vm_resize_pstate; lib/mem.c resize_heap"; attribute :>> invariant="Current GC census is closed independently of requested future members. GC retains actual assigned intervals plus one region for each actual fudge-restoration endpoint."; attribute :>> retired="target_processor_count_ scalar and conditional-only nominal floor"; attribute :>> cost="Closed-census restoration count and explicit physical growth reservation; no measured peak reduction"; }
  part grant:Contract { attribute :>> id="grant"; attribute :>> source="lib/mem.c ___reserve_vm_resize; ___setup_mem_pstate; ___rollback_vm_resize"; attribute :>> invariant="Before any new setup, charge all disjoint stack/heap pairs on the actual list. No fallback sharing for new contexts. Partial allocation returns to pre-grant capacity. Unknown native result never produces a grant."; attribute :>> retired="Each new setup independently acquiring sections and falling into fatal sharing fallback"; attribute :>> cost="Two section pointers and fixed status per slot; peak is actual required intervals minus usable existing capacity"; }
  part roots:Contract { attribute :>> id="roots"; attribute :>> source="setup.c start_processor_execution/___run; mem.c mark_vm_scmobj/mark_execution_roots; c_intf.c rooted marker endpoint"; attribute :>> invariant="VM roots thunk before GC; context roots it before member commit; thread reloads after sync; marker allocation reloads registered cell; entry marker invalidates before retirement. Legacy raw SFUN registration is still unqualified."; attribute :>> retired="thread.data_scmobj and pre-sync C local as implicit roots"; attribute :>> cost="Two root cells per execution context and one VM root; scan those cells, no duplicate heap traversal claim"; }
  part publication:Contract { attribute :>> id="publication"; attribute :>> source="setup.c created-thread entry gate; old-set OP_SET_PROCESSOR_COUNT; new-set finish"; attribute :>> invariant="Threads are created while parked outside Scheme/TLS participation. Publish members only after all setups and creates succeed; then release entry and consume completion with the new set."; attribute :>> retired="Publish count before pthread_create; fatal on partially created member population"; attribute :>> cost="One VM mutex/condition variable, parked entry and completion collective; existing barrier C-memory-model refinement stays open"; }
  part failure:Contract { attribute :>> id="failure"; attribute :>> source="setup.c abort/join/cleanup; os_thread.c create/join return-code adapters"; attribute :>> invariant="Known create failure has no child. Abort releases created threads to return without Scheme; cleanup/refund only after every join succeeds. Interrupted call or failed/unknown join retains slots, roots and grant, blocks GC/reuse/cleanup. No owner-death takeover is inferred."; attribute :>> retired="errno-based pthread result decoding; ignored shrink join; reclaim without quiescence"; attribute :>> cost="Fixed progress records, cancellation exclusion on POSIX; unknown state sacrifices progress rather than custody"; }
  part retirement:Contract { attribute :>> id="retirement"; attribute :>> source="mem.c ___can_retire_pstate/___transfer_retired_still; setup.c post-join cleanup"; attribute :>> invariant="Reject RC/native borrowed, foreign-effectful and extra retained-marker domains before shrinking. Admitted entry invalidates on its owner; after join move still ownership to active collector context instead of treating context death as object death. Unmanaged raw writers and nested FFI remain open."; attribute :>> retired="Unconditional free_still_objs/cleanup_rc on successful member retirement"; attribute :>> cost="Admission walk and still-chain splice; stricter refusal for domains without freeze/effect receipts"; }
  part def Obligation { ref part component:Contract; attribute id:String; attribute method:String; attribute artifact:String; attribute premise:String; }
  part observed:Obligation { ref part :>> component=census; attribute :>> id="VR-CENSUS"; attribute :>> method="native-diagnostic"; attribute :>> artifact="evidence/research/modern-c-bootstrap/startup-census.json"; attribute :>> premise="Unmodified predecessor p11: six total/two assigned before GC; six total after GC; third new context fails. Read-only process memory, not acceptance or cost measurement."; }
  part model:Obligation { ref part :>> component=publication; attribute :>> id="VR-QNT"; attribute :>> method="quint"; attribute :>> artifact="dev/refactoring/modern-c/models/quint/vm_resize_transaction.qnt"; attribute :>> premise="Concrete ledger phases, parked native threads, no-publication-before-create, failure/unknown custody and two membership sets; finite histories only."; }
  part proof:Obligation { ref part :>> component=grant; attribute :>> id="VR-LEAN"; attribute :>> method="lean"; attribute :>> artifact="dev/refactoring/modern-c/models/lean/VMResizeTransaction.lean"; attribute :>> premise="Conditional physical capacity, initialized/created coverage, refund after quiescence and roots retained on unknown result. Actual allocator/atomic steps require C refinement."; }
  part native:Obligation { ref part :>> component=roots; attribute :>> id="VR-NATIVE"; attribute :>> method="native"; attribute :>> artifact="evidence/research/modern-c-bootstrap/resize-bootstrap.recipe.json"; attribute :>> premise="Exact new source/profile complete bootstrap, host-budget map/continuation/GC, resize cycles and actual create/join fault controls; never import old pass."; }
  part refine:Obligation { ref part :>> component=failure; attribute :>> id="VR-REFINE"; attribute :>> method="source-refinement"; attribute :>> artifact="vendor/gambit/lib/setup.c"; attribute :>> premise="OPEN: full barrier memory model, nonlocal escape/stop receipts, raw FFI writers, allocator interruption, retired processor identity and destructor affinity; no unconditional recovery claim."; }
  part def Edge { ref part producer:Contract; ref part consumer:Contract; }
  part a:Edge { ref part :>> producer=census; ref part :>> consumer=grant; }
  part b:Edge { ref part :>> producer=roots; ref part :>> consumer=grant; }
  part c:Edge { ref part :>> producer=grant; ref part :>> consumer=publication; }
  part d:Edge { ref part :>> producer=publication; ref part :>> consumer=failure; }
  part e:Edge { ref part :>> producer=failure; ref part :>> consumer=retirement; }
}
